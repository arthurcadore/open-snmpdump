-- =========================================================================
-- Copyright (C) 2023 Intelbras S.A. All rights reserved.
--
-- Description: DHCP Snooping MIB 2
-- Reference:
-- Version:     V1.6
-- History:
-- V1.0 The initial version, created by lilin, 2012.05.15
-- V1.1 Modified the mib description by lilin, 2013.04.15
-- V1.2 Modified ibDhcpSnoop2IfMaxLearnNum by yuguoqing, 2014.03.20
-- V1.3 Modified ibDhcpSnoop2IfOpt82CIDMode by heminhong, 2017.01.13
-- V1.4 Modified ibDhcpSnoop2BindDbName by wugang, 2021.07.05
-- V1.5 Modified ibDhcpSnoop2Traps by wanganyu, 2022.05.16
-- V1.6 Add ibDhcpSnoop2UntrustRelpyAlm and ibDhcpSnoop2RateLimitAlm
--      by wanganyu, 2022.07.22
-- =========================================================================
IB-DHCP-SNOOP2-MIB DEFINITIONS ::= BEGIN

-- =========================================================================
-- Imported variables and types
-- =========================================================================
IMPORTS
    TruthValue, RowStatus, MacAddress
        FROM SNMPv2-TC
    MODULE-IDENTITY, OBJECT-TYPE, Counter64, Unsigned32, NOTIFICATION-TYPE
        FROM SNMPv2-SMI
    ifIndex, InterfaceIndexOrZero, ifName
        FROM IF-MIB
    InetAddressIPv4
        FROM INET-ADDRESS-MIB
    ibCommon
        FROM IB-OID-MIB;

-- =========================================================================
-- Module identity
-- =========================================================================
ibDhcpSnoop2 MODULE-IDENTITY
    LAST-UPDATED "202207260000Z"
    ORGANIZATION
        "Intelbras S.A. Industria de Telecomunicacao Eletronica Brasileria."
    CONTACT-INFO
        ""
    DESCRIPTION "DHCP SNOOPING MIB 2"
    REVISION
        "202207260000Z"
    DESCRIPTION
        "Modified to add 'Trap' mode."
    REVISION
        "202107050000Z"
    DESCRIPTION
        "Modified to add 'ibDhcpSnoop2BindDbName' mode."
    REVISION
        "201701130000Z"
    DESCRIPTION
        "Modified to add 'ibDhcpSnoop2IfOpt82CIDMode' mode."
    REVISION
         "201304150000Z"
    DESCRIPTION
        "The private MIB file includes the DHCP Snooping profile."
    ::= { ibCommon  124 }

-- ==========================================================================
-- Scalar objects definition
-- ==========================================================================
    ibDhcpSnoop2ScalarObjects OBJECT IDENTIFIER ::= {  ibDhcpSnoop2 1  }

-- ==================================================================
-- ibDhcpSnoop2ScalarObjects: ibDhcpSnoop2ConfigGroup
-- ==================================================================
ibDhcpSnoop2ConfigGroup   OBJECT IDENTIFIER ::= { ibDhcpSnoop2ScalarObjects 1 }

ibDhcpSnoop2Enabled OBJECT-TYPE
    SYNTAX     TruthValue
    MAX-ACCESS read-write
    STATUS     current
    DESCRIPTION
        "If the value of this object is set to 'true',
         DHCP snooping is enabled."
    DEFVAL { false }
    ::= { ibDhcpSnoop2ConfigGroup 1 }

ibDhcpSnoop2BindDbName OBJECT-TYPE
    SYNTAX     OCTET STRING(SIZE(0..255))
    MAX-ACCESS read-write
    STATUS     current
    DESCRIPTION
        "Name of the file that used to store binding information.

         If the value of the object is set to a zero-length string,
         the configuration will be removed."
    ::= { ibDhcpSnoop2ConfigGroup 2 }

ibDhcpSnoop2BindRefreshIntvl OBJECT-TYPE
    SYNTAX     Unsigned32(60..864000)
    MAX-ACCESS read-write
    STATUS     current
    DESCRIPTION
        "The refresh interval of the binding information in seconds."
    DEFVAL { 300 }
    ::= { ibDhcpSnoop2ConfigGroup 3 }

ibDhcpSnoop2BindRefresh OBJECT-TYPE
    SYNTAX     INTEGER
    {
        on(1)
    }
    MAX-ACCESS read-write
    STATUS     current
    DESCRIPTION
        "If the value of this object is set to 'on', the binding
         information will be refreshed immediately."
    ::= { ibDhcpSnoop2ConfigGroup 4 }

-- ==================================================================
-- ibDhcpSnoop2ScalarObjects: ibDhcpSnoop2StatisticsGroup
-- ==================================================================
ibDhcpSnoop2StatisticsGroup   OBJECT IDENTIFIER ::= { ibDhcpSnoop2ScalarObjects 2 }

ibDhcpSnoop2PktSentNum OBJECT-TYPE
    SYNTAX      Counter64
    MAX-ACCESS  read-only
    STATUS      current
    DESCRIPTION
        "The total number of the packets send by DHCP snooping."
    ::= { ibDhcpSnoop2StatisticsGroup 1 }

ibDhcpSnoop2PktRcvNum OBJECT-TYPE
    SYNTAX      Counter64
    MAX-ACCESS  read-only
    STATUS      current
    DESCRIPTION
        "The total number of the packets received by
         DHCP snooping."
    ::= { ibDhcpSnoop2StatisticsGroup 2 }

ibDhcpSnoop2PktDropNum OBJECT-TYPE
    SYNTAX      Counter64
    MAX-ACCESS  read-only
    STATUS      current
    DESCRIPTION
        "The total number of the packets dropped by
         DHCP snooping."
    ::= { ibDhcpSnoop2StatisticsGroup 3 }

ibDhcpSnoop2TrapDropNum OBJECT-TYPE
    SYNTAX      Counter64
    MAX-ACCESS  read-only
    STATUS      current
    DESCRIPTION
        "The number of the packets dropped for Trap."
    ::= { ibDhcpSnoop2StatisticsGroup 4 }

ibDhcpSnoop2PktVlanID OBJECT-TYPE
    SYNTAX      Unsigned32(1..4094)
    MAX-ACCESS  accessible-for-notify
    STATUS      current
    DESCRIPTION
        "VLAN ID."
    ::= { ibDhcpSnoop2StatisticsGroup 5 }
-- ==========================================================================
-- Table definition
-- ==========================================================================
    ibDhcpSnoop2Tables OBJECT IDENTIFIER ::= {  ibDhcpSnoop2 2  }

-- ==========================================================================
-- 1st Table of ibDhcpSnoop2Tables: ibDhcpSnoop2BindTable
-- ==========================================================================
ibDhcpSnoop2BindTable OBJECT-TYPE
    SYNTAX     SEQUENCE OF IbDhcpSnoop2BindEntry
    MAX-ACCESS not-accessible
    STATUS     current
    DESCRIPTION
        "The table containing information of DHCP clients listened by
         DHCP snooping."
    ::= { ibDhcpSnoop2Tables 1 }

ibDhcpSnoop2BindEntry OBJECT-TYPE
    SYNTAX     IbDhcpSnoop2BindEntry
    MAX-ACCESS not-accessible
    STATUS     current
    DESCRIPTION
        "An entry containing information of DHCP clients."
    INDEX
        {
            ibDhcpSnoop2BindIpAddr,
            ibDhcpSnoop2BindVlanId,
            ibDhcpSnoop2BindSecVlanId
        }
    ::= { ibDhcpSnoop2BindTable 1 }

IbDhcpSnoop2BindEntry ::=
    SEQUENCE
        {
            ibDhcpSnoop2BindIpAddr           InetAddressIPv4,
            ibDhcpSnoop2BindVlanId           Unsigned32,
            ibDhcpSnoop2BindSecVlanId        Unsigned32,
            ibDhcpSnoop2BindMacAddr          MacAddress,
            ibDhcpSnoop2BindLease            Unsigned32,
            ibDhcpSnoop2BindPortIndex        InterfaceIndexOrZero,
            ibDhcpSnoop2BindRowStatus        RowStatus
        }

ibDhcpSnoop2BindIpAddr OBJECT-TYPE
    SYNTAX     InetAddressIPv4
    MAX-ACCESS not-accessible
    STATUS     current
    DESCRIPTION
        "DHCP client's IP addresses collected by DHCP snooping."
    ::= { ibDhcpSnoop2BindEntry 1 }

ibDhcpSnoop2BindVlanId OBJECT-TYPE
    SYNTAX     Unsigned32(1..4094)
    MAX-ACCESS not-accessible
    STATUS     current
    DESCRIPTION
        "DHCP client's VLAN ID collected by DHCP snooping."
    ::= { ibDhcpSnoop2BindEntry 2 }

ibDhcpSnoop2BindSecVlanId OBJECT-TYPE
    SYNTAX     Unsigned32(1..4094 | 65535)
    MAX-ACCESS not-accessible
    STATUS     current
    DESCRIPTION
        "DHCP client's second VLAN ID collected by DHCP snooping.
         65535 means no second VLAN."
    ::= { ibDhcpSnoop2BindEntry 3 }

ibDhcpSnoop2BindMacAddr OBJECT-TYPE
    SYNTAX     MacAddress
    MAX-ACCESS read-only
    STATUS     current
    DESCRIPTION
        "DHCP client's MAC address collected by DHCP snooping."
    ::= { ibDhcpSnoop2BindEntry 4 }

ibDhcpSnoop2BindLease OBJECT-TYPE
    SYNTAX     Unsigned32
    MAX-ACCESS read-only
    STATUS     current
    DESCRIPTION
        "Left lease time in seconds collected by DHCP snooping.
         The value of this object cannot be 0."
    ::= { ibDhcpSnoop2BindEntry 5 }

ibDhcpSnoop2BindPortIndex OBJECT-TYPE
    SYNTAX     InterfaceIndexOrZero
    MAX-ACCESS read-only
    STATUS     current
    DESCRIPTION
        "DHCP client's port index collected by DHCP snooping.
         The value of zero means unknown port."
    ::= { ibDhcpSnoop2BindEntry 6 }

ibDhcpSnoop2BindRowStatus    OBJECT-TYPE
     SYNTAX      RowStatus
     MAX-ACCESS  read-create
     STATUS      current
     DESCRIPTION
         "RowStatus.  Only destroy action is allow to use."
     ::= { ibDhcpSnoop2BindEntry 7 }

-- ==========================================================================
-- 2nd Table of ibDhcpSnoop2Tables: ibDhcpSnoop2IfConfigTable
-- ==========================================================================
ibDhcpSnoop2IfConfigTable OBJECT-TYPE
    SYNTAX     SEQUENCE OF IbDhcpSnoop2IfConfigEntry
    MAX-ACCESS not-accessible
    STATUS     current
    DESCRIPTION
        "A table is used to configure DHCP snooping functions on ports."
    ::= {ibDhcpSnoop2Tables 2 }

ibDhcpSnoop2IfConfigEntry OBJECT-TYPE
    SYNTAX     IbDhcpSnoop2IfConfigEntry
    MAX-ACCESS not-accessible
    STATUS     current
    DESCRIPTION
        "An entry containing DHCP snooping configurations of ports."
    INDEX   { ifIndex }
    ::= {ibDhcpSnoop2IfConfigTable 1}

IbDhcpSnoop2IfConfigEntry  ::=
    SEQUENCE
        {
            ibDhcpSnoop2IfTrustStatus                INTEGER,
            ibDhcpSnoop2IfCheckMac                   TruthValue,
            ibDhcpSnoop2IfCheckRequest               TruthValue,
            ibDhcpSnoop2IfRateLimit                  Unsigned32,
            ibDhcpSnoop2IfRecordBind                 TruthValue,
            ibDhcpSnoop2IfMaxLearnNum                Unsigned32,
            ibDhcpSnoop2IfOpt82Enable                TruthValue,
            ibDhcpSnoop2IfOpt82Strategy              INTEGER,
            ibDhcpSnoop2IfOpt82CIDMode               INTEGER,
            ibDhcpSnoop2IfOpt82CIDNodeType           INTEGER,
            ibDhcpSnoop2IfOpt82CIDNodeStr            OCTET STRING,
            ibDhcpSnoop2IfOpt82CIDStr                OCTET STRING,
            ibDhcpSnoop2IfOpt82CIDFormat             INTEGER,
            ibDhcpSnoop2IfOpt82RIDMode               INTEGER,
            ibDhcpSnoop2IfOpt82RIDStr                OCTET STRING,
            ibDhcpSnoop2IfOpt82RIDFormat             INTEGER
        }

ibDhcpSnoop2IfTrustStatus OBJECT-TYPE
    SYNTAX     INTEGER
    {
        untrusted(0),
        trusted(1)
    }
    MAX-ACCESS read-write
    STATUS     current
    DESCRIPTION
        "Trusted status of the port."
    DEFVAL { untrusted }
    ::= { ibDhcpSnoop2IfConfigEntry 1 }

ibDhcpSnoop2IfCheckMac OBJECT-TYPE
    SYNTAX      TruthValue
    MAX-ACCESS  read-write
    STATUS      current
    DESCRIPTION
        "If the value is 'true', MAC address of DHCP packets received
         on the port will be checked."
    DEFVAL { false }
    ::= { ibDhcpSnoop2IfConfigEntry 2 }

ibDhcpSnoop2IfCheckRequest OBJECT-TYPE
    SYNTAX     TruthValue
    MAX-ACCESS read-write
    STATUS     current
    DESCRIPTION
        "If the value is 'true', DHCP request packets will be checked."
    DEFVAL { false }
    ::= { ibDhcpSnoop2IfConfigEntry 3 }

ibDhcpSnoop2IfRateLimit OBJECT-TYPE
    SYNTAX     Unsigned32
    MAX-ACCESS read-write
    STATUS     current
    DESCRIPTION
        "The rate limit in Kbps.
         If the value is 0, there is no rate limit on the port."
    DEFVAL { 0 }
    ::= { ibDhcpSnoop2IfConfigEntry 4 }

ibDhcpSnoop2IfRecordBind OBJECT-TYPE
    SYNTAX     TruthValue
    MAX-ACCESS read-write
    STATUS     current
    DESCRIPTION
        "If the value is 'true', information of DHCP packets received
         on the port will be recorded."
    DEFVAL { false }
    ::= { ibDhcpSnoop2IfConfigEntry 5 }

ibDhcpSnoop2IfMaxLearnNum OBJECT-TYPE
    SYNTAX     Unsigned32(0..4294967295)
    MAX-ACCESS read-write
    STATUS     current
    DESCRIPTION
        "The maximum number of binding entries that could be learned on
         the port.
         If the value is 0, it means that there is no threshold on the
         port."
    DEFVAL { 0 }
    ::= { ibDhcpSnoop2IfConfigEntry 6 }

ibDhcpSnoop2IfOpt82Enable OBJECT-TYPE
    SYNTAX     TruthValue
    MAX-ACCESS read-write
    STATUS     current
    DESCRIPTION
        "If DHCP snooping supports option 82 functions, the
         value is 'true'.
         If DHCP snooping does NOT support option 82 functions,
         the value is 'false'."
    DEFVAL     { false }
    ::= { ibDhcpSnoop2IfConfigEntry 7 }

ibDhcpSnoop2IfOpt82Strategy     OBJECT-TYPE
    SYNTAX      INTEGER
    {
        drop(1),
        keep(2),
        replace(3)
    }
    MAX-ACCESS  read-write
    STATUS      current
    DESCRIPTION
        "The strategy of DHCP snooping handling option 82.

         'drop' indicates DHCP snooping discarding the request
         packet including option 82.

         'keep' indicates DHCP snooping accepting the request
         packet without any change of the option 82.

         'replace' indicates DHCP snooping accepting the
         request packet on condition that it generates a new
         option 82 to replace the original one."
    DEFVAL      { replace }
    ::= { ibDhcpSnoop2IfConfigEntry 8 }

ibDhcpSnoop2IfOpt82CIDMode OBJECT-TYPE
    SYNTAX      INTEGER
    {
        normal(1),
        verbose(2),
        userDefine(3),
        bas(4)
    }
    MAX-ACCESS  read-write
    STATUS      current
    DESCRIPTION
        "The mode of filling in the circuit ID suboption
         of DHCP option 82.

         'normal' is the standard mode.

         'verbose' is the detailed mode.

         'userDefine' is the user-defined mode.

         'bas' is the bas mode.

         If the value of this object is set to 'userDefine',
         ibDhcpSnoop2IfOpt82CIDStr must also be set."
    DEFVAL      { normal }
    ::= { ibDhcpSnoop2IfConfigEntry 9 }

ibDhcpSnoop2IfOpt82CIDNodeType OBJECT-TYPE
    SYNTAX     INTEGER
    {
        invalid(1),
        mac(2),
        sysname(3),
        userDefine(4)
    }
    MAX-ACCESS read-write
    STATUS     current
    DESCRIPTION
        "Type of access node identifier that is used to fill
         in the circuit ID suboption of option 82 when the value
         of ibDhcpSnoop2IfOption82CIDMode is set to 'verbose'.

         The SET operation of this object must be with the SET
         operation of ibDhcpSnoop2IfOpt82CIDMode.

         'invalid' indicates that the node identifier is NOT used
         to fill in the circuit ID suboption of option 82.
         If the value of ibDhcpSnoop2IfOpt82CIDMode is NOT
         'verbose', the value of this object is set to 'invalid'
         automatically.
         Otherwise the value of this object cannot be set to 'invalid'.

         'mac' indicates that the node identifier is
         filled in with the bridge MAC of DHCP snooping device.
         If the value of ibDhcpSnoop2IfOpt82CIDMode is set to
         'verbose', the default value of this object is 'mac'.

         'sysname' indicates that the node identifier
         is filled in with the sysname of the DHCP snooping.

         'userDefine' indicates the node identifier
         is filled in with the string defined by the object
         of ibDhcpSnoop2IfOpt82CIDNodeStr.
         If the value is set to 'userDefine', the value of
         ibDhcpSnoop2IfOpt82CIDNodeStr must also be set to
         a non-zero length string."
    ::= { ibDhcpSnoop2IfConfigEntry 10 }

ibDhcpSnoop2IfOpt82CIDNodeStr      OBJECT-TYPE
    SYNTAX     OCTET STRING(SIZE(0..50))
    MAX-ACCESS read-write
    STATUS     current
    DESCRIPTION
        "The string defined by user to fill in the
         node identifier in the verbose mode.

         If the value of ibDhcpSnoop2IfOpt82CIDMode is NOT
         'verbose', or the value of ibDhcpSnoop2IfOpt82CIDNodeType
         is NOT 'userDefine', it is set to a zero-length string
         automatically.
         Otherwise it must be set to a non-zero length string.

         The SET operation of this object must be with the SET
         operation of ibDhcpSnoop2IfOpt82CIDMode and
         ibDhcpSnoop2IfOpt82CIDNodeType."
    ::= { ibDhcpSnoop2IfConfigEntry 11 }

ibDhcpSnoop2IfOpt82CIDStr      OBJECT-TYPE
    SYNTAX      OCTET STRING(SIZE(0|3..63))
    MAX-ACCESS  read-write
    STATUS      current
    DESCRIPTION
        "The string defined by user to fill in the circuit ID
         suboption of option 82 in the user-define mode.

         If the value of ibDhcpSnoop2IfOpt82CIDMode is
         NOT 'userDefine', it is set to a zero-length string
         automatically.
         Otherwise it must be set to a non-zero length string.

         The SET operation of this object must be with the SET
         operation of ibDhcpSnoop2IfOpt82CIDMode."
    ::= { ibDhcpSnoop2IfConfigEntry 12 }

ibDhcpSnoop2IfOpt82CIDFormat    OBJECT-TYPE
    SYNTAX      INTEGER
    {
        hex(1),
        ascii(2),
        undefine(3)
    }
    MAX-ACCESS  read-write
    STATUS      current
    DESCRIPTION
        "The format of the circuit ID suboption of DHCP
         option 82.

         'hex' is the hex format.

         'ascii' is the ascii format.

         'undefine' is the undefine format.

         If the value of ibDhcpSnoop2IfOpt82CIDMode is
         'normal', this object is set with 'hex' automatically
         and cannot be set with 'undefine'.

         If the value of ibDhcpSnoop2IfOpt82CIDMode is
         'verbose', the default value of this object is 'undefine'.

         If the value of ibDhcpSnoop2IfOpt82CIDMode is
         'userDefine', this object is set with 'ascii' automatically
         and cannot be set with other value.

         The SET operation of this object must be with the SET
         operation of ibDhcpSnoop2IfOpt82CIDMode."
    ::= { ibDhcpSnoop2IfConfigEntry 13 }

ibDhcpSnoop2IfOpt82RIDMode OBJECT-TYPE
    SYNTAX      INTEGER
    {
        normal(1),
        sysname(2),
        userDefine(3)
    }
    MAX-ACCESS  read-write
    STATUS      current
    DESCRIPTION
        "The mode of filling in the remote ID suboption
         of DHCP option 82.

         'normal' is the standard mode.

         'userDefine' is the user-defined mode.

         'sysname' is the sysname mode.

         If the value of this object is set to 'userDefine',
         ibDhcpSnoop2IfOpt82RIDStr must also be set."
    DEFVAL      { normal }
    ::= { ibDhcpSnoop2IfConfigEntry 14 }

ibDhcpSnoop2IfOpt82RIDStr  OBJECT-TYPE
    SYNTAX      OCTET STRING (SIZE(0..63))
    MAX-ACCESS  read-write
    STATUS      current
    DESCRIPTION
        "The string defined by user to fill in the
         remote ID in the user-defined mode.

         If the value of ibDhcpSnoop2IfOpt82RIDMode is
         NOT 'userDefine', this object is set with a zero-length
         string automatically.
         Otherwise it must be set with a non-zero length string.

         The SET operation of this object must be with the SET
         operation of ibDhcpSnoop2IfOpt82RIDMode."
    ::= { ibDhcpSnoop2IfConfigEntry 15 }

ibDhcpSnoop2IfOpt82RIDFormat    OBJECT-TYPE
    SYNTAX      INTEGER
    {
        hex(1),
        ascii(2)
    }
    MAX-ACCESS  read-write
    STATUS      current
    DESCRIPTION
        "The format of DHCP option 82 remote ID in 'normal' mode.

         'hex' is the hex format.

         'ascii' is the ascii format.

         If the value of ibDhcpSnoop2IfOpt82RIDMode is
         'sysname' or 'userDefine', this object is set with 'ascii'
         automatically and cannot be set with other value.

         If the value of ibDhcpSnoop2IfOpt82RIDMode is
         'normal', the default value of this object is 'hex'.

         The SET operation of this object must be with the SET
         operation of ibDhcpSnoop2IfOpt82RIDMode."
    ::= { ibDhcpSnoop2IfConfigEntry 16 }

-- ==================================================================
-- 3rd Table of ibDhcpSnoop2Tables: ibDhcpSnoop2IfVlanCIDTable
-- ==================================================================
ibDhcpSnoop2IfVlanCIDTable   OBJECT-TYPE
    SYNTAX      SEQUENCE OF IbDhcpSnoop2IfVlanCIDEntry
    MAX-ACCESS  not-accessible
    STATUS      current
    DESCRIPTION
        "A table containing the information of the circuit ID
         suboption of DHCP option 82 in VLAN."
    ::= { ibDhcpSnoop2Tables 3 }

ibDhcpSnoop2IfVlanCIDEntry  OBJECT-TYPE
    SYNTAX      IbDhcpSnoop2IfVlanCIDEntry
    MAX-ACCESS  not-accessible
    STATUS      current
    DESCRIPTION
        "An entry containing the information of the circuit ID
         suboption of DHCP option 82 in VLAN."
    INDEX { ifIndex, ibDhcpSnoop2IfVlanCIDVlanIndex }
    ::= { ibDhcpSnoop2IfVlanCIDTable 1 }

IbDhcpSnoop2IfVlanCIDEntry   ::=
    SEQUENCE
    {
        ibDhcpSnoop2IfVlanCIDVlanIndex          Unsigned32,
        ibDhcpSnoop2IfVlanCIDStr                OCTET STRING,
        ibDhcpSnoop2IfVlanCIDRowStatus          RowStatus
    }

ibDhcpSnoop2IfVlanCIDVlanIndex OBJECT-TYPE
    SYNTAX      Unsigned32(1..4094)
    MAX-ACCESS  not-accessible
    STATUS      current
    DESCRIPTION
        "VLAN ID."
    ::= { ibDhcpSnoop2IfVlanCIDEntry 1 }

ibDhcpSnoop2IfVlanCIDStr      OBJECT-TYPE
    SYNTAX      OCTET STRING(SIZE(3..63))
    MAX-ACCESS  read-create
    STATUS      current
    DESCRIPTION
        "The string defined by user to fill in the
         circuit ID suboption of option 82."
    ::= { ibDhcpSnoop2IfVlanCIDEntry 2 }

ibDhcpSnoop2IfVlanCIDRowStatus    OBJECT-TYPE
     SYNTAX      RowStatus
     MAX-ACCESS  read-create
     STATUS      current
     DESCRIPTION
         "Operation status of this table entry.
          Three actions are used: active,
          createAndGo, destroy."
     ::= { ibDhcpSnoop2IfVlanCIDEntry 3 }

-- ==================================================================
-- 4th Table of ibDhcpSnoop2Tables: ibDhcpSnoop2IfVlanRIDTable
-- ==================================================================
ibDhcpSnoop2IfVlanRIDTable   OBJECT-TYPE
    SYNTAX      SEQUENCE OF IbDhcpSnoop2IfVlanRIDEntry
    MAX-ACCESS  not-accessible
    STATUS      current
    DESCRIPTION
        "A table containing the information of the remote ID
         suboption of DHCP option 82 in VLAN."
    ::= { ibDhcpSnoop2Tables 4 }

ibDhcpSnoop2IfVlanRIDEntry  OBJECT-TYPE
    SYNTAX      IbDhcpSnoop2IfVlanRIDEntry
    MAX-ACCESS  not-accessible
    STATUS      current
    DESCRIPTION
        "An entry containing the information of the remote ID
         suboption of DHCP option 82 in VLAN."
    INDEX { ifIndex, ibDhcpSnoop2IfVlanRIDVlanIndex }
    ::= { ibDhcpSnoop2IfVlanRIDTable 1 }

IbDhcpSnoop2IfVlanRIDEntry   ::=
    SEQUENCE
    {
        ibDhcpSnoop2IfVlanRIDVlanIndex              Unsigned32,
        ibDhcpSnoop2IfVlanRIDMode                   INTEGER,
        ibDhcpSnoop2IfVlanRIDStr                    OCTET STRING,
        ibDhcpSnoop2IfVlanRIDRowStatus              RowStatus
    }

ibDhcpSnoop2IfVlanRIDVlanIndex    OBJECT-TYPE
    SYNTAX      Unsigned32(1..4094)
    MAX-ACCESS  not-accessible
    STATUS      current
    DESCRIPTION
        "VLAN ID."
    ::= { ibDhcpSnoop2IfVlanRIDEntry 1 }

ibDhcpSnoop2IfVlanRIDMode    OBJECT-TYPE
    SYNTAX      INTEGER
    {
        sysname(1),
        userDefine(2)
    }
    MAX-ACCESS  read-create
    STATUS      current
    DESCRIPTION
        "The mode of filling in the remote ID suboption
         of DHCP option 82 in VLAN.

         'sysname' indicates using the device sysname to fill in
         the suboption.

         'userDefine' indicates using the string defined
         by ibDhcpSnoop2IfVlanRIDStr to fill in the suboption.

         If the value of this object is set to 'userDefine',
         ibDhcpSnoop2IfVlanRIDStr must also be set."
    ::= { ibDhcpSnoop2IfVlanRIDEntry 2 }

ibDhcpSnoop2IfVlanRIDStr      OBJECT-TYPE
    SYNTAX      OCTET STRING(SIZE(0..63))
    MAX-ACCESS  read-create
    STATUS      current
    DESCRIPTION
        "The string used to fill in the remote ID suboption.

         If the value of ibDhcpSnoop2IfVlanRIDMode is NOT 'userDefine',
         this object is set with a zero-length string automatically.
         Otherwise it must be set with a non-zero length string.

         The SET operation of this object must be with the SET
         operation of ibDhcpSnoop2IfVlanRIDMode."
    ::= { ibDhcpSnoop2IfVlanRIDEntry 3 }

ibDhcpSnoop2IfVlanRIDRowStatus    OBJECT-TYPE
     SYNTAX      RowStatus
     MAX-ACCESS  read-create
     STATUS      current
     DESCRIPTION
         "Operation status of this table entry.
          Three actions are used: active,
          createAndGo, destroy."
     ::= { ibDhcpSnoop2IfVlanRIDEntry 4 }
-- ==========================================================================
-- Trap definition
-- ==========================================================================
ibDhcpSnoop2Traps OBJECT IDENTIFIER ::= {  ibDhcpSnoop2 3  }

ibDhcpSnoop2TrapNotify OBJECT IDENTIFIER ::= { ibDhcpSnoop2Traps 0 }

ibDhcpSnoop2BindTblExh NOTIFICATION-TYPE
    OBJECTS
    {
        ifIndex
    }
    STATUS      current
    DESCRIPTION
        "This trap is generated when the DHCP snooping entry resource is exhausted"
    ::= { ibDhcpSnoop2TrapNotify 1 }

ibDhcpSnoop2BindTblExhRecov  NOTIFICATION-TYPE
    OBJECTS
    {
        ifIndex
    }
    STATUS      current
    DESCRIPTION
        "This trap is generated when the DHCP snooping entry resource recovers from exhaustion"
    ::= { ibDhcpSnoop2TrapNotify 2 }

ibDhcpSnoop2BindTblThresh  NOTIFICATION-TYPE
    OBJECTS
    {
        ifIndex
    }
    STATUS      current
    DESCRIPTION
        "This trap is generated when the usage of DHCP snooping entry
         resource has exceeded the threshold
         The value of the usage is sampled every minute."
    ::= { ibDhcpSnoop2TrapNotify 3 }

ibDhcpSnoop2BindTblThreshRecov  NOTIFICATION-TYPE
    OBJECTS
    {
        ifIndex
    }
    STATUS      current
    DESCRIPTION
        "This trap is generated when the usage of DHCP snooping entry resource has
         dropped below the threshold.
         The value of the usage is sampled every minute."
    ::= { ibDhcpSnoop2TrapNotify 4 }

ibDhcpSnoop2NomatchBindAlm  NOTIFICATION-TYPE
    OBJECTS
    {
        ifIndex
    }
    STATUS      current
    DESCRIPTION
        "This trap is generated when the number of DHCP requests discarded
         due to DHCP snooping entry mismatch
         has reached the threshold."
    ::= { ibDhcpSnoop2TrapNotify 5}

ibDhcpSnoop2ChaddrAlm  NOTIFICATION-TYPE
    OBJECTS
    {
        ifIndex
    }
    STATUS      current
    DESCRIPTION
        "This trap is generated when the number of DHCP requests discarded
         due to MAC address mismatch has reached the threshold."
    ::= { ibDhcpSnoop2TrapNotify 6 }

ibDhcpSnoop2UntrustRelpyAlm  NOTIFICATION-TYPE
    OBJECTS
    {
        ifName,
        ibDhcpSnoop2TrapDropNum,
        ibDhcpSnoop2PktVlanID
    }
    STATUS      current
    DESCRIPTION
        "This trap is generated when the number of DHCP requests discarded
         due to untrust port reply packets has reached the threshold."
    ::= { ibDhcpSnoop2TrapNotify 7}

ibDhcpSnoop2RateLimitAlm  NOTIFICATION-TYPE
    OBJECTS
    {
        ifName,
        ibDhcpSnoop2TrapDropNum,
        ibDhcpSnoop2PktVlanID
    }
    STATUS      current
    DESCRIPTION
        "This trap is generated when the number of DHCP requests discarded
         due to rate limit has reached the threshold."
    ::= { ibDhcpSnoop2TrapNotify 8}

END
