-- ============================================================================
-- Copyright (C) 2023 Intelbras S.A. All rights reserved.
--
-- Description: DVPN MIB
-- Reference:
-- Version: V1.0
-- History:
-- V1.0 2005-07-01
--   Initial version, created by zhanglihua, zhangzhen, lilin and liukan
-- ============================================================================
IB-DVPN-MIB DEFINITIONS ::= BEGIN

    IMPORTS
        ibCommon
            FROM IB-OID-MIB
        InetAddressType, InetAddress
            FROM INET-ADDRESS-MIB
        Integer32, Unsigned32, OBJECT-TYPE, MODULE-IDENTITY, NOTIFICATION-TYPE,
        TimeTicks
            FROM SNMPv2-SMI
        RowStatus, TEXTUAL-CONVENTION
            FROM SNMPv2-TC
        MODULE-COMPLIANCE, OBJECT-GROUP
            FROM SNMPv2-CONF
        ifIndex
            FROM IF-MIB;



--Node definitions


    ibDvpn MODULE-IDENTITY
        LAST-UPDATED "200507011936Z"        -- July 1, 2005 at 19:36 GMT
        ORGANIZATION
            "Intelbras S.A. Industria de Telecomunicacao Eletronica Brasileria."
        CONTACT-INFO
            ""
        DESCRIPTION
            "
                This MIB is Dynamic Virtual Private Network(Dvpn) mib.
                This MIB is applicable to router.
                Some objects in this may be used only for some specific products,
                so users should refer to the related documents to acquire more
                detail information.
            "
        ::= { ibCommon 57 }


    DvpnAlgorithmSuite ::= TEXTUAL-CONVENTION
        STATUS current
        DESCRIPTION
            "
                13 kinds of dvpn algorithms.
                                         encryption method | hash method | key width.
                dvpnDesCbcMd5PreShaModp768:          des   |  md5        |     768
                dvpnDesCbcMd5PreShaModp1024:         des   |  md5        |    1024
                dvpnDesCbcSha1PreShaModp768:         des   | sha1        |     768
                dvpnDesCbcSha1PreShaModp1024:        des   | sha1        |    1024
                dvpn3DesCbcMd5PreShaModp768:        3des   |  md5        |     768
                dvpn3DesCbcMd5PreShaModp1024:       3des   |  md5        |    1024
                dvpn3DesCbcSha1PreShaModp768:       3des   | sha1        |     768
                dvpn3DesCbcSha1PreShaModp1024:      3des   | sha1        |    1024
                dvpnAesCbcMd5PreShaModp768:          Aes   |  md5        |     768
                dvpnAesCbcMd5PreShaModp1024:         Aes   |  md5        |    1024
                dvpnAesCbcSHA1Sha1PreShaModp768:     Aes   | sha1        |     768
                dvpnAesCbcSHA1Sha1PreShaModp1024:    Aes   | sha1        |    1024
                dvpnAlgorithmNone:                  none   | none        |  no key
            "
        SYNTAX INTEGER
            {
                dvpnDesCbcMd5PreShaModp768(1),
                dvpnDesCbcMd5PreShaModp1024(2),
                dvpnDesCbcSha1PreShaModp768(3),
                dvpnDesCbcSha1PreShaModp1024(4),
                dvpn3DesCbcMd5PreShaModp768(5),
                dvpn3DesCbcMd5PreShaModp1024(6),
                dvpn3DesCbcSha1PreShaModp768(7),
                dvpn3DesCbcSha1PreShaModp1024(8),
                dvpnAesCbcMd5PreShaModp768(9),
                dvpnAesCbcMd5PreShaModp1024(10),
                dvpnAesCbcSHA1Sha1PreShaModp768(11),
                dvpnAesCbcSHA1Sha1PreShaModp1024(12),
                dvpnAlgorithmNone(13)
            }

    DvpnCommunicateType ::= TEXTUAL-CONVENTION
        STATUS current
        DESCRIPTION
            "
                The type of the communication between client and server.
                It indicates the direction of the communication.
            "
        SYNTAX INTEGER
            {
                clientToserver(1),
                serverToclient(2),
                serverToserver(3),
                clientToclient(4)
            }

    ibDvpnMibObjects OBJECT IDENTIFIER ::= { ibDvpn 1 }

    ibDvpnMibGlobal OBJECT IDENTIFIER  ::= { ibDvpnMibObjects 1 }

    ibDvpnMibTableTroop OBJECT IDENTIFIER  ::= { ibDvpnMibObjects 2 }

    ibDvpnMibNotification OBJECT IDENTIFIER  ::= { ibDvpnMibObjects 3 }

    ibDvpnMibConformance OBJECT IDENTIFIER ::= { ibDvpnMibObjects 4 }



    ibDvpnServiceEnable OBJECT-TYPE
        SYNTAX INTEGER
            {
                enable(1),
                disable(2)
            }
        MAX-ACCESS read-write
        STATUS current
        DESCRIPTION
            "
                Dvpn service enable or disable.
                If dvpn service is 'disable', dvpn service can not be used.
            "
        DEFVAL { disable }
        ::= { ibDvpnMibGlobal 1 }

    ibDvpnClassNumber OBJECT-TYPE
        SYNTAX Integer32
        MAX-ACCESS read-only
        STATUS current
        DESCRIPTION
            "
                The number of dvpn classes.
                It is only used on client.
            "
        DEFVAL { 0 }
        ::= { ibDvpnMibGlobal 2 }


    ibDvpnClientNumber OBJECT-TYPE
        SYNTAX Integer32
        MAX-ACCESS read-only
        STATUS current
        DESCRIPTION
            "
                The number of clients which register on the server.
                When a session of server to client type is built,
                add 1 to the value of this node.
                It is only used on server.
            "
        DEFVAL { 0 }
        ::= { ibDvpnMibGlobal 3 }

    ibDvpnMapAgeTime OBJECT-TYPE
        SYNTAX Integer32 (10..180)
        MAX-ACCESS read-write
        STATUS current
        DESCRIPTION
            "
                Dvpn map age time, the unit is second.
                It is only used on server.
            "
        DEFVAL { 30 }
        ::= { ibDvpnMibGlobal 4 }


    ibDvpnClientRegisterInterval OBJECT-TYPE
        SYNTAX Integer32 (3..60)
        MAX-ACCESS read-write
        STATUS current
        DESCRIPTION
            "
                The length of time between the registering of client, the unit
                is second.
                It is only used on client.
            "
        DEFVAL { 10 }
        ::= { ibDvpnMibGlobal 5 }


    ibDvpnClientRegisterDumb OBJECT-TYPE
        SYNTAX Integer32 (60..3600)
        MAX-ACCESS read-write
        STATUS current
        DESCRIPTION
            "
                The length of time when client dumbs, the unit is second.
                It is only used on client.
            "
        DEFVAL { 300 }
        ::= { ibDvpnMibGlobal 6 }


    ibDvpnClientRegisterRetry OBJECT-TYPE
       SYNTAX Integer32(1..6)
       MAX-ACCESS read-write
       STATUS current
       DESCRIPTION
           "
               Regist retry times of client after register fail.
               It is only used on client.
            "
       DEFVAL { 3 }
       ::= { ibDvpnMibGlobal 7 }

    ibDvpnInputPkt OBJECT-TYPE
        SYNTAX Unsigned32
        MAX-ACCESS read-only
        STATUS current
        DESCRIPTION
            "
                The number of recieved packets.
            "
        DEFVAL { 0 }
        ::= { ibDvpnMibGlobal 8 }

    ibDvpnDropPkt OBJECT-TYPE
        SYNTAX Unsigned32
        MAX-ACCESS read-only
        STATUS current
        DESCRIPTION
            "
                The number of packets have been droped.
            "
        DEFVAL { 0 }
        ::= { ibDvpnMibGlobal 9 }

    ibDvpnOutputPkt OBJECT-TYPE
        SYNTAX Unsigned32
        MAX-ACCESS read-only
        STATUS current
        DESCRIPTION
            "
                The number of packets have been sent.
            "
        DEFVAL { 0 }
        ::= { ibDvpnMibGlobal 10 }

    ibDvpnOutputErrorPkt OBJECT-TYPE
        SYNTAX Unsigned32
        MAX-ACCESS read-only
        STATUS current
        DESCRIPTION
            "
                The number of output error packets.
            "
        DEFVAL { 0 }
        ::= { ibDvpnMibGlobal 11 }

    ibDvpnEncryptErrorPkt  OBJECT-TYPE
        SYNTAX Unsigned32
        MAX-ACCESS read-only
        STATUS current
        DESCRIPTION
            "
                The number of packets have been encrypted wrongly.
            "
        DEFVAL { 0 }
        ::= { ibDvpnMibGlobal 12 }

    ibDvpnCurrentDeviceRole  OBJECT-TYPE
        SYNTAX INTEGER
            {
                none(1),
                server(2),
                client(3),
                both(4)
            }
        MAX-ACCESS read-only
        STATUS current
        DESCRIPTION
            "
                The current role of the device.
                The value is decided by the configuration of the tunnel-interface.
            "
        ::= { ibDvpnMibGlobal 13 }

    ibDvpnDomainNumber  OBJECT-TYPE
        SYNTAX Integer32
        MAX-ACCESS read-only
        STATUS current
        DESCRIPTION
            "
                The number of dvpn domains.

            "
        DEFVAL { 0 }
        ::= { ibDvpnMibGlobal 14 }

    ibDvpnMapNumber  OBJECT-TYPE
        SYNTAX Integer32
        MAX-ACCESS read-only
        STATUS current
        DESCRIPTION
            "
                The number of dvpn maps.
            "
        DEFVAL { 0 }
        ::= { ibDvpnMibGlobal 15 }

    ibDvpnSessionNumber OBJECT-TYPE
        SYNTAX Integer32
        MAX-ACCESS read-only
        STATUS current
        DESCRIPTION
             "
                 The number of dvpn sessiones including the session of all states.
             "
        DEFVAL { 0 }
        ::= {  ibDvpnMibGlobal 16 }

    ibDvpnServerPreSharedKey  OBJECT-TYPE
        SYNTAX OCTET STRING (SIZE (0..127))
        MAX-ACCESS read-write
        STATUS current
        DESCRIPTION
            "
                The pre-shared-key of server.
                It is only used on server.
            "
        ::= { ibDvpnMibGlobal 17 }

    ibDvpnMapTrapEnable OBJECT-TYPE
        SYNTAX INTEGER
            {
                enable(1),
                disable(2)
            }
        MAX-ACCESS read-write
        STATUS current
        DESCRIPTION
            "
                Dvpn map trap enable or disable.
            "
        DEFVAL { enable }
        ::= { ibDvpnMibGlobal 18 }

    ibDvpnSessionTrapEnable OBJECT-TYPE
        SYNTAX INTEGER
            {
                enable(1),
                disable(2)
            }
        MAX-ACCESS read-write
        STATUS current
        DESCRIPTION
            "
                Dvpn session trap enable or disable.
            "
        DEFVAL { enable }
        ::= { ibDvpnMibGlobal 19 }

    ibDvpnVersion  OBJECT-TYPE
        SYNTAX INTEGER
            {
                version2(1),
                version3(2)
            }
        MAX-ACCESS read-only
        STATUS current
        DESCRIPTION
            "
                Dvpn version.
            "
        ::= { ibDvpnMibGlobal 20 }

    ibDvpnClearDomainAllConection  OBJECT-TYPE
        SYNTAX Integer32(1..65535)
        MAX-ACCESS read-write
        STATUS current
        DESCRIPTION
            "
                Clear all dvpn conects in the domain, the parameter is
                the id of the domain.
            "
        ::= { ibDvpnMibGlobal 21 }

    ibDvpnClearDvpnStaInfo OBJECT-TYPE
        SYNTAX Integer32(1)
        MAX-ACCESS read-write
        STATUS current
        DESCRIPTION
            "
                Clear the statistic information of dvpn.
            "
        ::= {  ibDvpnMibGlobal 22 }

    ibDvpnTotalRedirectNumber OBJECT-TYPE
        SYNTAX Unsigned32
        MAX-ACCESS read-only
        STATUS current
        DESCRIPTION
            "
                The number of redirect packets.
                It is only used on server.
            "
        DEFVAL { 0 }
        ::= { ibDvpnMibGlobal 23 }


    ibDvpnGlobalAuthenClientType OBJECT-TYPE
        SYNTAX INTEGER
            {
                 none(1),
                 pap(2),
                 chap(3)
            }
        MAX-ACCESS read-write
        STATUS current
        DESCRIPTION
            "
                Dvpn global authentication type being used by server to client.
                The value is decided by the configuration by the user.
            "
        DEFVAL { none }
        ::= { ibDvpnMibGlobal 24 }



    ibDvpnGlobalUserDefAAADomain OBJECT-TYPE
        SYNTAX OCTET STRING (SIZE (0..24))
        MAX-ACCESS read-write
        STATUS current
        DESCRIPTION
            "
                Dvpn global AAA domain of the user. The domain will decide the
                authentication server which is used by the dvpn server to
                authenticate dvpn client.
            "
        ::= { ibDvpnMibGlobal 25 }

    ibDvpnLocalDeviceId OBJECT-TYPE
        SYNTAX OCTET STRING
        MAX-ACCESS read-only
        STATUS current
        DESCRIPTION
            "
                The device ID, it is a string.
            "
        ::= {  ibDvpnMibGlobal 26 }

    ibDvpnSessionHisAgeTime OBJECT-TYPE
        SYNTAX Integer32(1..100)
        MAX-ACCESS read-write
        STATUS current
        DESCRIPTION
            "
                The age-time of the ibDvpnSessionHisTable table.
                The unit is hour.
            "
        DEFVAL { 50 }
        ::= {  ibDvpnMibGlobal 27 }

    ibDvpnSessionHisReset OBJECT-TYPE
        SYNTAX INTEGER
            {
                 reset(1)
            }
        MAX-ACCESS read-write
        STATUS current
        DESCRIPTION
            "
                The reset flag of dvpn ibDvpnSessionHisTable table.
            "
        ::= {  ibDvpnMibGlobal 28 }


--ibDvpnPolicyTable

    ibDvpnPolicyTable  OBJECT-TYPE
        SYNTAX SEQUENCE OF IbDvpnPolicyEntry
        MAX-ACCESS not-accessible
        STATUS current
        DESCRIPTION
            "
                The dvpn policy table.
                It is used on dvpn server.
            "
        ::= { ibDvpnMibTableTroop 1 }

    ibDvpnPolicyEntry OBJECT-TYPE
        SYNTAX IbDvpnPolicyEntry
        MAX-ACCESS not-accessible
        STATUS current
        DESCRIPTION
            "
                The entry of ibDvpnPolicyTable.
            "
        INDEX { ibDvpnPolicyName }
        ::= { ibDvpnPolicyTable 1 }

    IbDvpnPolicyEntry ::=
        SEQUENCE {
            ibDvpnPolicyName                            OCTET STRING,
            ibDvpnPoAuthenClientType                    INTEGER,
            ibDvpnPoSessionAlgorithmSuite               DvpnAlgorithmSuite,
            ibDvpnPoSessionIdleTime                     Integer32,
            ibDvpnPoSessionKeepTime                     Integer32,
            ibDvpnPoSessionSetupInterval                Integer32,
            ibDvpnPoDataAlgorithmSuite                  DvpnAlgorithmSuite,
            ibDvpnPoSaSeconds                           Integer32,
            ibDvpnPoUserDefAAADomain                    OCTET STRING,
            ibDvpnPoRefTimes                            Integer32,
            ibDvpnPoRowStatus                           RowStatus
        }

    ibDvpnPolicyName OBJECT-TYPE
        SYNTAX OCTET STRING (SIZE(1..31))
        MAX-ACCESS not-accessible
        STATUS current
        DESCRIPTION
            "
                The name of Dvpn policy.
            "
        ::= { ibDvpnPolicyEntry 1 }

    ibDvpnPoAuthenClientType OBJECT-TYPE
        SYNTAX INTEGER
            {
                none(1),
                pap(2),
                chap(3)
            }
        MAX-ACCESS read-create
        STATUS current
        DESCRIPTION
            "
                The authentication type used by server to client.
                The value is decided by the policy configuration of the user.
                The default value is none.
            "
        DEFVAL { none }
        ::= { ibDvpnPolicyEntry 2 }

    ibDvpnPoSessionAlgorithmSuite OBJECT-TYPE
        SYNTAX DvpnAlgorithmSuite
        MAX-ACCESS read-create
        STATUS current
        DESCRIPTION
            "
                The algorithm suite used when session is created.
            "
        DEFVAL { dvpnDesCbcMd5PreShaModp768 }
        ::= { ibDvpnPolicyEntry 3 }

    ibDvpnPoSessionIdleTime OBJECT-TYPE
        SYNTAX Integer32(60..86400)
        MAX-ACCESS read-create
        STATUS current
        DESCRIPTION
            "
                The session idle time, the unit is second.
            "
        DEFVAL { 300 }
        ::= { ibDvpnPolicyEntry 4 }

    ibDvpnPoSessionKeepTime OBJECT-TYPE
        SYNTAX Integer32(5..300)
        MAX-ACCESS read-create
        STATUS current
        DESCRIPTION
            "
                The session keepalive time, the unit is second.
            "
        DEFVAL { 10 }
        ::= { ibDvpnPolicyEntry 5 }

    ibDvpnPoSessionSetupInterval OBJECT-TYPE
        SYNTAX Integer32(5..60)
        MAX-ACCESS read-create
        STATUS current
        DESCRIPTION
            "
                The session setup interval time, the unit is second.
            "
        DEFVAL { 10 }
        ::= { ibDvpnPolicyEntry 6 }

    ibDvpnPoDataAlgorithmSuite OBJECT-TYPE
        SYNTAX DvpnAlgorithmSuite
        MAX-ACCESS read-create
        STATUS current
        DESCRIPTION
            "
                The algorithm suite used by the session for createing ipsec sa.
            "
        DEFVAL { dvpnDesCbcMd5PreShaModp768 }
        ::= { ibDvpnPolicyEntry 7 }

    ibDvpnPoSaSeconds OBJECT-TYPE
        SYNTAX Integer32(180..604800)
        MAX-ACCESS read-create
        STATUS current
        DESCRIPTION
            "
                The duration of DVPN IPSec security association.
                The unit is second.
            "
        DEFVAL { 3600 }
        ::= { ibDvpnPolicyEntry 8 }

    ibDvpnPoUserDefAAADomain OBJECT-TYPE
        SYNTAX OCTET STRING (SIZE (0..24))
        MAX-ACCESS read-create
        STATUS current
        DESCRIPTION
            "
                Dvpn policy AAA domain of the user. The domain will decide the
                authentication server which used by the dvpn server to authenticate
                dvpn client.
            "
        ::= { ibDvpnPolicyEntry 9 }

    ibDvpnPoRefTimes OBJECT-TYPE
        SYNTAX Integer32
        MAX-ACCESS read-only
        STATUS current
        DESCRIPTION
            "
                The total times of the policy being used by dvpn.
            "
        ::= { ibDvpnPolicyEntry 10 }

    ibDvpnPoRowStatus OBJECT-TYPE
        SYNTAX RowStatus
        MAX-ACCESS read-create
        STATUS current
        DESCRIPTION
            "
                The status of this conceptual row.
                We support the characteristic of active(1),createAndGo(4),destroy(6).
            "
        ::= { ibDvpnPolicyEntry 11 }



--ibDvpnDomainInfoTable

    ibDvpnDomainInfoTable OBJECT-TYPE
        SYNTAX SEQUENCE OF IbDvpnDomainInfoEntry
        MAX-ACCESS not-accessible
        STATUS current
        DESCRIPTION
            "
                The dvpn domain table.
            "
        ::= { ibDvpnMibTableTroop 2 }

    ibDvpnDomainInfoEntry OBJECT-TYPE
        SYNTAX IbDvpnDomainInfoEntry
        MAX-ACCESS not-accessible
        STATUS current
        DESCRIPTION
            "
                The entry of ibDvpnDomainInfoTable.
            "
        INDEX { ibDvpnDomainID }
        ::= { ibDvpnDomainInfoTable 1 }

    IbDvpnDomainInfoEntry ::=
        SEQUENCE
        {
            ibDvpnDomainID                       Integer32,
            ibDvpnDomainSessionNum               Unsigned32,
            ibDvpnDomainRedirectNum              Unsigned32,
            ibDvpnDomainInputPkt                 Unsigned32,
            ibDvpnDomainDropPkt                  Unsigned32,
            ibDvpnDomainOutputPkt                Unsigned32,
            ibDvpnDomainOutputErrorPkt           Unsigned32,
            ibDvpnDomainEncryptErrorPkt          Unsigned32
        }

    ibDvpnDomainID OBJECT-TYPE
        SYNTAX Integer32(1..65535)
        MAX-ACCESS not-accessible
        STATUS current
        DESCRIPTION
            "
                Dvpn domain ID.
            "
        ::= { ibDvpnDomainInfoEntry 1 }

    ibDvpnDomainSessionNum OBJECT-TYPE
        SYNTAX Unsigned32
        MAX-ACCESS read-only
        STATUS current
        DESCRIPTION
            "
                The number of session in this dvpn domain.
            "
        ::= { ibDvpnDomainInfoEntry 2 }

    ibDvpnDomainRedirectNum OBJECT-TYPE
        SYNTAX Unsigned32
        MAX-ACCESS read-only
        STATUS current
        DESCRIPTION
            "
               The number of redirect packets in this dvpn domain.
            "
        ::= { ibDvpnDomainInfoEntry 3 }

    ibDvpnDomainInputPkt OBJECT-TYPE
        SYNTAX Unsigned32
        MAX-ACCESS read-only
        STATUS current
        DESCRIPTION
            "
               The number of input packets in this dvpn domain.
            "
        ::= { ibDvpnDomainInfoEntry 4 }

    ibDvpnDomainDropPkt OBJECT-TYPE
        SYNTAX Unsigned32
        MAX-ACCESS read-only
        STATUS current
        DESCRIPTION
            "
                The number of drop packets in this dvpn domain.
            "
        ::= { ibDvpnDomainInfoEntry 5 }

    ibDvpnDomainOutputPkt OBJECT-TYPE
        SYNTAX Unsigned32
        MAX-ACCESS read-only
        STATUS current
        DESCRIPTION
            "
                The number of output packets in this dvpn domain.
            "
        ::= { ibDvpnDomainInfoEntry 6 }

    ibDvpnDomainOutputErrorPkt OBJECT-TYPE
        SYNTAX Unsigned32
        MAX-ACCESS read-only
        STATUS current
        DESCRIPTION
            "
                The number of output error packets in this dvpn domain.
            "
        ::= { ibDvpnDomainInfoEntry 7 }

    ibDvpnDomainEncryptErrorPkt OBJECT-TYPE
        SYNTAX Unsigned32
        MAX-ACCESS read-only
        STATUS current
        DESCRIPTION
            "
                The number of encrypt error packets in this dvpn domain.
            "
        ::= { ibDvpnDomainInfoEntry 8 }





--ibDvpnClassTable

    ibDvpnClassTable OBJECT-TYPE
        SYNTAX SEQUENCE OF IbDvpnClassEntry
        MAX-ACCESS not-accessible
        STATUS current
        DESCRIPTION
            "
                The Dvpn class table.
                It is only used on dvpn client.
            "
        ::= { ibDvpnMibTableTroop 3 }

    ibDvpnClassEntry OBJECT-TYPE
        SYNTAX IbDvpnClassEntry
        MAX-ACCESS not-accessible
        STATUS current
        DESCRIPTION
            "
                The entry of the ibDvpnClassTable.
            "
        INDEX { ibDvpnClassName }
        ::= { ibDvpnClassTable 1 }

    IbDvpnClassEntry ::=
        SEQUENCE {
            ibDvpnClassName                 OCTET STRING,
            ibDvpnClServerPublicIpType      InetAddressType,
            ibDvpnClServerPublicIp          InetAddress,
            ibDvpnClServerPriIpType         InetAddressType,
            ibDvpnClServerPriIp             InetAddress,
            ibDvpnClAlgorithmSuite          DvpnAlgorithmSuite,
            ibDvpnClAuthenServerType        INTEGER,
            ibDvpnClPreShareKey             OCTET STRING,
            ibDvpnClUserName                OCTET STRING,
            ibDvpnClPwdEncrypted            INTEGER,
            ibDvpnClPasswd                  OCTET STRING,
            ibDvpnClassRowStatus            RowStatus
        }

    ibDvpnClassName OBJECT-TYPE
        SYNTAX OCTET STRING (SIZE(1..31))
        MAX-ACCESS not-accessible
        STATUS current
        DESCRIPTION
            "
                The dvpn class name. It is the index of ibDvpnClassTable.
            "
        ::= { ibDvpnClassEntry  1 }

    ibDvpnClServerPublicIpType OBJECT-TYPE
        SYNTAX InetAddressType
        MAX-ACCESS read-create
        STATUS current
        DESCRIPTION
            "
                Dvpn server public ip type (ipv4, ipv6).
            "
        ::= { ibDvpnClassEntry  2 }

    ibDvpnClServerPublicIp OBJECT-TYPE
        SYNTAX InetAddress
        MAX-ACCESS read-create
        STATUS current
        DESCRIPTION
            "
                Dvpn server public ip address.
            "
        ::= { ibDvpnClassEntry  3 }

    ibDvpnClServerPriIpType OBJECT-TYPE
        SYNTAX InetAddressType
        MAX-ACCESS read-create
        STATUS current
        DESCRIPTION
            "
                Dvpn server private ip type (ipv4, ipv6).
            "
        ::= { ibDvpnClassEntry  4 }

    ibDvpnClServerPriIp OBJECT-TYPE
        SYNTAX InetAddress
        MAX-ACCESS read-create
        STATUS current
        DESCRIPTION
            "
                Dvpn server private ip address.
            "
        ::= { ibDvpnClassEntry  5 }

    ibDvpnClAlgorithmSuite OBJECT-TYPE
        SYNTAX DvpnAlgorithmSuite
        MAX-ACCESS read-create
        STATUS current
        DESCRIPTION
            "
                The algorithm suite used by the client when sending registry
                packets to the server.
                'dvpnAlgorithmNone' is not supported here.
            "
        DEFVAL { dvpnDesCbcMd5PreShaModp768 }
        ::= { ibDvpnClassEntry  6 }

    ibDvpnClAuthenServerType OBJECT-TYPE
        SYNTAX INTEGER
            {
                none(1),
                preShareKey(2)
            }
        MAX-ACCESS read-create
        STATUS current
        DESCRIPTION
            "
                The authentication type being used by client to server.
                The value is decided by the class configuration of the user.
                The default value is none.
            "
        DEFVAL { none }
        ::= { ibDvpnClassEntry  7 }

    ibDvpnClPreShareKey OBJECT-TYPE
        SYNTAX OCTET STRING(SIZE(0..127))
        MAX-ACCESS read-create
        STATUS current
        DESCRIPTION
            "
                Dvpn PreShareKey.
                It is used when the method used by client when authenticating
                server is pre-share-key, only when the value of the key is the
                same as that on the server, the client can authenticate server
                successfully.
            "
        ::= { ibDvpnClassEntry  8 }

    ibDvpnClUserName OBJECT-TYPE
        SYNTAX OCTET STRING(SIZE(0..80))
        MAX-ACCESS read-create
        STATUS current
        DESCRIPTION
            "
                Dvpn UserName. It is configured by the user.
            "
        ::= { ibDvpnClassEntry  9 }

    ibDvpnClPwdEncrypted OBJECT-TYPE
        SYNTAX INTEGER
            {
                simple(1),
                cipher(2)
            }
        MAX-ACCESS read-create
        STATUS current
        DESCRIPTION
            "
                Dvpn password encrypted or not.
            "
        ::= { ibDvpnClassEntry  10 }

    ibDvpnClPasswd OBJECT-TYPE
        SYNTAX OCTET STRING
        MAX-ACCESS read-create
        STATUS current
        DESCRIPTION
            "
                Dvpn password. It is configured by the user.
            "
        ::= { ibDvpnClassEntry  11 }

    ibDvpnClassRowStatus OBJECT-TYPE
        SYNTAX RowStatus
        MAX-ACCESS read-create
        STATUS current
        DESCRIPTION
            "
                The status of this conceptual row.
                Only 'active', 'createAndGo' and 'destroy' are supported.
            "
        ::= { ibDvpnClassEntry  12 }


--ibDvpnTunnelTable

    ibDvpnTunnelTable OBJECT-TYPE
        SYNTAX     SEQUENCE OF IbDvpnTunnelEntry
        MAX-ACCESS not-accessible
        STATUS     current
        DESCRIPTION
            "
                The dvpn tunnel table.
            "
        ::= { ibDvpnMibTableTroop 4 }

    ibDvpnTunnelEntry OBJECT-TYPE
        SYNTAX     IbDvpnTunnelEntry
        MAX-ACCESS not-accessible
        STATUS     current
        DESCRIPTION
            "
                The Entry of ibDvpnTunnelTable.
            "
        INDEX { ifIndex }
        ::= { ibDvpnTunnelTable 1 }

    IbDvpnTunnelEntry ::= SEQUENCE {
        ibDvpnTunnelInterfaceType      INTEGER,
        ibDvpnTunnelAcl                Integer32,
        ibDvpnTunnelClientRegType      INTEGER,
        ibDvpnTunnelDvpnId             Integer32,
        ibDvpnTunnelPolicy             OCTET STRING,
        ibDvpnTunnelClass              OCTET STRING
    }


    ibDvpnTunnelInterfaceType OBJECT-TYPE
        SYNTAX     INTEGER
            {
                client(1),
                server(2)
            }
        MAX-ACCESS read-write
        STATUS     current
        DESCRIPTION
            "
                The type of dvpn tunnel (client or server).
            "
        DEFVAL { client }
        ::= { ibDvpnTunnelEntry 1 }

    ibDvpnTunnelAcl OBJECT-TYPE
        SYNTAX     Integer32
        MAX-ACCESS read-write
        STATUS     current
        DESCRIPTION
            "
                The security acl used by the tunnel.
                If a packet permits the rules, it will not be encrypted.
            "
        ::= { ibDvpnTunnelEntry 2 }

    ibDvpnTunnelClientRegType OBJECT-TYPE
        SYNTAX     INTEGER
            {
                undistributed(1),
                forward(2),
                undistributedandforward(3),
                normal(4)
            }
        MAX-ACCESS read-write
        STATUS     current
        DESCRIPTION
            "
                The register type used by the client .
                Only the interface type is client, it can be used.
                undistributed: If a client send a packet to the client with
                this configuration, setver will only forward the packet whitout
                sending redirect packets.

                forward: The client with this configuration will only send packets
                forwarded by server, which means it can not initiate to build
                a session with other clients.
                undistributedandforward: The client with this configuration have
                the characteristics of both 'forward' and 'undistributed'.
                normal: The client with this configuration can build session with
                other clients without any restriction.
            "
        DEFVAL { normal }
        ::= { ibDvpnTunnelEntry 3 }

    ibDvpnTunnelDvpnId OBJECT-TYPE
        SYNTAX     Integer32(0..65535)
        MAX-ACCESS read-write
        STATUS     current
        DESCRIPTION
            "
                The dvpn ID used by the tunnel.
                The dvpn ID is 0 means that user does not configure dvpn ID.
                User can not configure a dvpn ID with 0.
            "
        DEFVAL { 0 }
        ::= { ibDvpnTunnelEntry 4 }

    ibDvpnTunnelPolicy OBJECT-TYPE
        SYNTAX     OCTET STRING(SIZE(0..31))
        MAX-ACCESS read-write
        STATUS     current
        DESCRIPTION
            "
                The dvpn policy used by the tunnel.
                Only the interface type is server, it can be used.
            "
        ::= { ibDvpnTunnelEntry 5 }

    ibDvpnTunnelClass OBJECT-TYPE
        SYNTAX     OCTET STRING(SIZE(0..31))
        MAX-ACCESS read-write
        STATUS     current
        DESCRIPTION
            "
                The dvpn class used by the tunnel.
                Only the interface type is client, it can be used.
            "
        ::= { ibDvpnTunnelEntry 6 }


--ibDvpnMapTable

    ibDvpnMapTable OBJECT-TYPE
        SYNTAX SEQUENCE OF IbDvpnMapEntry
        MAX-ACCESS not-accessible
        STATUS current
        DESCRIPTION
            "
                The dvpn map table.
            "
        ::= { ibDvpnMibTableTroop 5 }

    ibDvpnMapEntry OBJECT-TYPE
        SYNTAX IbDvpnMapEntry
        MAX-ACCESS not-accessible
        STATUS current
        DESCRIPTION
            "
                The entry of the ibDvpnMapTable.
            "
        INDEX { ibDvpnMapIndex }
        ::= { ibDvpnMapTable 1 }

    IbDvpnMapEntry ::=
        SEQUENCE {
            ibDvpnMapIndex                       Unsigned32,
            ibDvpnMapPeerDeviceId                OCTET STRING,
            ibDvpnMapDvpnId                      Unsigned32,
            ibDvpnMapBuildTime                   TimeTicks,
            ibDvpnMapPeerPriIpType               InetAddressType,
            ibDvpnMapPeerPriIp                   InetAddress,
            ibDvpnMapPeerPublicIpType            InetAddressType,
            ibDvpnMapPeerPublicIp                InetAddress,
            ibDvpnMapLocalPriIpType              InetAddressType,
            ibDvpnMapLocalPriIp                  InetAddress,
            ibDvpnMapLocalPublicIpType           InetAddressType,
            ibDvpnMapLocalPublicIp               InetAddress,
            ibDvpnMapUserName                    OCTET STRING,
            ibDvpnMapUdpPort                     Integer32,
            ibDvpnMapControlId                   Unsigned32,
            ibDvpnMapType                        DvpnCommunicateType,
            ibDvpnMapState                       INTEGER
        }

    ibDvpnMapIndex OBJECT-TYPE
        SYNTAX Unsigned32
        MAX-ACCESS accessible-for-notify
        STATUS current
        DESCRIPTION
            "
                The index of ibDvpnMapTable.
            "
        ::= { ibDvpnMapEntry 1 }

    ibDvpnMapPeerDeviceId OBJECT-TYPE
        SYNTAX OCTET STRING
        MAX-ACCESS read-only
        STATUS current
        DESCRIPTION
            "
                The identifier of peer device.
                It is a string.
            "
        ::= { ibDvpnMapEntry 2 }

    ibDvpnMapDvpnId OBJECT-TYPE
        SYNTAX Unsigned32
        MAX-ACCESS read-only
        STATUS current
        DESCRIPTION
            "
                The ID of the dvpn domain which the map belongs to.
                The dvpn ID is 0 means that the map has not been built.
                It has not gotten the dvpn ID at that time.
            "
        ::= { ibDvpnMapEntry 3 }

    ibDvpnMapBuildTime OBJECT-TYPE
        SYNTAX TimeTicks
        MAX-ACCESS read-only
        STATUS current
        DESCRIPTION
            "
                The time of the map created, the unit is second.
            "
        ::= { ibDvpnMapEntry 4 }

    ibDvpnMapPeerPriIpType OBJECT-TYPE
        SYNTAX InetAddressType
        MAX-ACCESS read-only
        STATUS current
        DESCRIPTION
            "
                The private ip type (ipv4, ipv6) of map peer device.
            "
        ::= { ibDvpnMapEntry 5 }

    ibDvpnMapPeerPriIp OBJECT-TYPE
        SYNTAX InetAddress
        MAX-ACCESS read-only
        STATUS current
        DESCRIPTION
            "
                The private ip of map peer device.
            "
        ::= { ibDvpnMapEntry 6 }

    ibDvpnMapPeerPublicIpType OBJECT-TYPE
        SYNTAX InetAddressType
        MAX-ACCESS read-only
        STATUS current
        DESCRIPTION
            "
                The public ip type (ipv4, ipv6) of map peer device.
            "
        ::= { ibDvpnMapEntry 7 }

    ibDvpnMapPeerPublicIp OBJECT-TYPE
        SYNTAX InetAddress
        MAX-ACCESS read-only
        STATUS current
        DESCRIPTION
            "
                The public ip of map peer device.
            "
        ::= { ibDvpnMapEntry 8 }

    ibDvpnMapLocalPriIpType OBJECT-TYPE
        SYNTAX InetAddressType
        MAX-ACCESS read-only
        STATUS current
        DESCRIPTION
            "
                The private ip type (ipv4, ipv6) of map local device.
            "
        ::= { ibDvpnMapEntry 9 }

    ibDvpnMapLocalPriIp OBJECT-TYPE
        SYNTAX InetAddress
        MAX-ACCESS read-only
        STATUS current
        DESCRIPTION
            "
                The private ip of map local device.
            "
        ::= { ibDvpnMapEntry 10 }

    ibDvpnMapLocalPublicIpType OBJECT-TYPE
        SYNTAX InetAddressType
        MAX-ACCESS read-only
        STATUS current
        DESCRIPTION
            "
                The public ip type (ipv4, ipv6) of map local device.
            "
        ::= { ibDvpnMapEntry 11 }

    ibDvpnMapLocalPublicIp OBJECT-TYPE
        SYNTAX InetAddress
        MAX-ACCESS read-only
        STATUS current
        DESCRIPTION
            "
                The public ip of map local device.
            "
        ::= { ibDvpnMapEntry 12 }

    ibDvpnMapUserName OBJECT-TYPE
        SYNTAX OCTET STRING
        MAX-ACCESS read-only
        STATUS current
        DESCRIPTION
            "
                The user name used by the client registering to server.
                If the client is not been authenticated, this is a null string.
            "
        ::= { ibDvpnMapEntry 13 }

    ibDvpnMapUdpPort OBJECT-TYPE
        SYNTAX Integer32
        MAX-ACCESS read-only
        STATUS current
        DESCRIPTION
            "
                The udp port used by map peer device.
            "
        ::= { ibDvpnMapEntry 14 }

    ibDvpnMapControlId OBJECT-TYPE
        SYNTAX Unsigned32
        MAX-ACCESS read-only
        STATUS current
        DESCRIPTION
            "
                Dvpn map control ID.
            "
        ::= { ibDvpnMapEntry 15 }

    ibDvpnMapType OBJECT-TYPE
        SYNTAX DvpnCommunicateType
        MAX-ACCESS read-only
        STATUS current
        DESCRIPTION
            "
                The type of the map.
                'clientToclient' is not supported here.
            "
        ::= { ibDvpnMapEntry 16 }

    ibDvpnMapState OBJECT-TYPE
        SYNTAX INTEGER
            {
                mapClientInit(1),
                mapClientBegin(2),
                mapClientAlgreq(3),
                mapClientKexReq(4),
                mapClientAuthenReq(5),
                mapClientConfigReq(6),
                mapClientReq(7),
                mapClientSuccess(8),
                mapServerBegin(9),
                mapServerAlgorithm(10),
                mapServerKexInit(11),
                mapServerAuthenInit(12),
                mapServerConfigInit(13),
                mapServerInit(14),
                mapServerFinished(15)
            }
        MAX-ACCESS read-only
        STATUS current
        DESCRIPTION
            "
                mapClientInit: The client initiates the map.
                mapClientBegin: The client begins the process of registering
                                to the server.
                mapClientAlgreq: The client requests to negotiate the algorithm.
                mapClientKexReq: The client requests to negotiate the key.
                mapClientAuthenReq: The client sends authentication information
                                    to the server.
                mapClientConfigReq: The client requests to get some configuration
                                    information from the server. Do not support now.
                mapClientReq: The client requests to register to the server.
                mapClientSuccess: The client registers to the server successfully.
                mapServerBegin: The server begins the process of receive a new register.
                mapServerAlgorithm:The sever begins to negotiate Algorithm.
                mapServerKexInit: The server replys to the algorithm negotiation
                                  packet from the client successfully and begin
                                  to negotiate key.
                mapServerAuthenInit: The server replys to the key negotiation
                                     packet from the client successfully and
                                     begin to authenticate client, in the case of
                                     the authentication-client method is not none.
                mapServerConfigInit: The server send some configuration information
                                     to client. Do not support now.
                mapServerInit: The server replys to the authentication packet
                               from the client successfully and begin to receive
                               client information.
                mapServerFinished: The server receives client information successfully.
            "
        ::= { ibDvpnMapEntry 17 }



--ibDvpnSessionTable

    ibDvpnSessionTable  OBJECT-TYPE
        SYNTAX SEQUENCE OF IbDvpnSessionEntry
        MAX-ACCESS not-accessible
        STATUS current
        DESCRIPTION
            "
                The dvpn session table.
            "
        ::= { ibDvpnMibTableTroop 6 }

    ibDvpnSessionEntry OBJECT-TYPE
        SYNTAX IbDvpnSessionEntry
        MAX-ACCESS not-accessible
        STATUS current
        DESCRIPTION
            "
                The entry of ibDvpnSessionTable.
            "
        INDEX { ibDvpnSessionDvpnId,
                ibDvpnSessionPeerPriIpType,
                ibDvpnSessionPeerPriIp
              }
        ::= { ibDvpnSessionTable 1 }

    IbDvpnSessionEntry ::=
        SEQUENCE {
            ibDvpnSessionDvpnId                          Integer32,
            ibDvpnSessionPeerPriIpType                   InetAddressType,
            ibDvpnSessionPeerPriIp                       InetAddress,
            ibDvpnSessionPeerDeviceId                    OCTET STRING,
            ibDvpnSessionBuildTime                       TimeTicks,
            ibDvpnSessionPeerPubIpType                   InetAddressType,
            ibDvpnSessionPeerPubIp                       InetAddress,
            ibDvpnSessionLocalPubIpType                  InetAddressType,
            ibDvpnSessionLocalPubIp                      InetAddress,
            ibDvpnSessionLocalPriIpType                  InetAddressType,
            ibDvpnSessionLocalPriIp                      InetAddress,
            ibDvpnSessionPeerUdpPort                     Integer32,
            ibDvpnSessionInitiator                       INTEGER,
            ibDvpnSessionUserName                        OCTET STRING,
            ibDvpnSessionState                           INTEGER,
            ibDvpnSessionType                            DvpnCommunicateType,
            ibDvpnSessionPeerType                        INTEGER
        }

    ibDvpnSessionDvpnId OBJECT-TYPE
        SYNTAX Integer32
        MAX-ACCESS accessible-for-notify
        STATUS current
        DESCRIPTION
            "
                The ID of the dvpn domain which the session belongs to.
            "
        ::= { ibDvpnSessionEntry 1 }

    ibDvpnSessionPeerPriIpType OBJECT-TYPE
        SYNTAX InetAddressType
        MAX-ACCESS accessible-for-notify
        STATUS current
        DESCRIPTION
            "
               The private ip type (ipv4, ipv6) of session peer device.
            "
        ::= { ibDvpnSessionEntry 2 }

    ibDvpnSessionPeerPriIp OBJECT-TYPE
        SYNTAX InetAddress
        MAX-ACCESS accessible-for-notify
        STATUS current
        DESCRIPTION
            "
                The private ip of the session peer device.
            "
        ::= { ibDvpnSessionEntry 3 }

    ibDvpnSessionPeerDeviceId OBJECT-TYPE
        SYNTAX OCTET STRING
        MAX-ACCESS read-only
        STATUS current
        DESCRIPTION
            "
                The device ID of session peer device.
                It is a string.
            "
        ::= { ibDvpnSessionEntry 4 }

    ibDvpnSessionBuildTime OBJECT-TYPE
        SYNTAX TimeTicks
        MAX-ACCESS read-only
        STATUS current
        DESCRIPTION
            "
                The time of the Session being built, the unit is second.
            "
        ::= { ibDvpnSessionEntry 5 }

    ibDvpnSessionPeerPubIpType OBJECT-TYPE
        SYNTAX InetAddressType
        MAX-ACCESS read-only
        STATUS current
        DESCRIPTION
            "
                The public ip type (ipv4, ipv6) of session peer device.
            "
        ::= { ibDvpnSessionEntry 6 }

    ibDvpnSessionPeerPubIp OBJECT-TYPE
        SYNTAX InetAddress
        MAX-ACCESS read-only
        STATUS current
        DESCRIPTION
            "
                The public ip of session peer device.
            "
        ::= { ibDvpnSessionEntry 7 }


    ibDvpnSessionLocalPubIpType OBJECT-TYPE
        SYNTAX InetAddressType
        MAX-ACCESS read-only
        STATUS current
        DESCRIPTION
            "
               The public ip type (ipv4, ipv6) of session local device.
            "
        ::= { ibDvpnSessionEntry 8 }

    ibDvpnSessionLocalPubIp OBJECT-TYPE
        SYNTAX InetAddress
        MAX-ACCESS read-only
        STATUS current
        DESCRIPTION
            "
               The public ip of session local device.
            "
        ::= { ibDvpnSessionEntry 9 }

    ibDvpnSessionLocalPriIpType OBJECT-TYPE
        SYNTAX InetAddressType
        MAX-ACCESS read-only
        STATUS current
        DESCRIPTION
            "
               The private ip type (ipv4, ipv6) of session local device.
            "
        ::= { ibDvpnSessionEntry 10 }

    ibDvpnSessionLocalPriIp OBJECT-TYPE
        SYNTAX InetAddress
        MAX-ACCESS read-only
        STATUS current
        DESCRIPTION
            "
               The private ip of session local device.
            "
        ::= { ibDvpnSessionEntry 11 }

    ibDvpnSessionPeerUdpPort OBJECT-TYPE
        SYNTAX Integer32
        MAX-ACCESS read-only
        STATUS current
        DESCRIPTION
            "
               The udp port used by session peer device .
            "
        ::= { ibDvpnSessionEntry 12 }

    ibDvpnSessionInitiator OBJECT-TYPE
        SYNTAX INTEGER
            {
                yes(1),
                no(2)
            }
        MAX-ACCESS read-only
        STATUS current
        DESCRIPTION
            "
                The flag of initiator.
            "
        ::= { ibDvpnSessionEntry 13 }

    ibDvpnSessionUserName OBJECT-TYPE
        SYNTAX OCTET STRING
        MAX-ACCESS read-only
        STATUS current
        DESCRIPTION
            "
                The user's name.
                If the session type is client to client,
                the value of this object is a null string.
            "
        ::= { ibDvpnSessionEntry 14 }

    ibDvpnSessionState OBJECT-TYPE
        SYNTAX INTEGER
            {
                 sessionSetupInit(1),
                 sessionSetupReq(2),
                 sessionSetupSuccess(3),
                 sessionRekeyReq(4),
                 sessionRekeyRep(5)
            }
        MAX-ACCESS read-only
        STATUS current
        DESCRIPTION
            "
                The state of the session.
                sessionSetupInit: The initiation of the session.
                sessionSetupReq: The initiator requests to negotiate the SA and
                                 so on of the session.
                sessionSetupSuccess: The session has been built successfully.
                sessionRekeyReq: The initiator requests to renegotiate the SA.
                sessionRekeyRep: The passive side replies with a SA renegotiation
                                 response packet successfully.
            "
        ::= { ibDvpnSessionEntry 15 }

    ibDvpnSessionType OBJECT-TYPE
        SYNTAX DvpnCommunicateType
        MAX-ACCESS read-only
        STATUS current
        DESCRIPTION
            "
                The type of the session.
            "
        ::= { ibDvpnSessionEntry 16 }

    ibDvpnSessionPeerType OBJECT-TYPE
        SYNTAX INTEGER
            {
                router(1),
                pcClient(2)
            }
        MAX-ACCESS read-only
        STATUS current
        DESCRIPTION
            "
                The type of the session peer device.
                It may be client software or a router.
            "
        ::= { ibDvpnSessionEntry 17 }


--ibDvpnSessionHisTable

    ibDvpnSessionHisTable OBJECT-TYPE
        SYNTAX     SEQUENCE OF IbDvpnSessionHisEntry
        MAX-ACCESS not-accessible
        STATUS     current
        DESCRIPTION
            "
                The dvpn session history table.
                This table contains session's history information,
                include input/output packet number, up/down time, etc.
                This table will exist during the 'ibDvpnSessionHisAgeTime'.
            "
        ::= { ibDvpnMibTableTroop 7 }

    ibDvpnSessionHisEntry OBJECT-TYPE
        SYNTAX     IbDvpnSessionHisEntry
        MAX-ACCESS not-accessible
        STATUS     current
        DESCRIPTION
            "
                The entry of ibDvpnSessionHisTable.
            "
        INDEX { ibDvpnSessionHisDvpnID,
                ibDvpnSessionHisPeerPriIPType,
                ibDvpnSessionHisPeerPriIP }
        ::= { ibDvpnSessionHisTable 1 }

    IbDvpnSessionHisEntry ::= SEQUENCE {
        ibDvpnSessionHisDvpnID           Integer32,
        ibDvpnSessionHisPeerPriIPType    InetAddressType,
        ibDvpnSessionHisPeerPriIP        InetAddress,
        ibDvpnSessionHisSendPkt          Unsigned32,
        ibDvpnSessionHisRcvPkt           Unsigned32,
        ibDvpnSessionHisOnlineNumber     Unsigned32,
        ibDvpnSessionHisFirstUpTime      TimeTicks,
        ibDvpnSessionHisLastUpTime       TimeTicks,
        ibDvpnSessionHisLastDownTime     TimeTicks,
        ibDvpnSessionHisOnlineFlag       INTEGER,
        ibDvpnSessionHisPeerDeviceId     OCTET STRING
     }


    ibDvpnSessionHisDvpnID OBJECT-TYPE
        SYNTAX     Integer32(1..65535)
        MAX-ACCESS not-accessible
        STATUS     current
        DESCRIPTION
            "
                The ID of the dvpn domain which the session belongs to.
            "
        ::= { ibDvpnSessionHisEntry 1 }

    ibDvpnSessionHisPeerPriIPType OBJECT-TYPE
        SYNTAX     InetAddressType
        MAX-ACCESS read-only
        STATUS     current
        DESCRIPTION
            "
                The private ip type (ipv4, ipv6) of session peer device.
            "
        ::= { ibDvpnSessionHisEntry 2 }

    ibDvpnSessionHisPeerPriIP OBJECT-TYPE
        SYNTAX     InetAddress
        MAX-ACCESS not-accessible
        STATUS     current
        DESCRIPTION
            "
                 The private ip of the session peer device.
            "
        ::= { ibDvpnSessionHisEntry 3 }

    ibDvpnSessionHisSendPkt OBJECT-TYPE
        SYNTAX     Unsigned32
        MAX-ACCESS read-only
        STATUS     current
        DESCRIPTION
            "
                The number of sent packets on the session.
            "
        ::= { ibDvpnSessionHisEntry 4 }

    ibDvpnSessionHisRcvPkt OBJECT-TYPE
        SYNTAX     Unsigned32
        MAX-ACCESS read-only
        STATUS     current
        DESCRIPTION
            "
                The number of received packets on the session.
            "
        ::= { ibDvpnSessionHisEntry 5 }

    ibDvpnSessionHisOnlineNumber OBJECT-TYPE
        SYNTAX     Unsigned32
        MAX-ACCESS read-only
        STATUS     current
        DESCRIPTION
            "
                The number of the session online.
            "
        ::= { ibDvpnSessionHisEntry 6 }

    ibDvpnSessionHisFirstUpTime OBJECT-TYPE
        SYNTAX     TimeTicks
        MAX-ACCESS read-only
        STATUS     current
        DESCRIPTION
            "
                The session first online time.
            "
        ::= { ibDvpnSessionHisEntry 7 }


    ibDvpnSessionHisLastUpTime OBJECT-TYPE
        SYNTAX     TimeTicks
        MAX-ACCESS read-only
        STATUS     current
        DESCRIPTION
            "
                The session last online time.
            "
        ::= { ibDvpnSessionHisEntry 8 }

    ibDvpnSessionHisLastDownTime OBJECT-TYPE
        SYNTAX     TimeTicks
        MAX-ACCESS read-only
        STATUS     current
        DESCRIPTION
            "
                The session last down time.
            "
        ::= { ibDvpnSessionHisEntry 9 }


    ibDvpnSessionHisOnlineFlag OBJECT-TYPE
        SYNTAX     INTEGER
            {
                yes(1),
                no(2)
            }
        MAX-ACCESS read-only
        STATUS     current
        DESCRIPTION
            "
                If the session is online, the value is 'yes'.
                If the session is not online, the value is 'no'.
            "
        ::= { ibDvpnSessionHisEntry 10 }

    ibDvpnSessionHisPeerDeviceId OBJECT-TYPE
        SYNTAX OCTET STRING
        MAX-ACCESS read-only
        STATUS current
        DESCRIPTION
            "
                The identifier of peer device.
                It is a string.
            "
        ::= { ibDvpnSessionHisEntry 11 }



 --ibDvpnMibTrap

    ibDvpnNotification OBJECT IDENTIFIER ::= { ibDvpnMibNotification 0 }

    ibDvpnSessionBuildNotification NOTIFICATION-TYPE
        OBJECTS {
            ibDvpnSessionDvpnId,
            ibDvpnSessionPeerPriIpType,
            ibDvpnSessionPeerPriIp,
            ibDvpnLocalDeviceId,
            ibDvpnSessionLocalPriIpType,
            ibDvpnSessionLocalPriIp,
            ibDvpnSessionLocalPubIpType,
            ibDvpnSessionLocalPubIp,
            ibDvpnSessionPeerDeviceId,
            ibDvpnSessionPeerPubIpType,
            ibDvpnSessionPeerPubIp,
            ibDvpnSessionPeerUdpPort,
            ibDvpnSessionPeerType,
            ibDvpnSessionUserName
        }
        STATUS current
        DESCRIPTION
            "
                Dvpn session build notification.
            "
        ::= { ibDvpnNotification 1 }

    ibDvpnSessionDelNotification NOTIFICATION-TYPE
        OBJECTS {
            ibDvpnSessionDvpnId,
            ibDvpnSessionPeerPriIpType,
            ibDvpnSessionPeerPriIp,
            ibDvpnLocalDeviceId,
            ibDvpnSessionLocalPriIpType,
            ibDvpnSessionLocalPriIp,
            ibDvpnSessionLocalPubIpType,
            ibDvpnSessionLocalPubIp,
            ibDvpnSessionPeerDeviceId,
            ibDvpnSessionPeerPubIpType,
            ibDvpnSessionPeerPubIp,
            ibDvpnSessionPeerUdpPort,
            ibDvpnSessionPeerType,
            ibDvpnSessionUserName
        }
        STATUS current
        DESCRIPTION
            "
                Dvpn session deleted notification.
            "
        ::= { ibDvpnNotification 2 }

    ibDvpnMapBuildNotification NOTIFICATION-TYPE
        OBJECTS {
            ibDvpnMapIndex,
            ibDvpnMapDvpnId,
            ibDvpnMapPeerDeviceId,
            ibDvpnMapPeerPriIpType,
            ibDvpnMapPeerPriIp,
            ibDvpnMapPeerPublicIpType,
            ibDvpnMapPeerPublicIp,
            ibDvpnLocalDeviceId,
            ibDvpnMapLocalPriIpType,
            ibDvpnMapLocalPriIp,
            ibDvpnMapLocalPublicIpType,
            ibDvpnMapLocalPublicIp,
            ibDvpnMapUserName
        }
        STATUS current
        DESCRIPTION
            "
                Dvpn map build notification.
            "
        ::= { ibDvpnNotification 3 }

    ibDvpnMapDelNotification NOTIFICATION-TYPE
        OBJECTS {
            ibDvpnMapIndex,
            ibDvpnMapDvpnId,
            ibDvpnMapPeerDeviceId,
            ibDvpnMapPeerPriIpType,
            ibDvpnMapPeerPriIp,
            ibDvpnMapPeerPublicIpType,
            ibDvpnMapPeerPublicIp,
            ibDvpnLocalDeviceId,
            ibDvpnMapLocalPriIpType,
            ibDvpnMapLocalPriIp,
            ibDvpnMapLocalPublicIpType,
            ibDvpnMapLocalPublicIp,
            ibDvpnMapUserName
        }
        STATUS current
        DESCRIPTION
            "
                Dvpn map deleted notification.
            "
        ::= { ibDvpnNotification 4 }


--conformance and Compliance define

    ibDvpnMibCompliances OBJECT IDENTIFIER ::= { ibDvpnMibConformance 1 }

    ibDvpnMibCompliance MODULE-COMPLIANCE
        STATUS current
        DESCRIPTION
            "
                The compliance statement for entities which implement
                the DVPN MIB.
            "
        MODULE
            MANDATORY-GROUPS {
                ibDvpnGlobalGroup,
                ibDvpnDomainInfoGroup,
                ibDvpnPolicyGroup,
                ibDvpnClassGroup,
                ibDvpnTunnelGroup,
                ibDvpnMapGroup,
                ibDvpnSessionGroup,
                ibDvpnSessionHisGroup,
                ibDvpnNotificationGroup
            }
        ::= { ibDvpnMibCompliances 1 }

    ibDvpnMibGroups OBJECT IDENTIFIER ::= { ibDvpnMibConformance 2 }

    ibDvpnGlobalGroup OBJECT-GROUP
        OBJECTS {
            ibDvpnServiceEnable,
            ibDvpnClassNumber,
            ibDvpnClientNumber,
            ibDvpnMapAgeTime,
            ibDvpnClientRegisterInterval,
            ibDvpnClientRegisterDumb,
            ibDvpnClientRegisterRetry,
            ibDvpnInputPkt,
            ibDvpnDropPkt,
            ibDvpnOutputPkt,
            ibDvpnOutputErrorPkt,
            ibDvpnEncryptErrorPkt,
            ibDvpnCurrentDeviceRole,
            ibDvpnDomainNumber,
            ibDvpnMapNumber,
            ibDvpnSessionNumber,
            ibDvpnServerPreSharedKey,
            ibDvpnMapTrapEnable,
            ibDvpnSessionTrapEnable,
            ibDvpnVersion,
            ibDvpnClearDomainAllConection,
            ibDvpnClearDvpnStaInfo,
            ibDvpnTotalRedirectNumber,
            ibDvpnGlobalAuthenClientType,
            ibDvpnGlobalUserDefAAADomain,
            ibDvpnLocalDeviceId,
            ibDvpnSessionHisAgeTime,
            ibDvpnSessionHisReset
        }
        STATUS current
        DESCRIPTION
            "
                A collection of objects providing dvpn global information.
            "
        ::= { ibDvpnMibGroups 1 }

    ibDvpnPolicyGroup OBJECT-GROUP
        OBJECTS {
            ibDvpnPoAuthenClientType,
            ibDvpnPoSessionAlgorithmSuite,
            ibDvpnPoSessionIdleTime,
            ibDvpnPoSessionKeepTime,
            ibDvpnPoSessionSetupInterval,
            ibDvpnPoDataAlgorithmSuite,
            ibDvpnPoSaSeconds,
            ibDvpnPoUserDefAAADomain,
            ibDvpnPoRefTimes,
            ibDvpnPoRowStatus
        }
        STATUS current
        DESCRIPTION
            "
                A collection of objects providing dvpn policy information.
            "
        ::= { ibDvpnMibGroups 2 }

    ibDvpnDomainInfoGroup OBJECT-GROUP
        OBJECTS {
            ibDvpnDomainSessionNum,
            ibDvpnDomainRedirectNum,
            ibDvpnDomainInputPkt,
            ibDvpnDomainDropPkt,
            ibDvpnDomainOutputPkt,
            ibDvpnDomainOutputErrorPkt,
            ibDvpnDomainEncryptErrorPkt
        }
        STATUS current
        DESCRIPTION
            "
                A collection of objects providing dvpn domain information.
            "
        ::= { ibDvpnMibGroups 3 }

    ibDvpnClassGroup OBJECT-GROUP
        OBJECTS {
            ibDvpnClServerPublicIpType,
            ibDvpnClServerPublicIp,
            ibDvpnClServerPriIpType,
            ibDvpnClServerPriIp,
            ibDvpnClAlgorithmSuite,
            ibDvpnClAuthenServerType,
            ibDvpnClPreShareKey,
            ibDvpnClUserName,
            ibDvpnClPwdEncrypted,
            ibDvpnClPasswd,
            ibDvpnClassRowStatus
        }
        STATUS current
        DESCRIPTION
            "
                A collection of objects providing dvpn class information.
            "
        ::= { ibDvpnMibGroups 4 }

    ibDvpnTunnelGroup OBJECT-GROUP
        OBJECTS {
            ibDvpnTunnelInterfaceType,
            ibDvpnTunnelAcl,
            ibDvpnTunnelClientRegType,
            ibDvpnTunnelDvpnId,
            ibDvpnTunnelPolicy,
            ibDvpnTunnelClass
        }
        STATUS current
        DESCRIPTION
            "
                A collection of objects providing dvpn tunnel interface information.
            "
        ::= { ibDvpnMibGroups 5 }

    ibDvpnMapGroup OBJECT-GROUP
        OBJECTS {
            ibDvpnMapIndex,
            ibDvpnMapPeerDeviceId,
            ibDvpnMapDvpnId,
            ibDvpnMapBuildTime,
            ibDvpnMapPeerPriIpType,
            ibDvpnMapPeerPriIp,
            ibDvpnMapPeerPublicIpType,
            ibDvpnMapPeerPublicIp,
            ibDvpnMapLocalPriIpType,
            ibDvpnMapLocalPriIp,
            ibDvpnMapLocalPublicIpType,
            ibDvpnMapLocalPublicIp,
            ibDvpnMapUserName,
            ibDvpnMapUdpPort,
            ibDvpnMapControlId,
            ibDvpnMapType,
            ibDvpnMapState
        }
        STATUS current
        DESCRIPTION
            "
                A collection of objects providing dvpn map information.
            "
        ::= { ibDvpnMibGroups 6 }

    ibDvpnSessionGroup OBJECT-GROUP
        OBJECTS {
            ibDvpnSessionDvpnId,
            ibDvpnSessionPeerDeviceId,
            ibDvpnSessionBuildTime,
            ibDvpnSessionPeerPubIpType,
            ibDvpnSessionPeerPubIp,
            ibDvpnSessionPeerPriIpType,
            ibDvpnSessionPeerPriIp,
            ibDvpnSessionLocalPubIpType,
            ibDvpnSessionLocalPubIp,
            ibDvpnSessionLocalPriIpType,
            ibDvpnSessionLocalPriIp,
            ibDvpnSessionPeerUdpPort,
            ibDvpnSessionInitiator,
            ibDvpnSessionUserName,
            ibDvpnSessionState,
            ibDvpnSessionType,
            ibDvpnSessionPeerType
        }
        STATUS current
        DESCRIPTION
            "
                A collection of objects providing dvpn session information.
            "
        ::= { ibDvpnMibGroups 7 }

    ibDvpnSessionHisGroup OBJECT-GROUP
        OBJECTS {
            ibDvpnSessionHisPeerPriIPType,
            ibDvpnSessionHisSendPkt,
            ibDvpnSessionHisRcvPkt,
            ibDvpnSessionHisOnlineNumber,
            ibDvpnSessionHisFirstUpTime,
            ibDvpnSessionHisLastUpTime,
            ibDvpnSessionHisLastDownTime,
            ibDvpnSessionHisOnlineFlag,
            ibDvpnSessionHisPeerDeviceId
        }
        STATUS current
        DESCRIPTION
            "
                A collection of objects providing dvpn session history information.
            "
        ::= { ibDvpnMibGroups 8 }


    ibDvpnNotificationGroup OBJECT-GROUP
        OBJECTS {
            ibDvpnSessionBuildNotification,
            ibDvpnSessionDelNotification,
            ibDvpnMapBuildNotification,
            ibDvpnMapDelNotification
        }
        STATUS current
        DESCRIPTION
            "
                A collection of objects providing dvpn notification information.
            "
        ::= { ibDvpnMibGroups 9 }

END
