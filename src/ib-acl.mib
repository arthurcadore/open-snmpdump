-- ============================================================================
-- Copyright (C) 2023 Intelbras S.A. All rights reserved.
--
-- Description:
-- Reference:
-- Version: V3.4
-- History:
-- V1.0 created by yuhui.
-- V2.0 2004-10-12 updated by gaolong
--     Define MODULE-IDENTITY for ibAcl
--     Remove chinese characters
--     Add limitation(0..65535) for some table index
--     Fix a default value error of ibAclAdvancedEstablish
-- V2.1 2004-11-18 updated by yubo
--     Add 'ibAclIDSTable' for IDS
-- V2.2 2004-12-13
--     Fix syntax bugs and adjust format of the whole file by jinyi
--     Modify description of ibAclAdvancedDscp by zhuangyu
-- V2.3 2005-1-26 updated by WuZhao02557
--     Change MAX-ACCESS from read-create to not-accessible for the
--     following MIB nodes:
--       ibAclNumGroupAclNum, ibAclNameGroupIndex, ibAclBasicAclNum,
--       ibAclBasicSubitem, ibAclAdvancedAclNum, ibAclAdvancedSubitem
--       ibAclIfAclNum, ibAclIfSubitem, ibAclLinkAclNum, ibAclLinkSubitem
--       ibAclUserAclNum, ibAclUserSubitem, ibAclActiveAclIndex,
--       ibAclActiveIfIndex, ibAclActiveVlanID, ibAclActiveDirection
--     Adjust format of whole file.
--     2005-01-27   updated by zhangyinxi
--     1. Add objects ibAclLinkL2LabelRangeOp, ibAclLinkL2LabelRangeBegin
--        ibAclLinkL2LabelRangeEnd and ibAclLinkMplsExp in ibAclLinkTable
--     2. Add an enumeration mpls(34887) to object ibAclLinkProtocol
--     3. Expand the range of object ibAclActiveVlanID to Integer32
-- V2.4 2005-2-24
--     Make the index of ibAclIDSTable IMPLIED by fuzhenyu because IDS devices
--     require fixed length index to be used. IDS devices only provide index
--     with no sub-identifier indicating the length of the string.
--     Modify enum name(value is 4) of ibAclLinkFormatType to ieee802Dot3 by daishijun
-- V2.5 2005-7-25
--     Add objects ibAclMib2Mode, ibAclVersion, ibAclMib2ObjectsCapabilities,
--      ibAclIPAclNumGroupTable, ibAclIPAclBasicTable, ibAclIPAclAdvancedTable,
--      ibAclMACTable, ibAclEnUserTable by tangshun.
-- V2.6 2006-01-03
--     Add objects ibAclIPAclBasicComment, ibAclIPAclAdvancedComment,
--      ibAclMACComment, ibAclEnUserComment by tangshun.
-- V2.7 2006-03-09 updated by changhuifeng
--     Add object ibAclIPAclAdvancedReflective in ibAclIPAclAdvancedTable.
--     Modify the description of object ibAclIPAclAdvancedFragmentFlag.
--     Modify the description of object ibAclMib2Version.
--     Modify the description of object ibAclLinkDestAny for text error.
--     Modify the description of object ibAclMib2CharacteristicsValue.
-- V2.8 2006-07-06 updated by xialei
--     Modify the description of ibAclIPAclAdvancedIcmpType
--     and ibAclIPAclAdvancedIcmpCode.
--     Change value range of ibAclIPAclAdvancedIcmpCode.
-- V2.9 2006-08-08 updated by chenzhaojie
--     Add enumeration value to ibAclActiveDirection.
-- V3.0 2010-09-01 updated by zhaixiaoxiang
--     Add ibAclResourceUsageTable.
-- V3.1 2012-02-06 updated by wangchenxiao
--     Add ibPacketfilterTrapObjects
--     Add ibPacketfilterTrap
--     2012-02-14 updated by mouxuanli
--     Add ibAclMib2ProcessingStatus of object ibAclMib2NodesGroup
--     Add ibAclNumberGroupName of object ibAclNumberGroupTable
--     Add ibAclIPAclBasicCounting of object ibAclIPAclBasicTable
--     Add ibAclIPAclBasicRouteTypeAny of object ibAclIPAclBasicTable
--     Add ibAclIPAclBasicRouteTypeValue of object ibAclIPAclBasicTable
--     Add ibAclIPAclAdvancedCounting of object ibAclIPAclAdvancedTable
--     Add ibAclIPAclAdvancedTCPFlagMask of object ibAclIPAclAdvancedTable
--     Add ibAclIPAclAdvancedTCPFlagValue of object ibAclIPAclAdvancedTable
--     Add ibAclIPAclAdvancedRouteTypeAny of object ibAclIPAclAdvancedTable
--     Add ibAclIPAclAdvancedRouteTypeValue of object ibAclIPAclAdvancedTable
--     Add ibAclIPAclAdvancedFlowLabel of object ibAclIPAclAdvancedTable
--     Add ibAclMACLog of object ibAclMACTable
--     Add ibAclMACCounting of object ibAclMACTable
--     Add ibAclEnUserLog of object ibAclEnUserTable
--     Add ibAclEnUserCounting of object ibAclEnUserTable
--     Modify the description of ibAclResourceType
--     Add ibAclResourceTypeDescription of object ibAclResourceUsageTable
--     Add ibAclPacketFilterObjects
-- V3.2 2012-11-30 updated by gaoyu
--     Add ibPfilterRunApplyObjType of object ibPfilterAclGroupRunInfoTable
--     Add ibPfilterRunApplyObjIndex of object ibPfilterAclGroupRunInfoTable
--     Add ibPfilterRunApplyDirection of object ibPfilterAclGroupRunInfoTable
--     Add ibPfilterRunApplyAclType of object ibPfilterAclGroupRunInfoTable
--     Add ibPfilterRunApplyAclIndex of object ibPfilterAclGroupRunInfoTable
--     modify the ibPfilterRunApplyObjType of object ibPfilterAclRuleRunInfoTable
--     modify the ibPfilterRunApplyObjIndex of object ibPfilterAclRuleRunInfoTable
--     modify the ibPfilterRunApplyDirection of object ibPfilterAclRuleRunInfoTable
--     modify the ibPfilterRunApplyAclType of object ibPfilterAclRuleRunInfoTable
--     modify the ibPfilterRunApplyAclIndex of object ibPfilterAclRuleRunInfoTable
-- V3.3 2013-11-30 updated by gaoyu
--     Add ibAclNamedGroupTable to object ibAclMib2GlobalGroup
--     Add ibAclIPAclNamedBscTable to object ibAclIPAclGroup
--     Add ibAclIPAclNamedAdvTable to object ibAclIPAclGroup
--     Add ibAclNamedMACTable to object ibAclMACAclGroup
--     Add ibAclIntervalGroup to object ibAclMib2Objects
--     Modify ibPfilterApplyAclType of object ibPfilterApplyTable
--     Modify ibPfilterRunApplyAclType of object ibPfilterAclGroupRunInfoTable
--     Modify ibPfilterSumAclType of object ibPfilterStatisticSumTable
--     Add ibPfilter2ApplyTable to object ibAclPacketFilterObjects
--     Add ibPfilter2AclGroupRunInfoTable to object ibAclPacketFilterObjects
--     Add ibPfilter2AclRuleRunInfoTable to object ibAclPacketFilterObjects
--     Add ibPfilter2StatisticSumTable to object ibAclPacketFilterObjects
--     Add ibAclPacketIfName to object ibAclPacketfilterTrapObjects
--     Add ibAclPacketDirection  to object ibAclPacketfilterTrapObjects
--     Add ibAclPacketBAGG to object ibAclPacketfilterTrapObjects
--     Add ibAclPacketVlanID to object ibAclPacketfilterTrapObjects
--     Add ibAclPacketSrcIP to object ibAclPacketfilterTrapObjects
--     Add ibAclPacketDstIP to object ibAclPacketfilterTrapObjects
--     Add ibAclPacketProtocol to object ibAclPacketfilterTrapObjects
--     Add ibAclPacketDscp to object ibAclPacketfilterTrapObjects
--     Add ibAclPacketFlowLabel to object ibAclPacketfilterTrapObjects
--     Add ibAclPacketIcmpIgmpType to object ibAclPacketfilterTrapObjects
--     Add ibAclPacketIcmpIgmpCode to object ibAclPacketfilterTrapObjects
--     Add ibAclPacketTcpFlags to object ibAclPacketfilterTrapObjects
--     Add ibAclPacketSrcPort to object ibAclPacketfilterTrapObjects
--     Add ibAclPacketDstPort to object ibAclPacketfilterTrapObjects
--     Add ibAclPacketSrcMacAddr to object ibAclPacketfilterTrapObjects
--     Add ibAclPacketDstMacAddr to object ibAclPacketfilterTrapObjects
--     Add ibAclPacketMacTypeLen to object ibAclPacketfilterTrapObjects
--     Add ibAclPacketVlanPCP to object ibAclPacketfilterTrapObjects
--     Add ibAclRuleMatchCount to object ibPfilterTrapPrefix
--     Add ibAclFirstIPv4PktCaptured to object ibPfilterTrapPrefix
--     Add ibAclFirstIPv6PktCaptured to object ibPfilterTrapPrefix
--     Add ibAclFirstEthernetPktCaptured to object ibPfilterTrapPrefix
--     2014-2-20 updated by gaoyu
--     Add ibAclNamedUserTable to object ibAclEnUserAclGroup
--     2014-07-08 updated by gaoyu
--     Add ibAclIPAclAdvancedSrcSuffix to object ibAclIPAclAdvancedTable
--     Add ibAclIPAclAdvancedDestSuffix to object ibAclIPAclAdvancedTable
--     Add ibAclIPAclNamedAdvSrcSuffix to object ibAclIPAclNamedAdvTable
--     Add ibAclIPAclNamedAdvDstSuffix to object ibAclIPAclNamedAdvTable
-- V3.4 2014-10-20 updated by gaoyu
--     Add ibAclMib2ResourceThreshold to object ibAclMib2NodesGroup
--     Add ibAclMib2ResourceLogInterval to object ibAclMib2NodesGroup
--     Add ibAclResourceTypeName to object ibAclTrapObjects
--     Add ibAclResourceUsage to object ibAclTrapObjects
--     Add ibAclResourceUsedEntries to object ibAclTrapObjects
--     Add ibAclResourceTotalEntries to object ibAclTrapObjects
--     Add ibAclResourceChassisID to object ibAclTrapObjects
--     Add ibAclResourceSlotID to object ibAclTrapObjects
--     Add ibAclResourceTrap to object ibAclTrapPrefix
-- ============================================================================
IB-ACL-MIB DEFINITIONS ::= BEGIN

        IMPORTS
            ibCommon
                FROM  IB-OID-MIB
            IpAddress, Integer32, Counter32, OBJECT-TYPE, MODULE-IDENTITY,
            NOTIFICATION-TYPE, Unsigned32, Counter64
                FROM SNMPv2-SMI
            InetAddressType, InetAddress, InetAddressPrefixLength
                FROM INET-ADDRESS-MIB
            RowStatus, TruthValue, MacAddress, TEXTUAL-CONVENTION
                FROM SNMPv2-TC;

--
-- Node definitions
--

        ibAcl MODULE-IDENTITY
            LAST-UPDATED "201410201000Z"        -- Oct 20, 2014 at 10:00 GMT
            ORGANIZATION
                "Intelbras S.A. Industria de Telecomunicacao Eletronica Brasileria."
            CONTACT-INFO
                ""
            DESCRIPTION
                "ACL management information base for managing devices
                that support access control list and packet filtering.
                "
            REVISION "201410201000Z"            -- Oct 22, 2014 at 10:00 GMT
            DESCRIPTION
                "Added 2 ndoes to configure TCAM function and 6 nodes to show trap info."
            ::= { ibCommon 8 }

-- Rule action value
        RuleAction ::= TEXTUAL-CONVENTION
            STATUS current
            DESCRIPTION
                "The value of rule's action.
                 permit: The packet matching the rule will be permitted to forward.
                 deny: The packet matching the rule will be denied.
                "
            SYNTAX INTEGER
            {
                invalid(1),
                permit(2),
                deny(3)
            }

-- CounterClear value
        CounterClear ::= TEXTUAL-CONVENTION
            STATUS  current
            DESCRIPTION
                "cleared: Reset the value of the rule's counter.
                 nouse: 'nouse' will be returned when getting.
                "
            SYNTAX INTEGER
            {
                cleared(1),
                nouse(2)
            }

-- PortOp value
        PortOp ::= TEXTUAL-CONVENTION
            STATUS current
            DESCRIPTION
                "The operation type of TCP and UDP.
                 lt : Less than given port number.
                 eq : Equal to given port number.
                 gt : Greater than given port number.
                 neq : Not equal to given port number.
                 range : Between two port numbers.
                 Default value is 'invalid'.
                "
            SYNTAX INTEGER
            {
                invalid(0),
                lt(1),
                eq(2),
                gt(3),
                neq(4),
                range(5)
            }

-- DSCP value
        DSCPValue ::= TEXTUAL-CONVENTION
            DISPLAY-HINT "d"
            STATUS current
            DESCRIPTION
                "The value of DSCP.
                 <0-63>  Value of DSCP
                 af11    Specify Assured Forwarding 11 service(10)
                 af12    Specify Assured Forwarding 12 service(12)
                 af13    Specify Assured Forwarding 13 service(14)
                 af21    Specify Assured Forwarding 21 service(18)
                 af22    Specify Assured Forwarding 22 service(20)
                 af23    Specify Assured Forwarding 23 service(22)
                 af31    Specify Assured Forwarding 31 service(26)
                 af32    Specify Assured Forwarding 32 service(28)
                 af33    Specify Assured Forwarding 33 service(30)
                 af41    Specify Assured Forwarding 41 service(34)
                 af42    Specify Assured Forwarding 42 service(36)
                 af43    Specify Assured Forwarding 43 service(38)
                 be      Specify Best Effort service(0)
                 cs1     Specify Class Selector 1 service(8)
                 cs2     Specify Class Selector 2 service(16)
                 cs3     Specify Class Selector 3 service(24)
                 cs4     Specify Class Selector 4 service(32)
                 cs5     Specify Class Selector 5 service(40)
                 cs6     Specify Class Selector 6 service(48)
                 cs7     Specify Class Selector 7 service(56)
                 ef      Specify Expedited Forwarding service(46)
                "
            SYNTAX Integer32 (0..63|255)

-- TCP Flags
        TCPFlag ::= TEXTUAL-CONVENTION
            STATUS current
            DESCRIPTION
                "Type of TCP.
                 invalid(0)
                 tcpack(1)  TCP protocol ACK Packet
                 tcpfin(2)  TCP protocol PIN Packet
                 tcppsh(3)  TCP protocol PUSH Packet
                 tcprst(4)  TCP protocol RST Packet
                 tcpsyn(5)  TCP protocol SYN Packet
                 tcpurg(6)  TCP protocol URG Packet
                 Default value is 'invalid'.
                "
            SYNTAX INTEGER
            {
                invalid(0),
                tcpack(1),
                tcpfin(2),
                tcppsh(3),
                tcprst(4),
                tcpsyn(5),
                tcpurg(6)
            }

-- Fragment Flags
        FragmentFlag ::= TEXTUAL-CONVENTION
            STATUS current
            DESCRIPTION
                "Type of fragment.
                 invalid(0)
                 fragment(1)       Frag-Type Fragment
                 fragmentSubseq(2) Frag-Type Fragment-subsequent
                 nonFragment(3)    Frag-Type non-Fragment
                 nonSubseq(4)      Frag-Type non-subsequent
                 Default value is 'invalid'.
                "
            SYNTAX INTEGER
            {
                invalid(0),
                fragment(1),
                fragmentSubseq(2),
                nonFragment(3),
                nonSubseq(4)
            }

-- Address Flags
        AddressFlag ::= TEXTUAL-CONVENTION
            STATUS current
            DESCRIPTION
                "Address flag to select IPv6 Address.
                 Default value is 'invalid'.

                 t64SrcAddrPre64DestAddrPre(1):
                 The mean of the enumeration 't64SrcAddrPre64DestAddrPre' is
                 that system gets the 64 bits prefix of source address and
                 the 64 bits prefix of destination address.

                 t64SrcAddrPre64DestAddrSuf(2):
                 The mean of the enumeration 't64SrcAddrPre64DestAddrSuf' is
                 that system gets the 64 bits prefix of source address and
                 the 64 bits suffix of destination address.

                 t64SrcAddrSuf64DestAddrPre(3):
                 The mean of the enumeration 't64SrcAddrSuf64DestAddrPre' is
                 that system gets the 64 bits suffix of source address and
                 the 64 bits prefix of destination address.

                 t64SrcAddrSuf64DestAddrSuf(4):
                 The mean of the enumeration 't64SrcAddrSuf64DestAddrSuf' is
                 that system gets the 64 bits suffix of source address and
                 the 64 bits suffix of destination address.

                 t128SourceAddress(5):
                 The mean of the enumeration 't128SourceAddress' is that
                 system gets the 128 bits of source address.

                 t128DestinationAddress(6):
                 The mean of the enumeration 't128SourceAddress' is that
                 system gets the 128 bits of destination address.
                "
            SYNTAX INTEGER
            {
                invalid(0),
                t64SrcAddrPre64DestAddrPre(1),
                t64SrcAddrPre64DestAddrSuf(2),
                t64SrcAddrSuf64DestAddrPre(3),
                t64SrcAddrSuf64DestAddrSuf(4),
                t128SourceAddress(5),
                t128DestinationAddress(6)
            }

-- Direction type
        DirectionType ::= TEXTUAL-CONVENTION
            STATUS  current
            DESCRIPTION
                "The direction: inbound or outbound."
            SYNTAX INTEGER
            {
                inbound(1),
                outbound(2)
            }

--
-- nodes defined
--
        ibAclMibObjects OBJECT IDENTIFIER ::= { ibAcl 1 }

        ibAclMode OBJECT-TYPE
            SYNTAX INTEGER
            {
                linkBased(1),
                ipBased(2)
            }
            MAX-ACCESS read-write
            STATUS current
            DESCRIPTION
                "Access-list mode."
            DEFVAL { ipBased }
            ::= { ibAclMibObjects 1 }

--
-- Node of ibAclNumGroupTable
--
        ibAclNumGroupTable OBJECT-TYPE
            SYNTAX SEQUENCE OF IbAclNumGroupEntry
            MAX-ACCESS not-accessible
            STATUS current
            DESCRIPTION
                "Configure the match-order of number-acl group."
            ::= { ibAclMibObjects 2 }

        ibAclNumGroupEntry OBJECT-TYPE
            SYNTAX IbAclNumGroupEntry
            MAX-ACCESS not-accessible
            STATUS current
            DESCRIPTION
                "Define the index of ibAclNumGroupTable."
            INDEX { ibAclNumGroupAclNum }
            ::= { ibAclNumGroupTable 1 }

        IbAclNumGroupEntry ::=
            SEQUENCE
            {
                ibAclNumGroupAclNum
                    Integer32,
                ibAclNumGroupMatchOrder
                    INTEGER,
                ibAclNumGroupSubitemNum
                    Integer32,
                ibAclNumGroupDescription
                    OCTET STRING,
                ibAclNumGroupCountClear
                    INTEGER,
                ibAclNumGroupRowStatus
                    RowStatus
             }

        ibAclNumGroupAclNum OBJECT-TYPE
            SYNTAX Integer32 (1000..5999)
            MAX-ACCESS not-accessible
            STATUS current
            DESCRIPTION
                "The index of number-acl group
                 Interface type:1000..1999
                 Basic type:2000..2999
                 Advance type:3000..3999
                 Link type:4000..4999
                 User type:5000..5999"
            ::= { ibAclNumGroupEntry 1 }

        ibAclNumGroupMatchOrder OBJECT-TYPE
            SYNTAX INTEGER
            {
                config(1),
                auto(2)
            }
            MAX-ACCESS read-create
            STATUS current
            DESCRIPTION
                "The match-order of number-acl group."
            DEFVAL { config }
            ::= { ibAclNumGroupEntry 2 }

        ibAclNumGroupSubitemNum OBJECT-TYPE
            SYNTAX Integer32
            MAX-ACCESS read-only
            STATUS current
            DESCRIPTION
                "The number of number-acl group's node."
            ::= { ibAclNumGroupEntry 3 }

        ibAclNumGroupDescription OBJECT-TYPE
            SYNTAX OCTET STRING (SIZE(0..127))
            MAX-ACCESS read-write
            STATUS current
            DESCRIPTION
                "The description of this acl group."
            ::= { ibAclNumGroupEntry 4 }

        ibAclNumGroupCountClear OBJECT-TYPE
            SYNTAX INTEGER
            {
                cleared(1),
                nouse(2)
            }
            MAX-ACCESS read-create
            STATUS current
            DESCRIPTION
                "Reset the value of rules' counter, which belong to this group."
            ::= { ibAclNumGroupEntry 5 }

        ibAclNumGroupRowStatus OBJECT-TYPE
            SYNTAX RowStatus
            MAX-ACCESS read-create
            STATUS current
            DESCRIPTION
                "RowStatus, now support three state: CreateAndGo, Active, Destroy."
            ::= { ibAclNumGroupEntry 6 }

--
-- Node of ibAclNameGroupTable
--
        ibAclNameGroupTable OBJECT-TYPE
            SYNTAX SEQUENCE OF IbAclNameGroupEntry
            MAX-ACCESS not-accessible
            STATUS current
            DESCRIPTION
                "Create acl-group that identified by name."
            ::= { ibAclMibObjects 3 }

        ibAclNameGroupEntry OBJECT-TYPE
            SYNTAX IbAclNameGroupEntry
            MAX-ACCESS not-accessible
            STATUS current
            DESCRIPTION
                "Define the index of ibAclNameGroupTable."
            INDEX { ibAclNameGroupIndex }
            ::= { ibAclNameGroupTable 1 }

        IbAclNameGroupEntry ::=
            SEQUENCE {
                ibAclNameGroupIndex
                    Integer32,
                ibAclNameGroupCreateName
                    OCTET STRING,
                ibAclNameGroupTypes
                    INTEGER,
                ibAclNameGroupMatchOrder
                    INTEGER,
                ibAclNameGroupSubitemNum
                    Integer32,
                ibAclNameGroupRowStatus
                    RowStatus
             }

        ibAclNameGroupIndex OBJECT-TYPE
            SYNTAX Integer32 (10000..12999)
            MAX-ACCESS not-accessible
            STATUS current
            DESCRIPTION
                "The index of name-acl group."
            ::= { ibAclNameGroupEntry 1 }

        ibAclNameGroupCreateName OBJECT-TYPE
            SYNTAX OCTET STRING (SIZE (0..32))
            MAX-ACCESS read-create
            STATUS current
            DESCRIPTION
                "The name of name-acl group."
            ::= { ibAclNameGroupEntry 2 }

        ibAclNameGroupTypes OBJECT-TYPE
            SYNTAX INTEGER
            {
                basic(1),
                advanced(2),
                ifBased(3),
                link(4),
                user(5)
            }
            MAX-ACCESS read-create
            STATUS current
            DESCRIPTION
                "The type of name-acl group."
            ::= { ibAclNameGroupEntry 3 }

        ibAclNameGroupMatchOrder OBJECT-TYPE
            SYNTAX INTEGER
            {
                config(1),
                auto(2)
            }
            MAX-ACCESS read-create
            STATUS current
            DESCRIPTION
                "The match-order of name-acl group."
            DEFVAL { config }
            ::= { ibAclNameGroupEntry 4 }

        ibAclNameGroupSubitemNum OBJECT-TYPE
            SYNTAX Integer32 (0..128)
            MAX-ACCESS read-only
            STATUS current
            DESCRIPTION
                "The number of name-acl group's node."
            ::= { ibAclNameGroupEntry 5 }

        ibAclNameGroupRowStatus OBJECT-TYPE
            SYNTAX RowStatus
            MAX-ACCESS read-create
            STATUS current
            DESCRIPTION
                "RowStatus, now support three state: CreateAndGo, Active, Destroy."
            ::= { ibAclNameGroupEntry 6 }

--
-- ibAclBasicRuleTable
--
        ibAclBasicRuleTable OBJECT-TYPE
            SYNTAX SEQUENCE OF IbAclBasicRuleEntry
            MAX-ACCESS not-accessible
            STATUS current
            DESCRIPTION
                "Configure the rule for basic acl group."
            ::= { ibAclMibObjects 4 }

        ibAclBasicRuleEntry OBJECT-TYPE
            SYNTAX IbAclBasicRuleEntry
            MAX-ACCESS not-accessible
            STATUS current
            DESCRIPTION
                "Define the index of ibAclBasicRuleTable."
            INDEX { ibAclBasicAclNum, ibAclBasicSubitem }
            ::= { ibAclBasicRuleTable 1 }

        IbAclBasicRuleEntry ::=
            SEQUENCE {
                ibAclBasicAclNum
                    Integer32,
                ibAclBasicSubitem
                    Integer32,
                ibAclBasicAct
                    INTEGER,
                ibAclBasicSrcIp
                    IpAddress,
                ibAclBasicSrcWild
                    IpAddress,
                ibAclBasicTimeRangeName
                    OCTET STRING,
                ibAclBasicFragments
                    TruthValue,
                ibAclBasicLog
                    TruthValue,
                ibAclBasicEnable
                    TruthValue,
                ibAclBasicCount
                    Counter32,
                ibAclBasicCountClear
                    INTEGER,
                ibAclBasicRowStatus
                    RowStatus
             }

        ibAclBasicAclNum OBJECT-TYPE
            SYNTAX Integer32 (0|2000..2999|10000..12999)
            MAX-ACCESS not-accessible
            STATUS current
            DESCRIPTION
                "The index of basic acl group."
            ::= { ibAclBasicRuleEntry 1 }

        ibAclBasicSubitem OBJECT-TYPE
            SYNTAX Integer32 (0..65535)
            MAX-ACCESS not-accessible
            STATUS current
            DESCRIPTION
                "The subindex of basic acl group."
            ::= { ibAclBasicRuleEntry 2 }

        ibAclBasicAct OBJECT-TYPE
            SYNTAX INTEGER
            {
                permit(1),
                deny(2)
            }
            MAX-ACCESS read-create
            STATUS current
            DESCRIPTION
                "The action of basic acl rule."
            ::= { ibAclBasicRuleEntry 3 }

        ibAclBasicSrcIp OBJECT-TYPE
            SYNTAX IpAddress
            MAX-ACCESS read-create
            STATUS current
            DESCRIPTION
                "Source IP-address of basic acl rule."
            ::= { ibAclBasicRuleEntry 4 }

        ibAclBasicSrcWild OBJECT-TYPE
            SYNTAX IpAddress
            MAX-ACCESS read-create
            STATUS current
            DESCRIPTION
                "Source IP-address wild of basic acl rule."
            ::= { ibAclBasicRuleEntry 5 }

        ibAclBasicTimeRangeName OBJECT-TYPE
            SYNTAX OCTET STRING (SIZE (0..32))
            MAX-ACCESS read-create
            STATUS current
            DESCRIPTION
                "The Time-range of basic acl rule."
            ::= { ibAclBasicRuleEntry 6 }

        ibAclBasicFragments OBJECT-TYPE
            SYNTAX TruthValue
            MAX-ACCESS read-create
            STATUS current
            DESCRIPTION
                "The flag of matching fragmented packet."
            ::= { ibAclBasicRuleEntry 7 }

        ibAclBasicLog OBJECT-TYPE
            SYNTAX TruthValue
            MAX-ACCESS read-create
            STATUS current
            DESCRIPTION
                "The flag of log."
            ::= { ibAclBasicRuleEntry 8 }

        ibAclBasicEnable OBJECT-TYPE
            SYNTAX TruthValue
            MAX-ACCESS read-only
            STATUS current
            DESCRIPTION
                "The rule is active or not.
                 true : active
                 false : inactive
                "
            ::= { ibAclBasicRuleEntry 9 }

        ibAclBasicCount OBJECT-TYPE
            SYNTAX Counter32
            MAX-ACCESS read-only
            STATUS current
            DESCRIPTION
                "The count of matched by basic rule."
            ::= { ibAclBasicRuleEntry 10 }

        ibAclBasicCountClear OBJECT-TYPE
            SYNTAX INTEGER
            {
                cleared(1),
                nouse(2)
            }
            MAX-ACCESS read-create
            STATUS current
            DESCRIPTION
                "Reset the value of counter."
            ::= { ibAclBasicRuleEntry 11 }

        ibAclBasicRowStatus OBJECT-TYPE
            SYNTAX RowStatus
            MAX-ACCESS read-create
            STATUS current
            DESCRIPTION
                "RowStatus, now support three state: CreateAndGo, Active, Destroy."
            ::= { ibAclBasicRuleEntry 12 }

--
-- ibAclAdvancedRuleTable
--
        ibAclAdvancedRuleTable OBJECT-TYPE
            SYNTAX SEQUENCE OF IbAclAdvancedRuleEntry
            MAX-ACCESS not-accessible
            STATUS current
            DESCRIPTION
                "Configure the rule for advanced acl group."
            ::= { ibAclMibObjects 5 }

        ibAclAdvancedRuleEntry OBJECT-TYPE
            SYNTAX IbAclAdvancedRuleEntry
            MAX-ACCESS not-accessible
            STATUS current
            DESCRIPTION
                "Define the index of ibAclAdvancedRuleTable."
            INDEX { ibAclAdvancedAclNum, ibAclAdvancedSubitem }
            ::= { ibAclAdvancedRuleTable 1 }

        IbAclAdvancedRuleEntry ::=
            SEQUENCE {
                ibAclAdvancedAclNum
                    Integer32,
                ibAclAdvancedSubitem
                    Integer32,
                ibAclAdvancedAct
                    INTEGER,
                ibAclAdvancedProtocol
                    Integer32,
                ibAclAdvancedSrcIp
                    IpAddress,
                ibAclAdvancedSrcWild
                    IpAddress,
                ibAclAdvancedSrcOp
                    INTEGER,
                ibAclAdvancedSrcPort1
                    Integer32,
                ibAclAdvancedSrcPort2
                    Integer32,
                ibAclAdvancedDestIp
                    IpAddress,
                ibAclAdvancedDestWild
                    IpAddress,
                ibAclAdvancedDestOp
                    INTEGER,
                ibAclAdvancedDestPort1
                    Integer32,
                ibAclAdvancedDestPort2
                    Integer32,
                ibAclAdvancedPrecedence
                    Integer32,
                ibAclAdvancedTos
                    Integer32,
                ibAclAdvancedDscp
                    Integer32,
                ibAclAdvancedEstablish
                    TruthValue,
                ibAclAdvancedTimeRangeName
                    OCTET STRING,
                ibAclAdvancedIcmpType
                    Integer32,
                ibAclAdvancedIcmpCode
                    Integer32,
                ibAclAdvancedFragments
                    TruthValue,
                ibAclAdvancedLog
                    TruthValue,
                ibAclAdvancedEnable
                    TruthValue,
                ibAclAdvancedCount
                    Counter32,
                ibAclAdvancedCountClear
                    INTEGER,
                ibAclAdvancedRowStatus
                    RowStatus
             }

        ibAclAdvancedAclNum OBJECT-TYPE
            SYNTAX Integer32 (0|3000..3999|10000..12999)
            MAX-ACCESS not-accessible
            STATUS current
            DESCRIPTION
                "The index of advanced acl group."
            ::= { ibAclAdvancedRuleEntry 1 }

        ibAclAdvancedSubitem OBJECT-TYPE
            SYNTAX Integer32 (0..65535)
            MAX-ACCESS not-accessible
            STATUS current
            DESCRIPTION
                "The subindex of advanced acl group."
            ::= { ibAclAdvancedRuleEntry 2 }

        ibAclAdvancedAct OBJECT-TYPE
            SYNTAX INTEGER
            {
                permit(1),
                deny(2)
            }
            MAX-ACCESS read-create
            STATUS current
            DESCRIPTION
                "The action of Advance acl rule."

            ::= { ibAclAdvancedRuleEntry 3 }

        ibAclAdvancedProtocol OBJECT-TYPE
            SYNTAX Integer32 (0..255)
            MAX-ACCESS read-create
            STATUS current
            DESCRIPTION
                "The protocol-type of advanced acl group.
                 <1-255>  Protocol number
                  gre      GRE tunneling(47)
                  icmp     Internet Control Message Protocol(1)
                  igmp     Internet Group Management Protocol(2)
                  ip       Any IP protocol
                  ipinip   IP in IP tunneling(4)
                  ospf     OSPF routing protocol(89)
                  tcp      Transmission Control Protocol (6)
                  udp      User Datagram Protocol (17)"
            ::= { ibAclAdvancedRuleEntry 4 }

        ibAclAdvancedSrcIp OBJECT-TYPE
            SYNTAX IpAddress
            MAX-ACCESS read-create
            STATUS current
            DESCRIPTION
                "Source IP-address of advanced acl group."
            ::= { ibAclAdvancedRuleEntry 5 }

        ibAclAdvancedSrcWild OBJECT-TYPE
            SYNTAX IpAddress
            MAX-ACCESS read-create
            STATUS current
            DESCRIPTION
                "Source IP-address wild of advanced acl group."
            ::= { ibAclAdvancedRuleEntry 6 }

        ibAclAdvancedSrcOp OBJECT-TYPE
            SYNTAX INTEGER
            {
                invalid(0),
                lt(1),
                eq(2),
                gt(3),
                neq(4),
                range(5)
            }
            MAX-ACCESS read-create
            STATUS current
            DESCRIPTION
                "The source IP-address's operator of advanced acl group."
            ::= { ibAclAdvancedRuleEntry 7 }

        ibAclAdvancedSrcPort1 OBJECT-TYPE
            SYNTAX Integer32 (0..65535)
            MAX-ACCESS read-create
            STATUS current
            DESCRIPTION
                "The fourth layer source port1."
            ::= { ibAclAdvancedRuleEntry 8 }

        ibAclAdvancedSrcPort2 OBJECT-TYPE
            SYNTAX Integer32 (0..65535)
            MAX-ACCESS read-create
            STATUS current
            DESCRIPTION
                "The fourth layer source port2."
            ::= { ibAclAdvancedRuleEntry 9 }

        ibAclAdvancedDestIp OBJECT-TYPE
            SYNTAX IpAddress
            MAX-ACCESS read-create
            STATUS current
            DESCRIPTION
                "Destination IP-address of advanced acl group."
            ::= { ibAclAdvancedRuleEntry 10 }

        ibAclAdvancedDestWild OBJECT-TYPE
            SYNTAX IpAddress
            MAX-ACCESS read-create
            STATUS current
            DESCRIPTION
                "Destination IP-address wild of advanced acl group."
            ::= { ibAclAdvancedRuleEntry 11 }

        ibAclAdvancedDestOp OBJECT-TYPE
            SYNTAX INTEGER
            {
                invalid(0),
                lt(1),
                eq(2),
                gt(3),
                neq(4),
                range(5)
            }
            MAX-ACCESS read-create
            STATUS current
            DESCRIPTION
                "The destination IP-address's operator of advanced acl group."
            ::= { ibAclAdvancedRuleEntry 12 }

        ibAclAdvancedDestPort1 OBJECT-TYPE
            SYNTAX Integer32 (0..65535)
            MAX-ACCESS read-create
            STATUS current
            DESCRIPTION
                "The fourth layer destination port1."
            ::= { ibAclAdvancedRuleEntry 13 }

        ibAclAdvancedDestPort2 OBJECT-TYPE
            SYNTAX Integer32 (0..65535)
            MAX-ACCESS read-create
            STATUS current
            DESCRIPTION
                "The fourth layer destination port2."
            ::= { ibAclAdvancedRuleEntry 14 }

        ibAclAdvancedPrecedence OBJECT-TYPE
            SYNTAX Integer32 (0..7|255)
            MAX-ACCESS read-create
            STATUS current
            DESCRIPTION
                "The value of IP-packet's precedence.
                <0-7>           Value of precedence
                routine         Specify routine precedence(0)
                priority        Specify priority precedence(1)
                immediate       Specify immediate precedence(2)
                flash           Specify flash precedence(3)
                flash-override  Specify flash-override precedence(4)
                critical        Specify critical precedence(5)
                internet        Specify internetwork control precedence(6)
                network         Specify network control precedence(7) "
            ::= { ibAclAdvancedRuleEntry 15 }

        ibAclAdvancedTos OBJECT-TYPE
            SYNTAX Integer32 (0..15|255)
            MAX-ACCESS read-create
            STATUS current
            DESCRIPTION
                "The value of IP-packet's TOS.
                  <0-15>             Value of TOS(type of service)
                  max-reliability    Match packets with max reliable TOS(2)
                  max-throughput     Match packets with max throughput TOS(4)
                  min-delay          Match packets with min delay TOS(8)
                  min-monetary-cost  Match packets with min monetary cost TOS(1)
                  normal             Match packets with normal TOS(0) "
            ::= { ibAclAdvancedRuleEntry 16 }

        ibAclAdvancedDscp OBJECT-TYPE
            SYNTAX Integer32 (0..63|255)
            MAX-ACCESS read-create
            STATUS current
            DESCRIPTION
                "The value of DSCP.
                <0-63>  Value of DSCP
                af11    Specify Assured Forwarding 11 service(10)
                af12    Specify Assured Forwarding 12 service(12)
                af13    Specify Assured Forwarding 13 service(14)
                af21    Specify Assured Forwarding 21 service(18)
                af22    Specify Assured Forwarding 22 service(20)
                af23    Specify Assured Forwarding 23 service(22)
                af31    Specify Assured Forwarding 31 service(26)
                af32    Specify Assured Forwarding 32 service(28)
                af33    Specify Assured Forwarding 33 service(30)
                af41    Specify Assured Forwarding 41 service(34)
                af42    Specify Assured Forwarding 42 service(36)
                af43    Specify Assured Forwarding 43 service(38)
                be      Specify Best Effort service(0)
                cs1     Specify Class Selector 1 service(8)
                cs2     Specify Class Selector 2 service(16)
                cs3     Specify Class Selector 3 service(24)
                cs4     Specify Class Selector 4 service(32)
                cs5     Specify Class Selector 5 service(40)
                cs6     Specify Class Selector 6 service(48)
                cs7     Specify Class Selector 7 service(56)
                ef      Specify Expedited Forwarding service(46)"
            ::= { ibAclAdvancedRuleEntry 17 }

        ibAclAdvancedEstablish OBJECT-TYPE
            SYNTAX TruthValue
            MAX-ACCESS read-create
            STATUS current
            DESCRIPTION
                "Establish flag."
            DEFVAL { false }
            ::= { ibAclAdvancedRuleEntry 18 }

        ibAclAdvancedTimeRangeName OBJECT-TYPE
            SYNTAX OCTET STRING (SIZE (0..32))
            MAX-ACCESS read-create
            STATUS current
            DESCRIPTION
                "The Time-range of advanced acl rule."
            ::= { ibAclAdvancedRuleEntry 19 }

        ibAclAdvancedIcmpType OBJECT-TYPE
            SYNTAX Integer32 (0..255|65535)
            MAX-ACCESS read-create
            STATUS current
            DESCRIPTION
                "The type of ICMP packet.
                Integer32               ICMP type
                echo                  Type=8, Code=0
                echo-reply            Type=0, Code=0
                fragmentneed-DFset    Type=3, Code=4
                host-redirect         Type=5, Code=1
                host-tos-redirect     Type=5, Code=3
                host-unreachable      Type=3, Code=1
                information-reply     Type=16, Code=0
                information-request   Type=15, Code=0
                net-redirect          Type=5, Code=0
                net-tos-redirect      Type=5, Code=2
                net-unreachable       Type=3, Code=0
                parameter-problem     Type=12, Code=0
                port-unreachable      Type=3, Code=3
                protocol-unreachable  Type=3, Code=2
                reassembly-timeout    Type=11, Code=1
                source-quench         Type=4, Code=0
                source-route-failed   Type=3, Code=5
                timestamp-reply       Type=14, Code=0
                timestamp-request     Type=13, Code=0
                ttl-exceeded          Type=11, Code=0  "
            ::= { ibAclAdvancedRuleEntry 20 }

        ibAclAdvancedIcmpCode OBJECT-TYPE
            SYNTAX Integer32 (0..255|65535)
            MAX-ACCESS read-create
            STATUS current
            DESCRIPTION
                "The code of ICMP packet."
            ::= { ibAclAdvancedRuleEntry 21 }

        ibAclAdvancedFragments OBJECT-TYPE
            SYNTAX TruthValue
            MAX-ACCESS read-create
            STATUS current
            DESCRIPTION
                "The flag of matching fragmented packet."
            ::= { ibAclAdvancedRuleEntry 22 }

        ibAclAdvancedLog OBJECT-TYPE
            SYNTAX TruthValue
            MAX-ACCESS read-create
            STATUS current
            DESCRIPTION
                "The flag of log."
            ::= { ibAclAdvancedRuleEntry 23 }

        ibAclAdvancedEnable OBJECT-TYPE
            SYNTAX TruthValue
            MAX-ACCESS read-only
            STATUS current
            DESCRIPTION
                "The rule is active or not.
                 true : active
                 false : inactive
                "
            ::= { ibAclAdvancedRuleEntry 24 }

        ibAclAdvancedCount OBJECT-TYPE
            SYNTAX Counter32
            MAX-ACCESS read-only
            STATUS current
            DESCRIPTION
                "The count of matched by advanced rule."
            ::= { ibAclAdvancedRuleEntry 25 }

        ibAclAdvancedCountClear OBJECT-TYPE
            SYNTAX INTEGER
            {
                cleared(1),
                nouse(2)
            }
            MAX-ACCESS read-create
            STATUS current
            DESCRIPTION
                "Reset the value of counter."
            ::= { ibAclAdvancedRuleEntry 26 }

        ibAclAdvancedRowStatus OBJECT-TYPE
            SYNTAX RowStatus
            MAX-ACCESS read-create
            STATUS current
            DESCRIPTION
                "RowStatus, now support three state: CreateAndGo, Active, Destroy."
            ::= { ibAclAdvancedRuleEntry 27 }
--
-- ibAclIfRuleTable
--
        ibAclIfRuleTable OBJECT-TYPE
            SYNTAX SEQUENCE OF IbAclIfRuleEntry
            MAX-ACCESS not-accessible
            STATUS current
            DESCRIPTION
                "Configure the rule for interface-based acl group."
            ::= { ibAclMibObjects 6 }

        ibAclIfRuleEntry OBJECT-TYPE
            SYNTAX IbAclIfRuleEntry
            MAX-ACCESS not-accessible
            STATUS current
            DESCRIPTION
                "Define the index of ibAclIfRuleTable."
            INDEX { ibAclIfAclNum, ibAclIfSubitem }
            ::= { ibAclIfRuleTable 1 }

        IbAclIfRuleEntry ::=
            SEQUENCE {
                ibAclIfAclNum
                    Integer32,
                ibAclIfSubitem
                    Integer32,
                ibAclIfAct
                    INTEGER,
                ibAclIfIndex
                    Integer32,
                ibAclIfAny
                    TruthValue,
                ibAclIfTimeRangeName
                    OCTET STRING,
                ibAclIfLog
                    TruthValue,
                ibAclIfEnable
                    TruthValue,
                ibAclIfCount
                    Counter32,
                ibAclIfCountClear
                    INTEGER,
                ibAclIfRowStatus
                    RowStatus
             }

        ibAclIfAclNum OBJECT-TYPE
            SYNTAX Integer32 (0|1000..1999|10000..12999)
            MAX-ACCESS not-accessible
            STATUS current
            DESCRIPTION
                "The index of interface-based acl group."
            ::= { ibAclIfRuleEntry 1 }

        ibAclIfSubitem OBJECT-TYPE
            SYNTAX Integer32 (0..65535)
            MAX-ACCESS not-accessible
            STATUS current
            DESCRIPTION
                "The subindex of interface-based acl group."
            ::= { ibAclIfRuleEntry 2 }

        ibAclIfAct OBJECT-TYPE
            SYNTAX INTEGER
            {
                permit(1),
                deny(2)
            }
            MAX-ACCESS read-create
            STATUS current
            DESCRIPTION
                "The action of interface-based acl group."
            ::= { ibAclIfRuleEntry 3 }

        ibAclIfIndex OBJECT-TYPE
            SYNTAX Integer32 (0..2147483647)
            MAX-ACCESS read-create
            STATUS current
            DESCRIPTION
                "The index of interface."
            ::= { ibAclIfRuleEntry 4 }

        ibAclIfAny OBJECT-TYPE
            SYNTAX TruthValue
            MAX-ACCESS read-create
            STATUS current
            DESCRIPTION
                "The flag of matching any interface."
            ::= { ibAclIfRuleEntry 5 }

        ibAclIfTimeRangeName OBJECT-TYPE
            SYNTAX OCTET STRING (SIZE (0..32))
            MAX-ACCESS read-create
            STATUS current
            DESCRIPTION
                "The Time-range of interface-based acl rule."
            ::= { ibAclIfRuleEntry 6 }

        ibAclIfLog OBJECT-TYPE
            SYNTAX TruthValue
            MAX-ACCESS read-create
            STATUS current
            DESCRIPTION
                "The flag of log."
            ::= { ibAclIfRuleEntry 7 }

        ibAclIfEnable OBJECT-TYPE
            SYNTAX TruthValue
            MAX-ACCESS read-only
            STATUS current
            DESCRIPTION
                "The rule is active or not.
                 true : active
                 false : inactive
                "
            ::= { ibAclIfRuleEntry 8 }

        ibAclIfCount OBJECT-TYPE
            SYNTAX Counter32
            MAX-ACCESS read-only
            STATUS current
            DESCRIPTION
                "The count of matched by basic rule."
            ::= { ibAclIfRuleEntry 9 }

        ibAclIfCountClear OBJECT-TYPE
            SYNTAX INTEGER
            {
                cleared(1),
                nouse(2)
            }
            MAX-ACCESS read-create
            STATUS current
            DESCRIPTION
                "Reset the value of the rule's counter."
            ::= { ibAclIfRuleEntry 10 }

        ibAclIfRowStatus OBJECT-TYPE
            SYNTAX RowStatus
            MAX-ACCESS read-create
            STATUS current
            DESCRIPTION
                "RowStatus, now support three state: CreateAndGo, Active, Destroy."
            ::= { ibAclIfRuleEntry 11 }

--
-- ibAclLinkTable
--
        ibAclLinkTable OBJECT-TYPE
            SYNTAX SEQUENCE OF IbAclLinkEntry
            MAX-ACCESS not-accessible
            STATUS current
            DESCRIPTION
                "Create link acl."
            ::= { ibAclMibObjects 7 }

        ibAclLinkEntry OBJECT-TYPE
            SYNTAX IbAclLinkEntry
            MAX-ACCESS not-accessible
            STATUS current
            DESCRIPTION
                "The entry of the link acl table."
            INDEX { ibAclLinkAclNum, ibAclLinkSubitem }
            ::= { ibAclLinkTable 1 }

        IbAclLinkEntry ::=
            SEQUENCE {
                ibAclLinkAclNum
                    Integer32,
                ibAclLinkSubitem
                    Integer32,
                ibAclLinkAct
                    INTEGER,
                ibAclLinkProtocol
                    INTEGER,
                ibAclLinkFormatType
                    INTEGER,
                ibAclLinkVlanTag
                    INTEGER,
                ibAclLinkVlanPri
                    Integer32,
                ibAclLinkSrcVlanId
                    Integer32,
                ibAclLinkSrcMac
                    MacAddress,
                ibAclLinkSrcMacWild
                    MacAddress,
                ibAclLinkSrcIfIndex
                    Integer32,
                ibAclLinkSrcAny
                    TruthValue,
                ibAclLinkDestVlanId
                    Integer32,
                ibAclLinkDestMac
                    MacAddress,
                ibAclLinkDestMacWild
                    MacAddress,
                ibAclLinkDestIfIndex
                    Integer32,
                ibAclLinkDestAny
                    TruthValue,
                ibAclLinkTimeRangeName
                    OCTET STRING,
                ibAclLinkEnable
                    TruthValue,
                ibAclLinkRowStatus
                    RowStatus,
                ibAclLinkTypeCode
                    OCTET STRING,
                ibAclLinkTypeMask
                    OCTET STRING,
                ibAclLinkLsapCode
                    OCTET STRING,
                ibAclLinkLsapMask
                    OCTET STRING,
                ibAclLinkL2LabelRangeOp
                    INTEGER,
                ibAclLinkL2LabelRangeBegin
                    Integer32,
                ibAclLinkL2LabelRangeEnd
                    Integer32,
                ibAclLinkMplsExp
                    Integer32
             }

        ibAclLinkAclNum OBJECT-TYPE
            SYNTAX Integer32 (0|4000..4999|10000..12999)
            MAX-ACCESS not-accessible
            STATUS current
            DESCRIPTION
                "The index of link-based acl group."
            ::= { ibAclLinkEntry 1 }

        ibAclLinkSubitem OBJECT-TYPE
            SYNTAX Integer32 (0..65535)
            MAX-ACCESS not-accessible
            STATUS current
            DESCRIPTION
                "The subindex of link-based acl group."
            ::= { ibAclLinkEntry 2 }

        ibAclLinkAct OBJECT-TYPE
            SYNTAX INTEGER
            {
                permit(1),
                deny(2)
            }
            MAX-ACCESS read-create
            STATUS current
            DESCRIPTION
                "The action of link-based acl group."
            ::= { ibAclLinkEntry 3 }

        ibAclLinkProtocol OBJECT-TYPE
            SYNTAX INTEGER
            {
                invalid(0),
                ip(2048),
                arp(2054),
                rarp(32821),
                mpls(34887),
                pppoeControl(34915),
                pppoeData(34916)
            }
            MAX-ACCESS read-create
            STATUS current
            DESCRIPTION
                "The layer 2 protocol-type of link acl rule."
            DEFVAL { invalid }
            ::= { ibAclLinkEntry 4 }

        ibAclLinkFormatType OBJECT-TYPE
            SYNTAX INTEGER
            {
                invalid(0),
                ethernetII(1),
                snap(2),
                ieee802Dot3And2(3),
                ieee802Dot3(4)
            }
            MAX-ACCESS read-create
            STATUS current
            DESCRIPTION
                "Format type of link acl rule."
            ::= { ibAclLinkEntry 5 }

        ibAclLinkVlanTag OBJECT-TYPE
            SYNTAX INTEGER
            {
                invalid(0),
                tagged(1),
                untagged(2)
            }
            MAX-ACCESS read-create
            STATUS current
            DESCRIPTION
                "The flag of vlan tag of link acl rule."
            ::= { ibAclLinkEntry 6 }

        ibAclLinkVlanPri OBJECT-TYPE
            SYNTAX Integer32 (0..7 | 255)
            MAX-ACCESS read-create
            STATUS current
            DESCRIPTION
                "Vlan priority of link acl rule."
            ::= { ibAclLinkEntry 7 }

        ibAclLinkSrcVlanId OBJECT-TYPE
            SYNTAX Integer32 (0..4094)
            MAX-ACCESS read-create
            STATUS current
            DESCRIPTION
                "Source vlan ID of link acl rule."
            ::= { ibAclLinkEntry 8 }

        ibAclLinkSrcMac OBJECT-TYPE
            SYNTAX MacAddress
            MAX-ACCESS read-create
            STATUS current
            DESCRIPTION
                "Source mac of link acl rule."
            ::= { ibAclLinkEntry 9 }

        ibAclLinkSrcMacWild OBJECT-TYPE
            SYNTAX MacAddress
            MAX-ACCESS read-create
            STATUS current
            DESCRIPTION
                "Source mac wildzard of link acl rule."
            ::= { ibAclLinkEntry 10 }

        ibAclLinkSrcIfIndex OBJECT-TYPE
            SYNTAX Integer32 (0..2147483647)
            MAX-ACCESS read-create
            STATUS current
            DESCRIPTION
                "Source IfIndex of link acl rule."
            ::= { ibAclLinkEntry 11 }

        ibAclLinkSrcAny OBJECT-TYPE
            SYNTAX TruthValue
            MAX-ACCESS read-create
            STATUS current
            DESCRIPTION
                "The flag of matching any source."
            ::= { ibAclLinkEntry 12 }

        ibAclLinkDestVlanId OBJECT-TYPE
            SYNTAX Integer32 (0..4094)
            MAX-ACCESS read-create
            STATUS current
            DESCRIPTION
                "Destination vlan ID of link acl rule."
            ::= { ibAclLinkEntry 13 }

        ibAclLinkDestMac OBJECT-TYPE
            SYNTAX MacAddress
            MAX-ACCESS read-create
            STATUS current
            DESCRIPTION
                "Destination mac of link acl rule."
            ::= { ibAclLinkEntry 14 }

        ibAclLinkDestMacWild OBJECT-TYPE
            SYNTAX MacAddress
            MAX-ACCESS read-create
            STATUS current
            DESCRIPTION
                "Destination mac wildzard of link acl rule."
            ::= { ibAclLinkEntry 15 }

        ibAclLinkDestIfIndex OBJECT-TYPE
            SYNTAX Integer32 (0..2147483647)
            MAX-ACCESS read-create
            STATUS current
            DESCRIPTION
                "Destination IfIndex of link acl rule."
            ::= { ibAclLinkEntry 16 }

        ibAclLinkDestAny OBJECT-TYPE
            SYNTAX TruthValue
            MAX-ACCESS read-create
            STATUS current
            DESCRIPTION
                "The flag of matching any destination."
            ::= { ibAclLinkEntry 17 }

        ibAclLinkTimeRangeName OBJECT-TYPE
            SYNTAX OCTET STRING (SIZE (0..32))
            MAX-ACCESS read-create
            STATUS current
            DESCRIPTION
                "The Time-range of link-based acl rule."
            ::= { ibAclLinkEntry 18 }

        ibAclLinkEnable OBJECT-TYPE
            SYNTAX TruthValue
            MAX-ACCESS read-only
            STATUS current
            DESCRIPTION
                "The rule is active or not.
                 true : active
                 false : inactive
                "
            ::= { ibAclLinkEntry 19 }

        ibAclLinkRowStatus OBJECT-TYPE
            SYNTAX RowStatus
            MAX-ACCESS read-create
            STATUS current
            DESCRIPTION
                "RowStatus, now support three state: CreateAndGo, Active, Destroy."
            ::= { ibAclLinkEntry 20 }

            ibAclLinkTypeCode   OBJECT-TYPE
            SYNTAX OCTET STRING ( SIZE(0..32) )
            MAX-ACCESS read-create
            STATUS current
            DESCRIPTION
                "The type of layer 2 protocol.0x0000...0xffff."
            ::= { ibAclLinkEntry 21 }

            ibAclLinkTypeMask   OBJECT-TYPE
            SYNTAX OCTET STRING ( SIZE(0..32) )
            MAX-ACCESS read-create
            STATUS current
            DESCRIPTION
                "The mask of layer 2 protocol.0x0000...0xffff."
            ::= { ibAclLinkEntry 22 }

            ibAclLinkLsapCode   OBJECT-TYPE
            SYNTAX     OCTET STRING (SIZE(0..32))
            MAX-ACCESS read-create
            STATUS current
            DESCRIPTION
                "The type of LSAP.0x0000...0xffff."
            ::= { ibAclLinkEntry 23 }

        ibAclLinkLsapMask   OBJECT-TYPE
            SYNTAX OCTET STRING (SIZE(0..32))
            MAX-ACCESS read-create
            STATUS current
            DESCRIPTION
                "The mask of LSAP.0x0000...0xffff."
            ::= { ibAclLinkEntry 24 }

        ibAclLinkL2LabelRangeOp OBJECT-TYPE
            SYNTAX INTEGER
            {
                invalid(0),
                lt(1),
                eq(2),
                gt(3),
                neq(4),
                range(5)
            }
            MAX-ACCESS read-create
            STATUS current
            DESCRIPTION
                "Operation symbol of the MPLS label.
                 If the symbol is range(5), the objects ibAclLinkL2LabelRangeBegin and
                 ibAclLinkL2LabelRangeEnd should have different values indicating a range.
                 Otherwise, only ibAclLinkL2LabelRangeBegin counts,
                 object ibAclLinkL2LabelRangeEnd is ignored.

                 invalid(0) -- unavailable
                 lt(1) -- less than
                 eq(2) -- equal
                 gt(3) -- great than
                 neq(4) -- not equal
                 range(5) -- a range with two ends included
                "
            ::= { ibAclLinkEntry 25 }

        ibAclLinkL2LabelRangeBegin OBJECT-TYPE
            SYNTAX Integer32
            MAX-ACCESS read-create
            STATUS current
            DESCRIPTION
                "The beginning of VPLS VC label."
            ::= { ibAclLinkEntry 26 }

        ibAclLinkL2LabelRangeEnd OBJECT-TYPE
            SYNTAX Integer32
            MAX-ACCESS read-create
            STATUS current
            DESCRIPTION
                "The end of VPLS VC label."
            ::= { ibAclLinkEntry 27 }

        ibAclLinkMplsExp OBJECT-TYPE
            SYNTAX Integer32
            MAX-ACCESS read-create
            STATUS current
            DESCRIPTION
                "The value of MPLS-packet's Exp."
            ::= { ibAclLinkEntry 28 }
--
-- ibAclUserTable
--
        ibAclUserTable OBJECT-TYPE
            SYNTAX SEQUENCE OF IbAclUserEntry
            MAX-ACCESS not-accessible
            STATUS current
            DESCRIPTION
                "Create user acl."
            ::= { ibAclMibObjects 8 }

        ibAclUserEntry OBJECT-TYPE
            SYNTAX IbAclUserEntry
            MAX-ACCESS not-accessible
            STATUS current
            DESCRIPTION
                "The entry of user acl table."
            INDEX { ibAclUserAclNum, ibAclUserSubitem }
            ::= { ibAclUserTable 1 }

        IbAclUserEntry ::=
            SEQUENCE {
                ibAclUserAclNum
                    Integer32,
                ibAclUserSubitem
                    Integer32,
                ibAclUserAct
                    INTEGER,
                ibAclUserFormatType
                    INTEGER,
                ibAclUserVlanTag
                    INTEGER,
                ibAclUserRuleStr
                    OCTET STRING,
                ibAclUserRuleMask
                    OCTET STRING,
                ibAclUserTimeRangeName
                    OCTET STRING,
                ibAclUserEnable
                    TruthValue,
                ibAclUserRowStatus
                    RowStatus
             }

        ibAclUserAclNum OBJECT-TYPE
            SYNTAX Integer32 (0|5000..5999|10000..12999)
            MAX-ACCESS not-accessible
            STATUS current
            DESCRIPTION
                "The number of the user acl."
            ::= { ibAclUserEntry 1 }

        ibAclUserSubitem OBJECT-TYPE
            SYNTAX Integer32 (0..65535)
            MAX-ACCESS not-accessible
            STATUS current
            DESCRIPTION
                "The subitem of the user acl."
            ::= { ibAclUserEntry 2 }

        ibAclUserAct OBJECT-TYPE
            SYNTAX INTEGER
            {
                permit(1),
                deny(2)
            }
            MAX-ACCESS read-create
            STATUS current
            DESCRIPTION
                "The action of the user acl."
            ::= { ibAclUserEntry 3 }

        ibAclUserFormatType OBJECT-TYPE
            SYNTAX INTEGER
            {
                invalid(0),
                ethernetII(1),
                snap(2),
                ieee802Dot2And3(3),
                ieee802Dot4(4)
            }
            MAX-ACCESS read-create
            STATUS current
            DESCRIPTION
                "Format type."
            DEFVAL { invalid }
            ::= { ibAclUserEntry 4 }

        ibAclUserVlanTag OBJECT-TYPE
            SYNTAX INTEGER
            {
                invalid(0),
                tagged(1),
                untagged(2)
            }
            MAX-ACCESS read-create
            STATUS current
            DESCRIPTION
                "Vlan tag exits or not."
            DEFVAL { invalid }
            ::= { ibAclUserEntry 5 }

        ibAclUserRuleStr OBJECT-TYPE
            SYNTAX OCTET STRING (SIZE (1..80))
            MAX-ACCESS read-create
            STATUS current
            DESCRIPTION
                "Rule string."
            ::= { ibAclUserEntry 6 }

        ibAclUserRuleMask OBJECT-TYPE
            SYNTAX OCTET STRING (SIZE (1..80))
            MAX-ACCESS read-create
            STATUS current
            DESCRIPTION
                "Rule mask."
            ::= { ibAclUserEntry 7 }

        ibAclUserTimeRangeName OBJECT-TYPE
            SYNTAX OCTET STRING (SIZE (0..32))
            MAX-ACCESS read-create
            STATUS current
            DESCRIPTION
                "The Time-range of the user defined acl."
            ::= { ibAclUserEntry 8 }

        ibAclUserEnable OBJECT-TYPE
            SYNTAX TruthValue
            MAX-ACCESS read-only
            STATUS current
            DESCRIPTION
                "The rule is active or not.
                 true : active
                 false : inactive
                "
            ::= { ibAclUserEntry 9 }

        ibAclUserRowStatus OBJECT-TYPE
            SYNTAX RowStatus
            MAX-ACCESS read-create
            STATUS current
            DESCRIPTION
                "RowStatus, now support three state: CreateAndGo, Active, Destroy."
            ::= { ibAclUserEntry 10 }
--
-- ibAclActiveTable
--
        ibAclActiveTable OBJECT-TYPE
            SYNTAX SEQUENCE OF IbAclActiveEntry
            MAX-ACCESS not-accessible
            STATUS current
            DESCRIPTION
                "Active acl."
            ::= { ibAclMibObjects 9 }

        ibAclActiveEntry OBJECT-TYPE
            SYNTAX IbAclActiveEntry
            MAX-ACCESS not-accessible
            STATUS current
            DESCRIPTION
                "The entry of active acl table."
            INDEX { ibAclActiveAclIndex,
                    ibAclActiveIfIndex,
                    ibAclActiveVlanID,
                    ibAclActiveDirection
                  }
            ::= { ibAclActiveTable 1 }

        IbAclActiveEntry ::=
            SEQUENCE {
                ibAclActiveAclIndex
                    Integer32,
                ibAclActiveIfIndex
                    Integer32,
                ibAclActiveVlanID
                    Integer32,
                ibAclActiveDirection
                    INTEGER,
                ibAclActiveUserAclNum
                    Integer32,
                ibAclActiveUserAclSubitem
                    Integer32,
                ibAclActiveIpAclNum
                    Integer32,
                ibAclActiveIpAclSubitem
                    Integer32,
                ibAclActiveLinkAclNum
                    Integer32,
                ibAclActiveLinkAclSubitem
                    Integer32,
                ibAclActiveRuntime
                    TruthValue,
                ibAclActiveRowStatus
                    RowStatus
             }

        ibAclActiveAclIndex OBJECT-TYPE
            SYNTAX Integer32 (0|1..5999|10000..12999)
            MAX-ACCESS not-accessible
            STATUS current
            DESCRIPTION
                "Acl index."
            ::= { ibAclActiveEntry 1 }

        ibAclActiveIfIndex OBJECT-TYPE
            SYNTAX Integer32 (0..2147483647)
            MAX-ACCESS not-accessible
            STATUS current
            DESCRIPTION
                "IfIndex."
            ::= { ibAclActiveEntry 2 }

        ibAclActiveVlanID OBJECT-TYPE
            SYNTAX Integer32
            MAX-ACCESS not-accessible
            STATUS current
            DESCRIPTION
                "The lower 16 bits is Vlan ID, the higher 16 bits,
                 if not zero, it describes the slot ID of the L3plus board.
                "
            ::= { ibAclActiveEntry 3 }

        ibAclActiveDirection OBJECT-TYPE
            SYNTAX INTEGER
            {
                invalid(0),
                input(1),
                output(2),
                both(3)
            }
            MAX-ACCESS not-accessible
            STATUS current
            DESCRIPTION
                "Direction."
            ::= { ibAclActiveEntry 4 }

        ibAclActiveUserAclNum OBJECT-TYPE
            SYNTAX Integer32 (0|5000..5999|10000..12999)
            MAX-ACCESS read-create
            STATUS current
            DESCRIPTION
                "The number of the user acl."
            ::= { ibAclActiveEntry 5 }

        ibAclActiveUserAclSubitem OBJECT-TYPE
            SYNTAX Integer32 (0..65535)
            MAX-ACCESS read-create
            STATUS current
            DESCRIPTION
                "The subitem of the user acl."
            ::= { ibAclActiveEntry 6 }

        ibAclActiveIpAclNum OBJECT-TYPE
            SYNTAX Integer32 (0|2000..3999|10000..12999)
            MAX-ACCESS read-create
            STATUS current
            DESCRIPTION
                "The number of the IP acl."
            ::= { ibAclActiveEntry 7 }

        ibAclActiveIpAclSubitem OBJECT-TYPE
            SYNTAX Integer32 (0..65535)
            MAX-ACCESS read-create
            STATUS current
            DESCRIPTION
                "The subitem of the IP acl."
            ::= { ibAclActiveEntry 8 }

        ibAclActiveLinkAclNum OBJECT-TYPE
            SYNTAX Integer32 (0|4000..4999|10000..12999)
            MAX-ACCESS read-create
            STATUS current
            DESCRIPTION
                "The num of the link acl."
            ::= { ibAclActiveEntry 9 }

        ibAclActiveLinkAclSubitem OBJECT-TYPE
            SYNTAX Integer32 (0..65535)
            MAX-ACCESS read-create
            STATUS current
            DESCRIPTION
                "The subitem of the link acl."
            ::= { ibAclActiveEntry 10 }

        ibAclActiveRuntime OBJECT-TYPE
            SYNTAX TruthValue
            MAX-ACCESS read-only
            STATUS current
            DESCRIPTION
                "Is run or not."
            ::= { ibAclActiveEntry 11 }

        ibAclActiveRowStatus OBJECT-TYPE
            SYNTAX RowStatus
            MAX-ACCESS read-create
            STATUS current
            DESCRIPTION
                "RowStatus, now support three state: CreateAndGo, Active, Destroy."
            ::= { ibAclActiveEntry 12 }

--
-- ibAclIDSTable
--
        ibAclIDSTable OBJECT-TYPE
            SYNTAX SEQUENCE OF IbAclIDSEntry
            MAX-ACCESS not-accessible
            STATUS current
            DESCRIPTION
                "Configure the rule for IDS."
            ::= { ibAclMibObjects 10 }

        ibAclIDSEntry OBJECT-TYPE
            SYNTAX IbAclIDSEntry
            MAX-ACCESS not-accessible
            STATUS current
            DESCRIPTION
                "The entry of acl ids table."
            INDEX { IMPLIED ibAclIDSName}
            ::= { ibAclIDSTable 1 }

        IbAclIDSEntry ::=
            SEQUENCE {
                ibAclIDSName
                    OCTET STRING,
                ibAclIDSSrcMac
                    MacAddress,
                ibAclIDSDestMac
                    MacAddress,
                ibAclIDSSrcIp
                    IpAddress,
                ibAclIDSSrcWild
                    IpAddress,
                ibAclIDSDestIp
                    IpAddress,
                ibAclIDSDestWild
                    IpAddress,
                ibAclIDSSrcPort
                    Integer32,
                ibAclIDSDestPort
                    Integer32,
                ibAclIDSProtocol
                    Integer32,
                ibAclIDSDenyTime
                    Unsigned32,
                ibAclIDSAct
                    INTEGER,
                ibAclIDSRowStatus
                    RowStatus
             }

        ibAclIDSName OBJECT-TYPE
            SYNTAX OCTET STRING (SIZE (1..32))
            MAX-ACCESS not-accessible
            STATUS current
            DESCRIPTION
                "The name index of the IDS table."
            ::= { ibAclIDSEntry 1 }

        ibAclIDSSrcMac OBJECT-TYPE
            SYNTAX MacAddress
            MAX-ACCESS read-create
            STATUS current
            DESCRIPTION
                "Source mac of IDS acl rule."
            ::= { ibAclIDSEntry 2 }


        ibAclIDSDestMac OBJECT-TYPE
            SYNTAX MacAddress
            MAX-ACCESS read-create
            STATUS current
            DESCRIPTION
                "Destination mac of IDS acl rule."
            ::= { ibAclIDSEntry 3 }

           ibAclIDSSrcIp OBJECT-TYPE
            SYNTAX IpAddress
            MAX-ACCESS read-create
            STATUS current
            DESCRIPTION
                "Source IP-address of IDS acl rule."
            ::= { ibAclIDSEntry 4 }

        ibAclIDSSrcWild OBJECT-TYPE
            SYNTAX IpAddress
            MAX-ACCESS read-create
            STATUS current
            DESCRIPTION
                "Source IP-address wild of IDS acl rule."
            ::= { ibAclIDSEntry 5 }

           ibAclIDSDestIp OBJECT-TYPE
            SYNTAX IpAddress
            MAX-ACCESS read-create
            STATUS current
            DESCRIPTION
                "Destination IP-address of IDS acl rule."
            ::= { ibAclIDSEntry 6 }

        ibAclIDSDestWild OBJECT-TYPE
            SYNTAX IpAddress
            MAX-ACCESS read-create
            STATUS current
            DESCRIPTION
                "Destination IP-address wild of IDS acl rule."
            ::= { ibAclIDSEntry 7 }

            ibAclIDSSrcPort OBJECT-TYPE
            SYNTAX Integer32 (0..65535)
            MAX-ACCESS read-create
            STATUS current
            DESCRIPTION
                "The fourth layer source port."
            ::= { ibAclIDSEntry 8 }

        ibAclIDSDestPort OBJECT-TYPE
            SYNTAX Integer32 (0..65535)
            MAX-ACCESS read-create
            STATUS current
            DESCRIPTION
                "The fourth layer destination port."
            ::= { ibAclIDSEntry 9 }

            ibAclIDSProtocol OBJECT-TYPE
            SYNTAX Integer32 (0..255)
            MAX-ACCESS read-create
            STATUS current
            DESCRIPTION
                "The protocol-type of advanced acl group.
                 <1-255>  Protocol number
                  gre      GRE tunneling(47)
                  icmp     Internet Control Message Protocol(1)
                  igmp     Internet Group Management Protocol(2)
                  ip       Any IP protocol
                  ipinip   IP in IP tunneling(4)
                  ospf     OSPF routing protocol(89)
                  tcp      Transmission Control Protocol (6)
                  udp      User Datagram Protocol (17)
                 "
            ::= { ibAclIDSEntry 10 }

        ibAclIDSDenyTime OBJECT-TYPE
            SYNTAX Unsigned32
            MAX-ACCESS read-create
            STATUS current
            DESCRIPTION
                "The maximum number of seconds which deny for this acl rule."
            DEFVAL { 0 }
            ::= { ibAclIDSEntry 11 }


        ibAclIDSAct OBJECT-TYPE
            SYNTAX INTEGER
            {
                permit(1),
                deny(2)
            }
            MAX-ACCESS read-create
            STATUS current
            DESCRIPTION
                "The action of IDS acl rule."
            ::= { ibAclIDSEntry 12 }

        ibAclIDSRowStatus OBJECT-TYPE
            SYNTAX RowStatus
            MAX-ACCESS read-create
            STATUS current
            DESCRIPTION
                "RowStatus, now supports three states:  CreateAndGo, Active, and Destroy."
            ::= { ibAclIDSEntry 13 }
--
-- Nodes of ibAclMib2Objects
--
        ibAclMib2Objects OBJECT IDENTIFIER ::= { ibAcl 2 }
--
-- Nodes of ibAclMib2GlobalGroup
--
        ibAclMib2GlobalGroup OBJECT IDENTIFIER ::= { ibAclMib2Objects 1 }

        ibAclMib2NodesGroup OBJECT IDENTIFIER ::= { ibAclMib2GlobalGroup 1 }

        ibAclMib2Mode OBJECT-TYPE
            SYNTAX INTEGER
            {
                linkBased(1),
                ipBased(2)
            }
            MAX-ACCESS read-write
            STATUS current
            DESCRIPTION
                "The applying mode of ACL."
            ::= { ibAclMib2NodesGroup 1 }

        ibAclMib2Version OBJECT-TYPE
            SYNTAX Integer32
            MAX-ACCESS read-only
            STATUS current
            DESCRIPTION
                "The version of this file.
                 The output value has the format of 'xx'or 'xxx'.
                 For example: 10 means 1.0; 125 means 12.5.
                "
            ::= { ibAclMib2NodesGroup 2 }

        ibAclMib2ObjectsCapabilities OBJECT-TYPE
            SYNTAX BITS
            {
                ibAclMib2Mode(0),
                ibAclVersion(1),
                ibAclMib2ObjectsCapabilities(2),
                ibAclMib2CapabilityTable(3),
                ibAclNumberGroupTable(4),
                ibAclIPAclBasicTable(5),
                ibAclIPAclAdvancedTable(6),
                ibAclMACTable(7),
                ibAclEnUserTable(8),
                ibAclMib2ProcessingStatus(9)
            }
            MAX-ACCESS read-only
            STATUS current
            DESCRIPTION
                "The objects of ibAclMib2Objects."
            ::= { ibAclMib2NodesGroup 3 }

        ibAclMib2ProcessingStatus OBJECT-TYPE
            SYNTAX INTEGER
            {
                processing(1),
                done(2)
            }
            MAX-ACCESS read-only
            STATUS current
            DESCRIPTION
                "The processing status of ACL operation."
            ::= { ibAclMib2NodesGroup 4 }

        ibAclMib2ResourceThreshold OBJECT-TYPE
            SYNTAX Integer32 (0..100)
            MAX-ACCESS read-write
            STATUS current
            DESCRIPTION
                "The threshold of TCAM resources.
                 The value 0 indicates that cancelling the TCAM resource notification function."
            ::= { ibAclMib2NodesGroup 5 }

        ibAclMib2ResourceLogInterval OBJECT-TYPE
            SYNTAX Integer32 (1..60)
            MAX-ACCESS read-write
            STATUS current
            DESCRIPTION
                "The value of interval.  It must be in the range of 1 to 60.
                 Default value is 5."
            ::= { ibAclMib2NodesGroup 6 }

        ibAclMib2CapabilityTable OBJECT-TYPE
            SYNTAX SEQUENCE OF IbAclMib2CapabilityEntry
            MAX-ACCESS not-accessible
            STATUS current
            DESCRIPTION
                "The capability of mib2."
            ::= { ibAclMib2GlobalGroup 2 }

        ibAclMib2CapabilityEntry OBJECT-TYPE
            SYNTAX IbAclMib2CapabilityEntry
            MAX-ACCESS not-accessible
            STATUS current
            DESCRIPTION
                "The information of Capability of mib2."
            INDEX { ibAclMib2EntityType,
                    ibAclMib2EntityIndex,
                    ibAclMib2ModuleIndex,
                    ibAclMib2CharacteristicsIndex
                  }
            ::= { ibAclMib2CapabilityTable 1 }

        IbAclMib2CapabilityEntry ::=
            SEQUENCE
            {
                ibAclMib2EntityType
                    INTEGER,
                ibAclMib2EntityIndex
                    Integer32,
                ibAclMib2ModuleIndex
                    INTEGER,
                ibAclMib2CharacteristicsIndex
                    Integer32,
                ibAclMib2CharacteristicsDesc
                    OCTET STRING,
                ibAclMib2CharacteristicsValue
                    Unsigned32
            }

        ibAclMib2EntityType OBJECT-TYPE
            SYNTAX INTEGER
            {
                system(1),
                interface(2)
            }
            MAX-ACCESS not-accessible
            STATUS current
            DESCRIPTION
                "The type of entity.
                 system: The entity is systemic level.
                 interface: The entity is interface level.
                "
            ::= { ibAclMib2CapabilityEntry 1 }

        ibAclMib2EntityIndex OBJECT-TYPE
            SYNTAX Integer32 (0..2147483647)
            MAX-ACCESS not-accessible
            STATUS current
            DESCRIPTION
                "The index of entity.
                 If ibAclMib2EntityType is system, the value of this object is 0.

                 If ibAclMib2EntityType is interface,
                 the value of this object is equal to 'ifIndex'.
                "
            ::= { ibAclMib2CapabilityEntry 2 }

        ibAclMib2ModuleIndex OBJECT-TYPE
            SYNTAX INTEGER
            {
                layer3(1),
                layer2(2),
                userDefined(3)
            }
            MAX-ACCESS not-accessible
            STATUS current
            DESCRIPTION
                "The module index of ACL."
            ::= { ibAclMib2CapabilityEntry 3 }

        ibAclMib2CharacteristicsIndex OBJECT-TYPE
            SYNTAX Integer32 (0..2147483647)
            MAX-ACCESS not-accessible
            STATUS current
            DESCRIPTION
                "The characteristics index of mib2.
                 See DESCRIPTION of ibAclMib2CharacteristicsValue
                 to get detail information about the value of this object.
                "
            ::= { ibAclMib2CapabilityEntry 4 }

        ibAclMib2CharacteristicsDesc OBJECT-TYPE
            SYNTAX OCTET STRING (SIZE(0..255))
            MAX-ACCESS read-only
            STATUS current
            DESCRIPTION
                "The description of characteristics."
            ::= { ibAclMib2CapabilityEntry 5 }

        ibAclMib2CharacteristicsValue OBJECT-TYPE
            SYNTAX Unsigned32
            MAX-ACCESS read-only
            STATUS current
            DESCRIPTION
                "The value of capability of this object.
                 TypeOfRuleStringValue : notSupport(0) and the length of
                 RuleString.

                 TypeOfCodeValue : OnlyOneNotSupport(0),
                                   MoreThanOneNotSupport(1)
                 If ibAclMib2CharacteristicsValue is 'moreThanOneNotSupport',
                 ibAclMib2CharacteristicsDesc must be used to depict which
                 protocols are not supported.  The output value of
                 ibAclMib2CharacteristicsDesc has the format of 'a,b'.
                 For example, 'ip,rarp'.

                 layer3 Module:
                 Index    Characteristics           value
                 1        SourceIPAddress           notSupport(0)
                 2        DestinationIPAddress      notSupport(0)
                 3        SourcePort                notSupport(0)
                 4        DestinationPort           notSupport(0)
                 5        IPPrecedence              notSupport(0)
                 6        TOS                       notSupport(0)
                 7        DSCP                      notSupport(0)
                 8        TCPFlag                   notSupport(0)
                 9        FragmentFlag              notSupport(0)
                 10       Log                       notSupport(0)
                 11       RuleMatchCounter          notSupport(0)
                 12       ResetRuleMatchCounter     notSupport(0)
                 13       VPN                       notSupport(0)
                 15       protocol                  notSupport(0)
                 16       AddressFlag               notSupport(0)

                 layer2 Module:
                 Index    Characteristics           value
                 1        ProtocolType              TypeOfCodeValue
                 2        SourceMAC                 notSupport(0)
                 3        DestinationMAC            notSupport(0)
                 4        LSAPType                  TypeOfCodeValue
                 5        CoS                       notSupport(0)

                 UserDefined Module:
                 Index    Characteristics           value
                 1        UserDefaultOffset         TypeOfRuleStringValue
                 2        UserL2RuleOffset          TypeOfRuleStringValue
                 3        UserMplsOffset            TypeOfRuleStringValue
                 4        UserIPv4Offset            TypeOfRuleStringValue
                 5        UserIPv6Offset            TypeOfRuleStringValue
                 6        UserL4Offset              TypeOfRuleStringValue
                 7        UserL5Offset              TypeOfRuleStringValue
                "
            ::= { ibAclMib2CapabilityEntry 6 }

--
-- Nodes of number group
--
        ibAclNumberGroupTable OBJECT-TYPE
            SYNTAX SEQUENCE OF IbAclNumberGroupEntry
            MAX-ACCESS not-accessible
            STATUS current
            DESCRIPTION
                "A table of the number acl group information."
            ::= { ibAclMib2GlobalGroup 3 }

        ibAclNumberGroupEntry OBJECT-TYPE
            SYNTAX IbAclNumberGroupEntry
            MAX-ACCESS not-accessible
            STATUS current
            DESCRIPTION
                "Number acl group information entry."
            INDEX { ibAclNumberGroupType, ibAclNumberGroupIndex }
            ::= { ibAclNumberGroupTable 1 }

        IbAclNumberGroupEntry ::=
            SEQUENCE
            {
                ibAclNumberGroupType
                    INTEGER,
                ibAclNumberGroupIndex
                    Integer32,
                ibAclNumberGroupRowStatus
                    RowStatus,
                ibAclNumberGroupMatchOrder
                    INTEGER,
                ibAclNumberGroupStep
                    Integer32,
                ibAclNumberGroupDescription
                    OCTET STRING,
                ibAclNumberGroupCountClear
                    CounterClear,
                ibAclNumberGroupRuleCounter
                    Counter32,
                ibAclNumberGroupName
                    OCTET STRING
            }
        ibAclNumberGroupType OBJECT-TYPE
            SYNTAX INTEGER
            {
                ipv4(1),
                ipv6(2),
                mac(3),
                user(4)
            }
            MAX-ACCESS not-accessible
            STATUS current
            DESCRIPTION
                "The type of number group.
                 Basic ACL and Advanced ACL support ipv4 and ipv6.
                 The range of Basic ACL is from 2000 to 2999.
                 The range of Advanced ACL is from 3000 to 3999.

                 Simple ACL supports ipv6 only.
                 The range of Simple ACL is from 10000 to 42767.

                 MAC ACL support mac only.
                 The range of MAC ACL is from 4000 to 4999.

                 User-defined ACL support user only.
                 The range of user-defined ACL is from 5000 to 5999.
                "
            ::= { ibAclNumberGroupEntry 1 }

        ibAclNumberGroupIndex OBJECT-TYPE
            SYNTAX Integer32 (2000..5999|10000..42767)
            MAX-ACCESS not-accessible
            STATUS current
            DESCRIPTION
                "The group index of number acl.
                 Basic type:2000..2999
                 Advanced type:3000..3999
                 MAC type:4000..4999
                 User type:5000..5999
                 Simple type:10000..42767
                "
            ::= { ibAclNumberGroupEntry 2 }

        ibAclNumberGroupRowStatus OBJECT-TYPE
            SYNTAX RowStatus
            MAX-ACCESS read-create
            STATUS current
            DESCRIPTION
                "RowStatus."
            ::= { ibAclNumberGroupEntry 3 }

        ibAclNumberGroupMatchOrder OBJECT-TYPE
            SYNTAX INTEGER
            {
                config(1),
                auto(2)
            }
            MAX-ACCESS read-create
            STATUS current
            DESCRIPTION
                "The match-order of number acl group."
            DEFVAL { config }
            ::= { ibAclNumberGroupEntry 4 }

        ibAclNumberGroupStep OBJECT-TYPE
            SYNTAX Integer32 (1..20)
            MAX-ACCESS read-create
            STATUS current
            DESCRIPTION
                "The step of rule index."
            DEFVAL { 5 }
            ::= { ibAclNumberGroupEntry 5 }

        ibAclNumberGroupDescription OBJECT-TYPE
            SYNTAX OCTET STRING (SIZE(0..127))
            MAX-ACCESS read-create
            STATUS current
            DESCRIPTION
                "Description of this acl group."
            ::= { ibAclNumberGroupEntry 6 }

        ibAclNumberGroupCountClear OBJECT-TYPE
            SYNTAX CounterClear
            MAX-ACCESS read-write
            STATUS current
            DESCRIPTION
                "Reset the value of counters of this group."
            DEFVAL { nouse }
            ::= { ibAclNumberGroupEntry 7 }

        ibAclNumberGroupRuleCounter OBJECT-TYPE
            SYNTAX Counter32
            MAX-ACCESS read-only
            STATUS current
            DESCRIPTION
                "The rule count of number acl group."
            ::= { ibAclNumberGroupEntry 8 }

        ibAclNumberGroupName OBJECT-TYPE
            SYNTAX OCTET STRING (SIZE(0..63))
            MAX-ACCESS read-create
            STATUS current
            DESCRIPTION
                "Name of this acl group."
            ::= { ibAclNumberGroupEntry 9 }

--
-- Nodes of named ACL group
--
       ibAclNamedGroupTable OBJECT-TYPE
            SYNTAX SEQUENCE OF IbAclNamedGroupEntry
            MAX-ACCESS not-accessible
            STATUS current
            DESCRIPTION
                "A table of the named ACL group."
            ::= { ibAclMib2GlobalGroup 4 }

        ibAclNamedGroupEntry OBJECT-TYPE
            SYNTAX IbAclNamedGroupEntry
            MAX-ACCESS not-accessible
            STATUS current
            DESCRIPTION
                "Named ACL group entry."
            INDEX
            {
                ibAclNumberGroupType,
                ibAclNamedGroupCategory,
                ibAclNamedGroupName
            }
            ::= { ibAclNamedGroupTable 1 }

        IbAclNamedGroupEntry ::=
            SEQUENCE
            {
                ibAclNamedGroupCategory
                    INTEGER,
                ibAclNamedGroupName
                    OCTET STRING,
                ibAclNamedGroupRowStatus
                    RowStatus,
                ibAclNamedGroupMatchOrder
                    INTEGER,
                ibAclNamedGroupStep
                    Integer32,
                ibAclNamedGroupDescription
                    OCTET STRING,
                ibAclNamedGroupCountClear
                    CounterClear,
                ibAclNamedGroupRuleCounter
                    Counter32
            }

        ibAclNamedGroupCategory OBJECT-TYPE
            SYNTAX INTEGER
            {
                invalid(0),
                basic(1),
                advanced(2)
            }
            MAX-ACCESS not-accessible
            STATUS current
            DESCRIPTION
                "The category of number group.  1 indicates basic ACL, 2 indicates
                advanced ACL."
            ::= { ibAclNamedGroupEntry 1 }

        ibAclNamedGroupName OBJECT-TYPE
            SYNTAX OCTET STRING (SIZE(1..63))
            MAX-ACCESS not-accessible
            STATUS current
            DESCRIPTION
                "Name of an ACL group, a case-insensitive string of 1 to 63
                characters.  It must start with an English letter.
                "
            ::= { ibAclNamedGroupEntry 2 }

        ibAclNamedGroupRowStatus OBJECT-TYPE
            SYNTAX RowStatus
            MAX-ACCESS read-create
            STATUS current
            DESCRIPTION
                "RowStatus."
            ::= { ibAclNamedGroupEntry 3 }

        ibAclNamedGroupMatchOrder OBJECT-TYPE
            SYNTAX INTEGER
            {
                config(1),
                auto(2)
            }
            MAX-ACCESS read-create
            STATUS current
            DESCRIPTION
                "The match-order of name acl group."
            DEFVAL { config }
            ::= { ibAclNamedGroupEntry 4 }

       ibAclNamedGroupStep OBJECT-TYPE
            SYNTAX Integer32 (1..20)
            MAX-ACCESS read-create
            STATUS current
            DESCRIPTION
                "The numbering step of the increment of the rule index."
            DEFVAL { 5 }
            ::= { ibAclNamedGroupEntry 5 }

        ibAclNamedGroupDescription OBJECT-TYPE
            SYNTAX OCTET STRING (SIZE(0..127))
            MAX-ACCESS read-create
            STATUS current
            DESCRIPTION
                "Description of this ACL group."
            ::= { ibAclNamedGroupEntry 6 }

        ibAclNamedGroupCountClear OBJECT-TYPE
            SYNTAX CounterClear
            MAX-ACCESS read-write
            STATUS current
            DESCRIPTION
                "Reset the statistics counter of this group."
            DEFVAL { nouse }
            ::= { ibAclNamedGroupEntry 7 }

        ibAclNamedGroupRuleCounter OBJECT-TYPE
            SYNTAX Counter32
            MAX-ACCESS read-only
            STATUS current
            DESCRIPTION
                "The amount of rules of this group."
            ::= { ibAclNamedGroupEntry 8 }

--
-- Node of ibAclIPv6Group
--
        ibAclIPAclGroup OBJECT IDENTIFIER ::= { ibAclMib2Objects 2 }

--
-- Nodes of ibAclIPAclBasicTable
--

        ibAclIPAclBasicTable OBJECT-TYPE
            SYNTAX SEQUENCE OF IbAclIPAclBasicEntry
            MAX-ACCESS not-accessible
            STATUS current
            DESCRIPTION
                "A table of basic rule group.
                 If some objects of this table are not supported by some products,
                 these objects can't be created, changed or applied.
                 Default value of these objects will be returned when they are read.
                "
            ::= { ibAclIPAclGroup 2 }

        ibAclIPAclBasicEntry OBJECT-TYPE
            SYNTAX IbAclIPAclBasicEntry
            MAX-ACCESS not-accessible
            STATUS current
            DESCRIPTION
                "Basic rule group information."
            INDEX { ibAclNumberGroupType,
                    ibAclNumberGroupIndex,
                    ibAclIPAclBasicRuleIndex
                  }
            ::= { ibAclIPAclBasicTable 1 }

        IbAclIPAclBasicEntry ::=
            SEQUENCE
            {
                ibAclIPAclBasicRuleIndex
                    Integer32,
                ibAclIPAclBasicRowStatus
                    RowStatus,
                ibAclIPAclBasicAct
                    RuleAction,
                ibAclIPAclBasicSrcAddrType
                    InetAddressType,
                ibAclIPAclBasicSrcAddr
                    InetAddress,
                ibAclIPAclBasicSrcPrefix
                    InetAddressPrefixLength,
                ibAclIPAclBasicSrcAny
                    TruthValue,
                ibAclIPAclBasicSrcWild
                    IpAddress,
                ibAclIPAclBasicTimeRangeName
                    OCTET STRING,
                ibAclIPAclBasicFragmentFlag
                    FragmentFlag,
                ibAclIPAclBasicLog
                    TruthValue,
                ibAclIPAclBasicCount
                    Unsigned32,
                ibAclIPAclBasicCountClear
                    CounterClear,
                ibAclIPAclBasicEnable
                    TruthValue,
                ibAclIPAclBasicVpnInstanceName
                    OCTET STRING,
                ibAclIPAclBasicComment
                    OCTET STRING,
                ibAclIPAclBasicCounting
                    TruthValue,
                ibAclIPAclBasicRouteTypeAny
                    TruthValue,
                ibAclIPAclBasicRouteTypeValue
                    Integer32
            }

        ibAclIPAclBasicRuleIndex OBJECT-TYPE
            SYNTAX Integer32 (0..65534)
            MAX-ACCESS not-accessible
            STATUS current
            DESCRIPTION
                "The rule index of basic acl group."
            ::= { ibAclIPAclBasicEntry 1 }

        ibAclIPAclBasicRowStatus OBJECT-TYPE
            SYNTAX RowStatus
            MAX-ACCESS read-create
            STATUS current
            DESCRIPTION
                "RowStatus."
            ::= { ibAclIPAclBasicEntry 2 }

        ibAclIPAclBasicAct OBJECT-TYPE
            SYNTAX RuleAction
            MAX-ACCESS read-create
            STATUS current
            DESCRIPTION
                "The action of basic acl rule."
            ::= { ibAclIPAclBasicEntry 3 }

        ibAclIPAclBasicSrcAddrType OBJECT-TYPE
            SYNTAX InetAddressType
            MAX-ACCESS read-create
            STATUS current
            DESCRIPTION
                "The IP addresses type of IP pool."
            ::= { ibAclIPAclBasicEntry 4 }

        ibAclIPAclBasicSrcAddr OBJECT-TYPE
            SYNTAX InetAddress
            MAX-ACCESS read-create
            STATUS current
            DESCRIPTION
                "The value of a local IP address is available for this association.

                 The type of this address is determined by the value of
                 ibAclIPAclBasicSrcAddrType.
                "
            ::= { ibAclIPAclBasicEntry 5 }

        ibAclIPAclBasicSrcPrefix OBJECT-TYPE
            SYNTAX InetAddressPrefixLength
            MAX-ACCESS read-create
            STATUS current
            DESCRIPTION
                "Denotes the length of a generic Internet network address prefix.
                 A value of n corresponds to an IP address mask
                 that has n contiguous 1-bits from the most significant bit (MSB)
                 and all other bits set to 0.
                "
            ::= { ibAclIPAclBasicEntry 6 }

        ibAclIPAclBasicSrcAny OBJECT-TYPE
            SYNTAX TruthValue
            MAX-ACCESS read-create
            STATUS current
            DESCRIPTION
                "The flag of matching any IP address."
            DEFVAL { true }
            ::= { ibAclIPAclBasicEntry 7 }

        ibAclIPAclBasicSrcWild OBJECT-TYPE
            SYNTAX IpAddress
            MAX-ACCESS read-create
            STATUS current
            DESCRIPTION
                "Source IPv4 address wildcard mask.
                 Only IPv4 Basic Rule supports this object.
                 Default value is '0.0.0.0'.
                "
            ::= { ibAclIPAclBasicEntry 8 }

        ibAclIPAclBasicTimeRangeName OBJECT-TYPE
            SYNTAX OCTET STRING (SIZE(0..32))
            MAX-ACCESS read-create
            STATUS current
            DESCRIPTION
                "The Time-range of basic acl rule.
                 Default value is zero-length.
                "
            ::= { ibAclIPAclBasicEntry 9 }

        ibAclIPAclBasicFragmentFlag OBJECT-TYPE
            SYNTAX FragmentFlag
            MAX-ACCESS read-create
            STATUS current
            DESCRIPTION
                "The flag of matching fragmented packets."
            DEFVAL { invalid }
            ::= { ibAclIPAclBasicEntry 10 }

        ibAclIPAclBasicLog OBJECT-TYPE
            SYNTAX TruthValue
            MAX-ACCESS read-create
            STATUS current
            DESCRIPTION
                "The packet will be logged when it matches the rule."
            DEFVAL { false }
            ::= { ibAclIPAclBasicEntry 11 }

        ibAclIPAclBasicCount OBJECT-TYPE
            SYNTAX Unsigned32
            MAX-ACCESS read-only
            STATUS current
            DESCRIPTION
                "The count of matches by the rule."
            ::= { ibAclIPAclBasicEntry 12 }

        ibAclIPAclBasicCountClear OBJECT-TYPE
            SYNTAX CounterClear
            MAX-ACCESS read-write
            STATUS current
            DESCRIPTION
                "Reset the value of counter."
            DEFVAL { nouse }
            ::= { ibAclIPAclBasicEntry 13 }

        ibAclIPAclBasicEnable OBJECT-TYPE
            SYNTAX TruthValue
            MAX-ACCESS read-only
            STATUS current
            DESCRIPTION
                "The rule is active or not.
                 true : active
                 false : inactive
                "
            DEFVAL { false }
            ::= { ibAclIPAclBasicEntry 14 }

        ibAclIPAclBasicVpnInstanceName OBJECT-TYPE
            SYNTAX OCTET STRING (SIZE(0..32))
            MAX-ACCESS read-create
            STATUS current
            DESCRIPTION
                "The VPN name, to which the rule will be applied.
                 Default value is zero-length.
                "
            ::= { ibAclIPAclBasicEntry 15 }

        ibAclIPAclBasicComment OBJECT-TYPE
            SYNTAX OCTET STRING (SIZE(0..127))
            MAX-ACCESS read-create
            STATUS current
            DESCRIPTION
                "The description of ACL rule.
                 Default value is Zero-length String.
                "
            ::= { ibAclIPAclBasicEntry 16 }

        ibAclIPAclBasicCounting OBJECT-TYPE
            SYNTAX TruthValue
            MAX-ACCESS read-create
            STATUS current
            DESCRIPTION
                "The packet will be counted when it matches the rule.
                 It is disabled by default.
                "
            DEFVAL { false }
            ::= { ibAclIPAclBasicEntry 17 }

        ibAclIPAclBasicRouteTypeAny OBJECT-TYPE
            SYNTAX TruthValue
            MAX-ACCESS read-create
            STATUS current
            DESCRIPTION
                "The flag of matching any type of routing header of IPv6 packet.
                "
            DEFVAL { false }
            ::= { ibAclIPAclBasicEntry 18 }

        ibAclIPAclBasicRouteTypeValue OBJECT-TYPE
            SYNTAX Integer32 (0..255|65535)
            MAX-ACCESS read-create
            STATUS current
            DESCRIPTION
                "Match specific type of routing header of IPv6 packet."
            DEFVAL { 65535 }
            ::= { ibAclIPAclBasicEntry 19 }

--
-- Notes of ibAclIPAclAdvancedTable
--
        ibAclIPAclAdvancedTable OBJECT-TYPE
            SYNTAX SEQUENCE OF IbAclIPAclAdvancedEntry
            MAX-ACCESS not-accessible
            STATUS current
            DESCRIPTION
                "A table of advanced and simple acl group.
                 If some objects of this table are not supported by some products,
                 these objects can't be created, changed and applied.
                 Default value of these objects will be returned when they are read.
                "
            ::= { ibAclIPAclGroup 3 }

        ibAclIPAclAdvancedEntry OBJECT-TYPE
            SYNTAX IbAclIPAclAdvancedEntry
            MAX-ACCESS not-accessible
            STATUS current
            DESCRIPTION
                "Advanced acl group information."
            INDEX { ibAclNumberGroupType,
                    ibAclNumberGroupIndex,
                    ibAclIPAclAdvancedRuleIndex
                  }
            ::= { ibAclIPAclAdvancedTable 1  }

        IbAclIPAclAdvancedEntry ::=
            SEQUENCE
            {
                ibAclIPAclAdvancedRuleIndex
                    Integer32,
                ibAclIPAclAdvancedRowStatus
                    RowStatus,
                ibAclIPAclAdvancedAct
                    RuleAction,
                ibAclIPAclAdvancedProtocol
                    Integer32,
                ibAclIPAclAdvancedAddrFlag
                    AddressFlag,
                ibAclIPAclAdvancedSrcAddrType
                    InetAddressType,
                ibAclIPAclAdvancedSrcAddr
                    InetAddress,
                ibAclIPAclAdvancedSrcPrefix
                    InetAddressPrefixLength,
                ibAclIPAclAdvancedSrcAny
                    TruthValue,
                ibAclIPAclAdvancedSrcWild
                    IpAddress,
                ibAclIPAclAdvancedSrcOp
                    PortOp,
                ibAclIPAclAdvancedSrcPort1
                    Integer32,
                ibAclIPAclAdvancedSrcPort2
                    Integer32,
                ibAclIPAclAdvancedDestAddrType
                    InetAddressType,
                ibAclIPAclAdvancedDestAddr
                    InetAddress,
                ibAclIPAclAdvancedDestPrefix
                    InetAddressPrefixLength,
                ibAclIPAclAdvancedDestAny
                    TruthValue,
                ibAclIPAclAdvancedDestWild
                    IpAddress,
                ibAclIPAclAdvancedDestOp
                    PortOp,
                ibAclIPAclAdvancedDestPort1
                    Integer32,
                ibAclIPAclAdvancedDestPort2
                    Integer32,
                ibAclIPAclAdvancedIcmpType
                    Integer32,
                ibAclIPAclAdvancedIcmpCode
                    Integer32,
                ibAclIPAclAdvancedPrecedence
                    Integer32,
                ibAclIPAclAdvancedTos
                    Integer32,
                ibAclIPAclAdvancedDscp
                    DSCPValue,
                ibAclIPAclAdvancedTimeRangeName
                    OCTET STRING,
                ibAclIPAclAdvancedTCPFlag
                    TCPFlag,
                ibAclIPAclAdvancedFragmentFlag
                    FragmentFlag,
                ibAclIPAclAdvancedLog
                    TruthValue,
                ibAclIPAclAdvancedCount
                    Unsigned32,
                ibAclIPAclAdvancedCountClear
                    CounterClear,
                ibAclIPAclAdvancedEnable
                    TruthValue,
                ibAclIPAclAdvancedVpnInstanceName
                    OCTET STRING,
                ibAclIPAclAdvancedComment
                    OCTET STRING,
                ibAclIPAclAdvancedReflective
                    TruthValue,
                ibAclIPAclAdvancedCounting
                    TruthValue,
                ibAclIPAclAdvancedTCPFlagMask
                    BITS,
                ibAclIPAclAdvancedTCPFlagValue
                    BITS,
                ibAclIPAclAdvancedRouteTypeAny
                    TruthValue,
                ibAclIPAclAdvancedRouteTypeValue
                    Integer32,
                ibAclIPAclAdvancedFlowLabel
                    Unsigned32,
                ibAclIPAclAdvancedSrcSuffix
                    Unsigned32,
                ibAclIPAclAdvancedDestSuffix
                    Unsigned32
            }

        ibAclIPAclAdvancedRuleIndex OBJECT-TYPE
            SYNTAX Integer32 (0..65534)
            MAX-ACCESS not-accessible
            STATUS current
            DESCRIPTION
                "The rule index of advanced acl group.
                 As a Simple ACL group, the value of this object must be 0.
                 As an Advanced ACL group, the value of this object is ranging
                 from 0 to 65534.
                "
            ::= { ibAclIPAclAdvancedEntry 1 }

        ibAclIPAclAdvancedRowStatus OBJECT-TYPE
            SYNTAX RowStatus
            MAX-ACCESS read-create
            STATUS current
            DESCRIPTION
                "RowStatus."
            ::= { ibAclIPAclAdvancedEntry 2 }

        ibAclIPAclAdvancedAct OBJECT-TYPE
            SYNTAX RuleAction
            MAX-ACCESS read-create
            STATUS current
            DESCRIPTION
                "The action of advanced acl rule."
            ::= { ibAclIPAclAdvancedEntry 3 }

        ibAclIPAclAdvancedProtocol OBJECT-TYPE
            SYNTAX Integer32 (0..255)
            MAX-ACCESS read-create
            STATUS current
            DESCRIPTION
                "The protocol-type of advanced acl group.  0 indicates any IPv4 or
                IPv6 protocol.
                  <1-255>  Protocol number
                  gre      GRE tunneling(47)
                  icmp     Internet Control Message Protocol(1)
                  icmpv6   Internet Control Message Protocol6(58)
                  igmp     Internet Group Management Protocol(2)
                  ipinip   IP in IP tunneling(4)
                  ospf     OSPF routing protocol(89)
                  tcp      Transmission Control Protocol (6)
                  udp      User Datagram Protocol (17)
                  ipv6-ah  IPv6 Authentication Header(51)
                  ipv6-esp IPv6 Encapsulating Security Payload(50)
                "
            ::= { ibAclIPAclAdvancedEntry 4 }

        ibAclIPAclAdvancedAddrFlag OBJECT-TYPE
            SYNTAX AddressFlag
            MAX-ACCESS read-create
            STATUS current
            DESCRIPTION
                "Address flag to select address."
            DEFVAL { invalid }
            ::= { ibAclIPAclAdvancedEntry 5 }

        ibAclIPAclAdvancedSrcAddrType OBJECT-TYPE
            SYNTAX InetAddressType
            MAX-ACCESS read-create
            STATUS current
            DESCRIPTION
                "The IP addresses type of IP pool."
            ::= { ibAclIPAclAdvancedEntry 6 }

        ibAclIPAclAdvancedSrcAddr OBJECT-TYPE
            SYNTAX InetAddress
            MAX-ACCESS read-create
            STATUS current
            DESCRIPTION
                "The value of a local IP address available for this association.

                 The type of this address is determined by the value of
                 ibAclIPAclAdvancedSrcAddrType.
                "
            ::= { ibAclIPAclAdvancedEntry 7 }

        ibAclIPAclAdvancedSrcPrefix OBJECT-TYPE
            SYNTAX InetAddressPrefixLength
            MAX-ACCESS read-create
            STATUS current
            DESCRIPTION
                "Denotes the length of a generic Internet network address prefix.
                 A value of n corresponds to an IP address mask
                 which has n contiguous 1-bits from the most significant bit (MSB)
                 and all other bits set to 0.
                "
            ::= { ibAclIPAclAdvancedEntry 8 }

        ibAclIPAclAdvancedSrcAny OBJECT-TYPE
            SYNTAX TruthValue
            MAX-ACCESS read-create
            STATUS current
            DESCRIPTION
                "The flag of matching any IP address."
            DEFVAL { true }
            ::= { ibAclIPAclAdvancedEntry 9 }

        ibAclIPAclAdvancedSrcWild OBJECT-TYPE
            SYNTAX IpAddress
            MAX-ACCESS read-create
            STATUS current
            DESCRIPTION
                "Source IPv4 address wildcard mask.
                 Only IPv4 Advanced Rule supports this object.
                 Default value is '0.0.0.0'.
                "
            ::= { ibAclIPAclAdvancedEntry 10 }

        ibAclIPAclAdvancedSrcOp OBJECT-TYPE
            SYNTAX PortOp
            MAX-ACCESS read-create
            STATUS current
            DESCRIPTION
                "Source port operation symbol of advanced acl group."
            DEFVAL { invalid }
            ::= { ibAclIPAclAdvancedEntry 11 }

        ibAclIPAclAdvancedSrcPort1 OBJECT-TYPE
            SYNTAX Integer32 (0..65535)
            MAX-ACCESS read-create
            STATUS current
            DESCRIPTION
                "The fourth layer source port1."
            DEFVAL { 0 }
            ::= { ibAclIPAclAdvancedEntry 12 }

        ibAclIPAclAdvancedSrcPort2 OBJECT-TYPE
            SYNTAX Integer32 (0..65535)
            MAX-ACCESS read-create
            STATUS current
            DESCRIPTION
                "The fourth layer source port2."
            DEFVAL { 65535 }
            ::= { ibAclIPAclAdvancedEntry 13 }

        ibAclIPAclAdvancedDestAddrType OBJECT-TYPE
            SYNTAX InetAddressType
            MAX-ACCESS read-create
            STATUS current
            DESCRIPTION
                "The IP addresses type of IP pool."
            ::= { ibAclIPAclAdvancedEntry 14 }

        ibAclIPAclAdvancedDestAddr OBJECT-TYPE
            SYNTAX InetAddress
            MAX-ACCESS read-create
            STATUS current
            DESCRIPTION
                "The value of a local IP address available for this association.

                 The type of this address is determined by the value of
                 ibAclIPAclAdvancedDestAddrType.
                "
            ::= { ibAclIPAclAdvancedEntry 15 }

        ibAclIPAclAdvancedDestPrefix OBJECT-TYPE
            SYNTAX InetAddressPrefixLength
            MAX-ACCESS read-create
            STATUS current
            DESCRIPTION
                "Denotes the length of a generic Internet network address prefix.
                 A value of n corresponds to an IP address mask
                 which has n contiguous 1-bits from the most significant bit (MSB)
                 and all other bits set to 0.
                "
            ::= { ibAclIPAclAdvancedEntry 16 }

        ibAclIPAclAdvancedDestAny OBJECT-TYPE
            SYNTAX TruthValue
            MAX-ACCESS read-create
            STATUS current
            DESCRIPTION
                "The flag of matching any IP address."
            DEFVAL { true }
            ::= { ibAclIPAclAdvancedEntry 17 }

        ibAclIPAclAdvancedDestWild OBJECT-TYPE
            SYNTAX IpAddress
            MAX-ACCESS read-create
            STATUS current
            DESCRIPTION
                "Destination IPv4 address wildcard mask.
                 Only IPv4 Advanced Rule supports this object.
                 Default value is '0.0.0.0'.
                "
            ::= { ibAclIPAclAdvancedEntry 18 }

        ibAclIPAclAdvancedDestOp OBJECT-TYPE
            SYNTAX PortOp
            MAX-ACCESS read-create
            STATUS current
            DESCRIPTION
                "Destination port operation symbol of advanced acl group."
            DEFVAL { invalid }
            ::= { ibAclIPAclAdvancedEntry 19 }

        ibAclIPAclAdvancedDestPort1 OBJECT-TYPE
            SYNTAX Integer32 (0..65535)
            MAX-ACCESS read-create
            STATUS current
            DESCRIPTION
                "The fourth layer destination port1."
            DEFVAL { 0 }
            ::= { ibAclIPAclAdvancedEntry 20 }

        ibAclIPAclAdvancedDestPort2 OBJECT-TYPE
            SYNTAX Integer32 (0..65535)
            MAX-ACCESS read-create
            STATUS current
            DESCRIPTION
                "The fourth layer destination port2."
            DEFVAL { 65535 }
            ::= { ibAclIPAclAdvancedEntry 21 }

        ibAclIPAclAdvancedIcmpType OBJECT-TYPE
            SYNTAX Integer32 (0..255|65535)
            MAX-ACCESS read-create
            STATUS current
            DESCRIPTION
                "The type of ICMP packet."
            DEFVAL { 65535 }
            ::= { ibAclIPAclAdvancedEntry 22 }

        ibAclIPAclAdvancedIcmpCode OBJECT-TYPE
            SYNTAX Integer32 (0..255|65535)
            MAX-ACCESS read-create
            STATUS current
            DESCRIPTION
                "The code of ICMP packet."
            DEFVAL { 65535 }
            ::= { ibAclIPAclAdvancedEntry 23 }

        ibAclIPAclAdvancedPrecedence OBJECT-TYPE
            SYNTAX Integer32 (0..7|255)
            MAX-ACCESS read-create
            STATUS current
            DESCRIPTION
                "The value of IP-packet's precedence.
                <0-7>           Value of precedence
                routine         Specify routine precedence(0)
                priority        Specify priority precedence(1)
                immediate       Specify immediate precedence(2)
                flash           Specify flash precedence(3)
                flash-override  Specify flash-override precedence(4)
                critical        Specify critical precedence(5)
                internet        Specify internetwork control precedence(6)
                network         Specify network control precedence(7)
                "
            DEFVAL { 255 }
            ::= { ibAclIPAclAdvancedEntry 24 }

        ibAclIPAclAdvancedTos OBJECT-TYPE
            SYNTAX Integer32 (0..15|255)
            MAX-ACCESS read-create
            STATUS current
            DESCRIPTION
                "The value of IP-packet's TOS.
                  <0-15>             Value of TOS(type of service)
                  max-reliability    Match packets with max reliable TOS(2)
                  max-throughput     Match packets with max throughput TOS(4)
                  min-delay          Match packets with min delay TOS(8)
                  min-monetary-cost  Match packets with min monetary cost TOS(1)
                  normal             Match packets with normal TOS(0)
                "
            DEFVAL { 255 }
            ::= { ibAclIPAclAdvancedEntry 25 }

        ibAclIPAclAdvancedDscp OBJECT-TYPE
            SYNTAX DSCPValue
            MAX-ACCESS read-create
            STATUS current
            DESCRIPTION
                "The value of DSCP of IP packet."
            DEFVAL { 255 }
            ::= { ibAclIPAclAdvancedEntry 26 }

        ibAclIPAclAdvancedTimeRangeName OBJECT-TYPE
            SYNTAX OCTET STRING (SIZE(0..32))
            MAX-ACCESS read-create
            STATUS current
            DESCRIPTION
                "The Time-range of advanced acl rule.
                 Default value is zero-length.
                "
            ::= { ibAclIPAclAdvancedEntry 27 }

        ibAclIPAclAdvancedTCPFlag OBJECT-TYPE
            SYNTAX TCPFlag
            MAX-ACCESS read-create
            STATUS current
            DESCRIPTION
                "The packet type of TCP protocol."
            DEFVAL { invalid }
            ::= { ibAclIPAclAdvancedEntry 28 }

        ibAclIPAclAdvancedFragmentFlag OBJECT-TYPE
            SYNTAX FragmentFlag
            MAX-ACCESS read-create
            STATUS current
            DESCRIPTION
                "The flag of matching fragmented packet,
                 and now support two value: 0 or 2."
            DEFVAL { invalid }
            ::= { ibAclIPAclAdvancedEntry 29 }

        ibAclIPAclAdvancedLog OBJECT-TYPE
            SYNTAX TruthValue
            MAX-ACCESS read-create
            STATUS current
            DESCRIPTION
                "Log matched packets."
            DEFVAL { false }
            ::= { ibAclIPAclAdvancedEntry 30 }

        ibAclIPAclAdvancedCount OBJECT-TYPE
            SYNTAX Unsigned32
            MAX-ACCESS read-only
            STATUS current
            DESCRIPTION
                "The count of matched by the rule."
            ::= { ibAclIPAclAdvancedEntry 31 }

        ibAclIPAclAdvancedCountClear OBJECT-TYPE
            SYNTAX CounterClear
            MAX-ACCESS read-write
            STATUS current
            DESCRIPTION
                "Reset the value of counter."
            DEFVAL { nouse }
            ::= { ibAclIPAclAdvancedEntry 32 }

        ibAclIPAclAdvancedEnable OBJECT-TYPE
            SYNTAX TruthValue
            MAX-ACCESS read-only
            STATUS current
            DESCRIPTION
                "The rule is active or not.
                 true : active
                 false : inactive
                "
            DEFVAL { false }
            ::= { ibAclIPAclAdvancedEntry 33 }

        ibAclIPAclAdvancedVpnInstanceName OBJECT-TYPE
            SYNTAX OCTET STRING (SIZE(0..32))
            MAX-ACCESS read-create
            STATUS current
            DESCRIPTION
                "The VPN name that the rule will be applied.
                 Default value is zero-length.
                "
            ::= { ibAclIPAclAdvancedEntry 34 }

        ibAclIPAclAdvancedComment OBJECT-TYPE
            SYNTAX OCTET STRING (SIZE(0..127))
            MAX-ACCESS read-create
            STATUS current
            DESCRIPTION
                "The description of ACL rule.
                 Default value is Zero-length String.
                "
            ::= { ibAclIPAclAdvancedEntry 35 }

        ibAclIPAclAdvancedReflective OBJECT-TYPE
            SYNTAX TruthValue
            MAX-ACCESS read-create
            STATUS current
            DESCRIPTION
                "The flag of reflective."
            ::= { ibAclIPAclAdvancedEntry 36 }

        ibAclIPAclAdvancedCounting OBJECT-TYPE
            SYNTAX TruthValue
            MAX-ACCESS read-create
            STATUS current
            DESCRIPTION
                "The packet will be counted when it matches the rule.
                 It is disabled by default.
                "
            DEFVAL { false }
            ::= { ibAclIPAclAdvancedEntry 37 }

        ibAclIPAclAdvancedTCPFlagMask OBJECT-TYPE
            SYNTAX BITS {
                           tcpack(0),
                           tcpfin(1),
                           tcppsh(2),
                           tcprst(3),
                           tcpsyn(4),
                           tcpurg(5)
                        }
            MAX-ACCESS read-create
            STATUS current
            DESCRIPTION
                "The TCP Flag Mask.  This is a bit-map of possible conditions.
                The various bit positions are:
                |0        |tcpack                 |
                |1        |tcpfin                 |
                |2        |tcppsh                 |
                |3        |tcprst                 |
                |4        |tcpsyn                 |
                |5        |tcpurg                 |
                "
            DEFVAL { { } }
            ::= { ibAclIPAclAdvancedEntry 38 }

        ibAclIPAclAdvancedTCPFlagValue OBJECT-TYPE
            SYNTAX BITS {
                           tcpack(0),
                           tcpfin(1),
                           tcppsh(2),
                           tcprst(3),
                           tcpsyn(4),
                           tcpurg(5)
                        }
            MAX-ACCESS read-create
            STATUS current
            DESCRIPTION
                "The TCP Flag Value.  This is a bit-map of possible conditions.
                The various bit positions are:
                |0        |tcpack                 |
                |1        |tcpfin                 |
                |2        |tcppsh                 |
                |3        |tcprst                 |
                |4        |tcpsyn                 |
                |5        |tcpurg                 |
                "
            DEFVAL { { } }
            ::= { ibAclIPAclAdvancedEntry 39 }

        ibAclIPAclAdvancedRouteTypeAny OBJECT-TYPE
            SYNTAX TruthValue
            MAX-ACCESS read-create
            STATUS current
            DESCRIPTION
                "The flag of matching any type of routing header of IPv6 packet.
                "
            DEFVAL { false }
            ::= { ibAclIPAclAdvancedEntry 40 }

        ibAclIPAclAdvancedRouteTypeValue OBJECT-TYPE
            SYNTAX Integer32 (0..255|65535)
            MAX-ACCESS read-create
            STATUS current
            DESCRIPTION
                "The type of routing header of IPv6 packet."
            DEFVAL { 65535 }
            ::= { ibAclIPAclAdvancedEntry 41 }

        ibAclIPAclAdvancedFlowLabel OBJECT-TYPE
            SYNTAX Unsigned32 (0..1048575|4294967295)
            MAX-ACCESS read-create
            STATUS current
            DESCRIPTION
                "The value of flow label of IPv6 packet header."
            DEFVAL { 4294967295 }
            ::= { ibAclIPAclAdvancedEntry 42 }

        ibAclIPAclAdvancedSrcSuffix OBJECT-TYPE
            SYNTAX Unsigned32
            MAX-ACCESS read-create
            STATUS current
            DESCRIPTION
                "Denotes the length of a generic Internet network address suffix.
                 A value of n corresponds to an IP address mask
                 that has n contiguous 1-bits from the least significant bit
                 and all other bits set to 0.
                "
            ::= { ibAclIPAclAdvancedEntry 43 }

        ibAclIPAclAdvancedDestSuffix OBJECT-TYPE
            SYNTAX Unsigned32
            MAX-ACCESS read-create
            STATUS current
            DESCRIPTION
                "Denotes the length of a generic Internet network address suffix.
                 A value of n corresponds to an IP address mask
                 that has n contiguous 1-bits from the least significant bit
                 and all other bits set to 0.
                "
            ::= { ibAclIPAclAdvancedEntry 44 }

--
--Nodes of ibAclIPAclNamedBscTable
--

        ibAclIPAclNamedBscTable OBJECT-TYPE
            SYNTAX SEQUENCE OF IbAclIPAclNamedBscEntry
            MAX-ACCESS not-accessible
            STATUS current
            DESCRIPTION
                "A table of basic rule of named ACL.
                 The name of ACL group will be used as an index in this table,
                 which differs from the table ibAclIPAclBasicTable.
                 If some objects of this table are not supported by some
                 products, these objects can't be created, changed or applied.
                 Default value of these objects will be returned when they are
                 read.
                "
            ::= { ibAclIPAclGroup 4 }

        ibAclIPAclNamedBscEntry OBJECT-TYPE
            SYNTAX IbAclIPAclNamedBscEntry
            MAX-ACCESS not-accessible
            STATUS current
            DESCRIPTION
                "Basic named ACL rule entry."
            INDEX
            {
                ibAclNumberGroupType,
                ibAclNamedGroupName,
                ibAclIPAclBasicRuleIndex
            }
            ::= { ibAclIPAclNamedBscTable 1 }

        IbAclIPAclNamedBscEntry ::=
            SEQUENCE
            {
                ibAclIPAclNamedBscRowStatus
                    RowStatus,
                ibAclIPAclNamedBscAct
                    RuleAction,
                ibAclIPAclNamedBscSrcAddrType
                    InetAddressType,
                ibAclIPAclNamedBscSrcAddr
                    InetAddress,
                ibAclIPAclNamedBscSrcPrefix
                    InetAddressPrefixLength,
                ibAclIPAclNamedBscSrcAny
                    TruthValue,
                ibAclIPAclNamedBscSrcWild
                    IpAddress,
                ibAclIPAclNamedBscTRangeName
                    OCTET STRING,
                ibAclIPAclNamedBscFragmentFlag
                    FragmentFlag,
                ibAclIPAclNamedBscLog
                    TruthValue,
                ibAclIPAclNamedBscCount
                    Unsigned32,
                ibAclIPAclNamedBscCountClear
                    CounterClear,
                ibAclIPAclNamedBscEnable
                    TruthValue,
                ibAclIPAclNamedBscVpnInstName
                    OCTET STRING,
                ibAclIPAclNamedBscComment
                    OCTET STRING,
                ibAclIPAclNamedBscCounting
                    TruthValue,
                ibAclIPAclNamedBscRouteTypeAny
                    TruthValue,
                ibAclIPAclNamedBscRouteTypeValue
                    Integer32
            }

        ibAclIPAclNamedBscRowStatus OBJECT-TYPE
            SYNTAX RowStatus
            MAX-ACCESS read-create
            STATUS current
            DESCRIPTION
                "RowStatus."
            ::= { ibAclIPAclNamedBscEntry 1 }

        ibAclIPAclNamedBscAct OBJECT-TYPE
            SYNTAX RuleAction
            MAX-ACCESS read-create
            STATUS current
            DESCRIPTION
                "The action of basic ACL rule."
            ::= { ibAclIPAclNamedBscEntry 2 }

        ibAclIPAclNamedBscSrcAddrType OBJECT-TYPE
            SYNTAX InetAddressType
            MAX-ACCESS read-create
            STATUS current
            DESCRIPTION
                "The IP addresses type of IP pool."
            ::= { ibAclIPAclNamedBscEntry 3 }

        ibAclIPAclNamedBscSrcAddr OBJECT-TYPE
            SYNTAX InetAddress
            MAX-ACCESS read-create
            STATUS current
            DESCRIPTION
                "The specified source IP address.
                 The type of this address is determined by the value of
                 ibAclIPAclNamedBscSrcAddrType.
                "
            ::= { ibAclIPAclNamedBscEntry 4 }

        ibAclIPAclNamedBscSrcPrefix OBJECT-TYPE
            SYNTAX InetAddressPrefixLength
            MAX-ACCESS read-create
            STATUS current
            DESCRIPTION
                "Specify the length of a generic Internet network address
                 prefix.  A value of n corresponds to an IP address mask that
                 has n contiguous 1-bits from the most significant bit (MSB)
                 and all other bits set to 0.
                "
            ::= { ibAclIPAclNamedBscEntry 5 }

        ibAclIPAclNamedBscSrcAny OBJECT-TYPE
            SYNTAX TruthValue
            MAX-ACCESS read-create
            STATUS current
            DESCRIPTION
                "The flag of matching any source IP address."
            DEFVAL { true }
            ::= { ibAclIPAclNamedBscEntry 6 }

        ibAclIPAclNamedBscSrcWild OBJECT-TYPE
            SYNTAX IpAddress
            MAX-ACCESS read-create
            STATUS current
            DESCRIPTION
                "Source IPv4 address wildcard mask.
                 Only IPv4 Basic Rule supports this object.
                 Default value is '0.0.0.0'.
                "
            ::= { ibAclIPAclNamedBscEntry 7 }

       ibAclIPAclNamedBscTRangeName OBJECT-TYPE
            SYNTAX OCTET STRING (SIZE(0..32))
            MAX-ACCESS read-create
            STATUS current
            DESCRIPTION
                "The Time-range of basic acl rule.
                 Default value is zero-length.
                "
            ::= { ibAclIPAclNamedBscEntry 8 }

        ibAclIPAclNamedBscFragmentFlag OBJECT-TYPE
            SYNTAX FragmentFlag
            MAX-ACCESS read-create
            STATUS current
            DESCRIPTION
                "The flag of matching fragmented packets."
            DEFVAL { invalid }
            ::= { ibAclIPAclNamedBscEntry 9 }

        ibAclIPAclNamedBscLog OBJECT-TYPE
            SYNTAX TruthValue
            MAX-ACCESS read-create
            STATUS current
            DESCRIPTION
                "The packet will be logged when it matches the rule."
            DEFVAL { false }
            ::= { ibAclIPAclNamedBscEntry 10 }

        ibAclIPAclNamedBscCount OBJECT-TYPE
            SYNTAX Unsigned32
            MAX-ACCESS read-only
            STATUS current
            DESCRIPTION
                "The count of matches by the rule."
            ::= { ibAclIPAclNamedBscEntry 11 }

        ibAclIPAclNamedBscCountClear OBJECT-TYPE
            SYNTAX CounterClear
            MAX-ACCESS read-write
            STATUS current
            DESCRIPTION
                "Reset the statistics counter of the rule."
            DEFVAL { nouse }
            ::= { ibAclIPAclNamedBscEntry 12 }

        ibAclIPAclNamedBscEnable OBJECT-TYPE
            SYNTAX TruthValue
            MAX-ACCESS read-only
            STATUS current
            DESCRIPTION
                "The rule is active or not.
                 true : active
                 false : inactive
                "
            DEFVAL { false }
            ::= { ibAclIPAclNamedBscEntry 13 }

        ibAclIPAclNamedBscVpnInstName OBJECT-TYPE
            SYNTAX OCTET STRING (SIZE(0..32))
            MAX-ACCESS read-create
            STATUS current
            DESCRIPTION
                "The VPN name, to which the rule will be applied.
                 Default value is zero-length.
                "
            ::= { ibAclIPAclNamedBscEntry 14 }

        ibAclIPAclNamedBscComment OBJECT-TYPE
            SYNTAX OCTET STRING (SIZE(0..127))
            MAX-ACCESS read-create
            STATUS current
            DESCRIPTION
                "The description of ACL rule.
                 Default value is Zero-length String.
                "
            ::= { ibAclIPAclNamedBscEntry 15 }

        ibAclIPAclNamedBscCounting OBJECT-TYPE
            SYNTAX TruthValue
            MAX-ACCESS read-create
            STATUS current
            DESCRIPTION
                "The packet will be counted when it matches the rule.
                 It is disabled by default.
                "
            DEFVAL { false }
            ::= { ibAclIPAclNamedBscEntry 16 }

        ibAclIPAclNamedBscRouteTypeAny OBJECT-TYPE
            SYNTAX TruthValue
            MAX-ACCESS read-create
            STATUS current
            DESCRIPTION
                "The flag of matching any type of routing header of IPv6 packet.
                "
            DEFVAL { false }
            ::= { ibAclIPAclNamedBscEntry 17 }

        ibAclIPAclNamedBscRouteTypeValue OBJECT-TYPE
            SYNTAX Integer32 (0..255|65535)
            MAX-ACCESS read-create
            STATUS current
            DESCRIPTION
                "Value of the routing header type of IPv6 packet,
                in the range of 0 to 255.
                "
            DEFVAL { 65535 }
            ::= { ibAclIPAclNamedBscEntry 18 }

--
-- Notes of ibAclIPAclNamedAdvTable
--
        ibAclIPAclNamedAdvTable OBJECT-TYPE
            SYNTAX SEQUENCE OF IbAclIPAclNamedAdvEntry
            MAX-ACCESS not-accessible
            STATUS current
            DESCRIPTION
                "A table of advanced rule of named ACL.
                 The name of ACL group will be used as an index in this table,
                 which differs from the table ibAclIPAclAdvancedTable.
                 If some objects of this table are not supported by some
                 products, these objects can't be created, changed or applied.
                 Default value of these objects will be returned when they are
                 read.
                "
            ::= { ibAclIPAclGroup 5 }

        ibAclIPAclNamedAdvEntry OBJECT-TYPE
            SYNTAX IbAclIPAclNamedAdvEntry
            MAX-ACCESS not-accessible
            STATUS current
            DESCRIPTION
                "Advanced ACL rule information entry."
            INDEX
            {
                ibAclNumberGroupType,
                ibAclNamedGroupName,
                ibAclIPAclAdvancedRuleIndex
            }
            ::= { ibAclIPAclNamedAdvTable 1 }

        IbAclIPAclNamedAdvEntry ::=
            SEQUENCE
            {
                ibAclIPAclNamedAdvRowStatus
                    RowStatus,
                ibAclIPAclNamedAdvAct
                    RuleAction,
                ibAclIPAclNamedAdvProtocol
                    Integer32,
                ibAclIPAclNamedAdvAddrFlag
                    AddressFlag,
                ibAclIPAclNamedAdvSrcAddrType
                    InetAddressType,
                ibAclIPAclNamedAdvSrcAddr
                    InetAddress,
                ibAclIPAclNamedAdvSrcPrefix
                    InetAddressPrefixLength,
                ibAclIPAclNamedAdvSrcAny
                    TruthValue,
                ibAclIPAclNamedAdvSrcWild
                    IpAddress,
                ibAclIPAclNamedAdvSrcOp
                    PortOp,
                ibAclIPAclNamedAdvSrcPort1
                    Integer32,
                ibAclIPAclNamedAdvSrcPort2
                    Integer32,
                ibAclIPAclNamedAdvDstAddrType
                    InetAddressType,
                ibAclIPAclNamedAdvDstAddr
                    InetAddress,
                ibAclIPAclNamedAdvDstPrefix
                    InetAddressPrefixLength,
                ibAclIPAclNamedAdvDstAny
                    TruthValue,
                ibAclIPAclNamedAdvDstWild
                    IpAddress,
                ibAclIPAclNamedAdvDstOp
                    PortOp,
                ibAclIPAclNamedAdvDstPort1
                    Integer32,
                ibAclIPAclNamedAdvDstPort2
                    Integer32,
                ibAclIPAclNamedAdvIcmpType
                    Integer32,
                ibAclIPAclNamedAdvIcmpCode
                    Integer32,
                ibAclIPAclNamedAdvPrecedence
                    Integer32,
                ibAclIPAclNamedAdvTos
                    Integer32,
                ibAclIPAclNamedAdvDscp
                    DSCPValue,
                ibAclIPAclNamedAdvTRangeName
                    OCTET STRING,
                ibAclIPAclNamedAdvTCPFlag
                    TCPFlag,
                ibAclIPAclNamedAdvFragmentFlag
                    FragmentFlag,
                ibAclIPAclNamedAdvLog
                    TruthValue,
                ibAclIPAclNamedAdvCount
                    Unsigned32,
                ibAclIPAclNamedAdvCountClear
                    CounterClear,
                ibAclIPAclNamedAdvEnable
                    TruthValue,
                ibAclIPAclNamedAdvVpnInstName
                    OCTET STRING,
                ibAclIPAclNamedAdvComment
                    OCTET STRING,
                ibAclIPAclNamedAdvReflective
                    TruthValue,
                ibAclIPAclNamedAdvCounting
                    TruthValue,
                ibAclIPAclNamedAdvTCPFlagMask
                    BITS,
                ibAclIPAclNamedAdvTCPFlagValue
                    BITS,
                ibAclIPAclNamedAdvRouteTypeAny
                    TruthValue,
                ibAclIPAclNamedAdvRouteTypeValue
                    Integer32,
                ibAclIPAclNamedAdvFlowLabel
                    Unsigned32,
                ibAclIPAclNamedAdvSrcSuffix
                    Unsigned32,
                ibAclIPAclNamedAdvDstSuffix
                    Unsigned32
            }

        ibAclIPAclNamedAdvRowStatus OBJECT-TYPE
            SYNTAX RowStatus
            MAX-ACCESS read-create
            STATUS current
            DESCRIPTION
                "RowStatus."
            ::= { ibAclIPAclNamedAdvEntry 1 }

        ibAclIPAclNamedAdvAct OBJECT-TYPE
            SYNTAX RuleAction
            MAX-ACCESS read-create
            STATUS current
            DESCRIPTION
                "The action of advanced ACL rule."
            ::= { ibAclIPAclNamedAdvEntry 2 }

        ibAclIPAclNamedAdvProtocol OBJECT-TYPE
            SYNTAX Integer32 (0..255)
            MAX-ACCESS read-create
            STATUS current
            DESCRIPTION
                "The protocol-type of advanced ACL rule.  0 indicates any IPv4 or
                IPv6 protocol.
                  <1-255>  Protocol number
                  gre      GRE tunneling(47)
                  icmp     Internet Control Message Protocol(1)
                  icmpv6   Internet Control Message Protocol6(58)
                  igmp     Internet Group Management Protocol(2)
                  ipinip   IP in IP tunneling(4)
                  ospf     OSPF routing protocol(89)
                  tcp      Transmission Control Protocol (6)
                  udp      User Datagram Protocol (17)
                  ipv6-ah  IPv6 Authentication Header(51)
                  ipv6-esp IPv6 Encapsulating Security Payload(50)
                "
            ::= { ibAclIPAclNamedAdvEntry 3 }

        ibAclIPAclNamedAdvAddrFlag OBJECT-TYPE
            SYNTAX AddressFlag
            MAX-ACCESS read-create
            STATUS current
            DESCRIPTION
                "Address flag to select address."
            DEFVAL { invalid }
            ::= { ibAclIPAclNamedAdvEntry 4 }

        ibAclIPAclNamedAdvSrcAddrType OBJECT-TYPE
            SYNTAX InetAddressType
            MAX-ACCESS read-create
            STATUS current
            DESCRIPTION
                "The type of source IP address.
                "
            ::= { ibAclIPAclNamedAdvEntry 5 }

        ibAclIPAclNamedAdvSrcAddr OBJECT-TYPE
            SYNTAX InetAddress
            MAX-ACCESS read-create
            STATUS current
            DESCRIPTION
                "The specified source IP address.
                 The type of this address is determined by the value of
                 ibAclIPAclNamedAdvSrcAddrType.
                "
            ::= { ibAclIPAclNamedAdvEntry 6 }

        ibAclIPAclNamedAdvSrcPrefix OBJECT-TYPE
            SYNTAX InetAddressPrefixLength
            MAX-ACCESS read-create
            STATUS current
            DESCRIPTION
                "Specify the length of a generic Internet network address
                 prefix.  A value of n corresponds to an IP address mask that
                 has n contiguous 1-bits from the most significant bit (MSB)
                 and all other bits set to 0.
                "
            ::= { ibAclIPAclNamedAdvEntry 7 }

        ibAclIPAclNamedAdvSrcAny OBJECT-TYPE
            SYNTAX TruthValue
            MAX-ACCESS read-create
            STATUS current
            DESCRIPTION
                "The flag of matching any IP address."
            DEFVAL { true }
            ::= { ibAclIPAclNamedAdvEntry 8 }

        ibAclIPAclNamedAdvSrcWild OBJECT-TYPE
            SYNTAX IpAddress
            MAX-ACCESS read-create
            STATUS current
            DESCRIPTION
                "Source IPv4 address wildcard mask.
                 Only IPv4 Advanced Rule supports this object.
                 Default value is '0.0.0.0'.
                "
            ::= { ibAclIPAclNamedAdvEntry 9 }

        ibAclIPAclNamedAdvSrcOp OBJECT-TYPE
            SYNTAX PortOp
            MAX-ACCESS read-create
            STATUS current
            DESCRIPTION
                "Source port operation symbol of advanced acl group."
            DEFVAL { invalid }
            ::= { ibAclIPAclNamedAdvEntry 10 }

        ibAclIPAclNamedAdvSrcPort1 OBJECT-TYPE
            SYNTAX Integer32 (0..65535)
            MAX-ACCESS read-create
            STATUS current
            DESCRIPTION
                "The fourth layer source port1."
            DEFVAL { 0 }
            ::= { ibAclIPAclNamedAdvEntry 11 }

        ibAclIPAclNamedAdvSrcPort2 OBJECT-TYPE
            SYNTAX Integer32 (0..65535)
            MAX-ACCESS read-create
            STATUS current
            DESCRIPTION
                "The fourth layer source port2."
            DEFVAL { 65535 }
            ::= { ibAclIPAclNamedAdvEntry 12 }

        ibAclIPAclNamedAdvDstAddrType OBJECT-TYPE
            SYNTAX InetAddressType
            MAX-ACCESS read-create
            STATUS current
            DESCRIPTION
                "The type of destination IP address.
                "
            ::= { ibAclIPAclNamedAdvEntry 13 }

        ibAclIPAclNamedAdvDstAddr OBJECT-TYPE
            SYNTAX InetAddress
            MAX-ACCESS read-create
            STATUS current
            DESCRIPTION
                "The specified destination IP address.
                 The type of this address is determined by the value of
                 ibAclIPAclNamedAdvDstAddrType.
                "
            ::= { ibAclIPAclNamedAdvEntry 14 }

        ibAclIPAclNamedAdvDstPrefix OBJECT-TYPE
            SYNTAX InetAddressPrefixLength
            MAX-ACCESS read-create
            STATUS current
            DESCRIPTION
                "Specify the length of a generic Internet network address
                 prefix.  A value of n corresponds to an IP address mask that
                 has n contiguous 1-bits from the most significant bit (MSB)
                 and all other bits set to 0.
                "
            ::= { ibAclIPAclNamedAdvEntry 15 }

        ibAclIPAclNamedAdvDstAny OBJECT-TYPE
            SYNTAX TruthValue
            MAX-ACCESS read-create
            STATUS current
            DESCRIPTION
                "The flag of matching any IP address."
            DEFVAL { true }
            ::= { ibAclIPAclNamedAdvEntry 16 }

        ibAclIPAclNamedAdvDstWild OBJECT-TYPE
            SYNTAX IpAddress
            MAX-ACCESS read-create
            STATUS current
            DESCRIPTION
                "Destination IPv4 address wildcard mask.
                 Only IPv4 Advanced Rule supports this object.
                 Default value is '0.0.0.0'.
                "
            ::= { ibAclIPAclNamedAdvEntry 17 }

        ibAclIPAclNamedAdvDstOp OBJECT-TYPE
            SYNTAX PortOp
            MAX-ACCESS read-create
            STATUS current
            DESCRIPTION
                "Destination port operation symbol of advanced acl group."
            DEFVAL { invalid }
            ::= { ibAclIPAclNamedAdvEntry 18 }

        ibAclIPAclNamedAdvDstPort1 OBJECT-TYPE
            SYNTAX Integer32 (0..65535)
            MAX-ACCESS read-create
            STATUS current
            DESCRIPTION
                "The fourth layer destination port1."
            DEFVAL { 0 }
            ::= { ibAclIPAclNamedAdvEntry 19 }

        ibAclIPAclNamedAdvDstPort2 OBJECT-TYPE
            SYNTAX Integer32 (0..65535)
            MAX-ACCESS read-create
            STATUS current
            DESCRIPTION
                "The fourth layer destination port2."
            DEFVAL { 65535 }
            ::= { ibAclIPAclNamedAdvEntry 20 }

        ibAclIPAclNamedAdvIcmpType OBJECT-TYPE
            SYNTAX Integer32 (0..255|65535)
            MAX-ACCESS read-create
            STATUS current
            DESCRIPTION
                "The type of ICMP packet."
            DEFVAL { 65535 }
            ::= { ibAclIPAclNamedAdvEntry 21 }

        ibAclIPAclNamedAdvIcmpCode OBJECT-TYPE
            SYNTAX Integer32 (0..255|65535)
            MAX-ACCESS read-create
            STATUS current
            DESCRIPTION
                "The code of ICMP packet."
            DEFVAL { 65535 }
            ::= { ibAclIPAclNamedAdvEntry 22 }

        ibAclIPAclNamedAdvPrecedence OBJECT-TYPE
            SYNTAX Integer32 (0..7|255)
            MAX-ACCESS read-create
            STATUS current
            DESCRIPTION
                "The value of IP-packet's precedence.
                <0-7>           Value of precedence
                routine         Specify routine precedence(0)
                priority        Specify priority precedence(1)
                immediate       Specify immediate precedence(2)
                flash           Specify flash precedence(3)
                flash-override  Specify flash-override precedence(4)
                critical        Specify critical precedence(5)
                internet        Specify internetwork control precedence(6)
                network         Specify network control precedence(7)
                "
            DEFVAL { 255 }
            ::= { ibAclIPAclNamedAdvEntry 23 }

        ibAclIPAclNamedAdvTos OBJECT-TYPE
            SYNTAX Integer32 (0..15|255)
            MAX-ACCESS read-create
            STATUS current
            DESCRIPTION
                "The value of IP-packet's TOS.
                  <0-15>             Value of TOS(type of service)
                  max-reliability    Match packets with max reliable TOS(2)
                  max-throughput     Match packets with max throughput TOS(4)
                  min-delay          Match packets with min delay TOS(8)
                  min-monetary-cost  Match packets with min monetary cost TOS(1)
                  normal             Match packets with normal TOS(0)
                "
            DEFVAL { 255 }
            ::= { ibAclIPAclNamedAdvEntry 24 }

        ibAclIPAclNamedAdvDscp OBJECT-TYPE
            SYNTAX DSCPValue
            MAX-ACCESS read-create
            STATUS current
            DESCRIPTION
                "The value of DSCP of IP packet."
            DEFVAL { 255 }
            ::= { ibAclIPAclNamedAdvEntry 25 }

        ibAclIPAclNamedAdvTRangeName OBJECT-TYPE
            SYNTAX OCTET STRING (SIZE(0..32))
            MAX-ACCESS read-create
            STATUS current
            DESCRIPTION
                "The Time-range of advanced ACL rule.
                 Default value is zero-length.
                "
            ::= { ibAclIPAclNamedAdvEntry 26 }

        ibAclIPAclNamedAdvTCPFlag OBJECT-TYPE
            SYNTAX TCPFlag
            MAX-ACCESS read-create
            STATUS current
            DESCRIPTION
                "The packet type of TCP protocol."
            DEFVAL { invalid }
            ::= { ibAclIPAclNamedAdvEntry 27 }

        ibAclIPAclNamedAdvFragmentFlag OBJECT-TYPE
            SYNTAX FragmentFlag
            MAX-ACCESS read-create
            STATUS current
            DESCRIPTION
                "The flag of matching fragmented packet,
                 and now support two value: 0 or 2.
                "
            DEFVAL { invalid }
            ::= { ibAclIPAclNamedAdvEntry 28 }

        ibAclIPAclNamedAdvLog OBJECT-TYPE
            SYNTAX TruthValue
            MAX-ACCESS read-create
            STATUS current
            DESCRIPTION
                "Log matched packets."
            DEFVAL { false }
            ::= { ibAclIPAclNamedAdvEntry 29 }

        ibAclIPAclNamedAdvCount OBJECT-TYPE
            SYNTAX Unsigned32
            MAX-ACCESS read-only
            STATUS current
            DESCRIPTION
                "The count of matches by the rule."
            ::= { ibAclIPAclNamedAdvEntry 30 }

        ibAclIPAclNamedAdvCountClear OBJECT-TYPE
            SYNTAX CounterClear
            MAX-ACCESS read-write
            STATUS current
            DESCRIPTION
                "Reset the statistics counter of this rule."
            DEFVAL { nouse }
            ::= { ibAclIPAclNamedAdvEntry 31 }

        ibAclIPAclNamedAdvEnable OBJECT-TYPE
            SYNTAX TruthValue
            MAX-ACCESS read-only
            STATUS current
            DESCRIPTION
                "The rule is active or not.
                 true : active
                 false : inactive
                "
            DEFVAL { false }
            ::= { ibAclIPAclNamedAdvEntry 32 }

        ibAclIPAclNamedAdvVpnInstName OBJECT-TYPE
            SYNTAX OCTET STRING (SIZE(0..32))
            MAX-ACCESS read-create
            STATUS current
            DESCRIPTION
                "The VPN name to which the rule will be applied.
                 Default value is zero-length.
                "
            ::= { ibAclIPAclNamedAdvEntry 33 }

        ibAclIPAclNamedAdvComment OBJECT-TYPE
            SYNTAX OCTET STRING (SIZE(0..127))
            MAX-ACCESS read-create
            STATUS current
            DESCRIPTION
                "The description of ACL rule.
                 Default value is zero-length String.
                "
            ::= { ibAclIPAclNamedAdvEntry 34 }

        ibAclIPAclNamedAdvReflective OBJECT-TYPE
            SYNTAX TruthValue
            MAX-ACCESS read-create
            STATUS current
            DESCRIPTION
                "The flag of reflective."
            ::= { ibAclIPAclNamedAdvEntry 35 }

        ibAclIPAclNamedAdvCounting OBJECT-TYPE
            SYNTAX TruthValue
            MAX-ACCESS read-create
            STATUS current
            DESCRIPTION
                "The packet will be counted when it matches the rule.
                 It is disabled by default.
                "
            DEFVAL { false }
            ::= { ibAclIPAclNamedAdvEntry 36 }

        ibAclIPAclNamedAdvTCPFlagMask OBJECT-TYPE
            SYNTAX BITS {
                           tcpack(0),
                           tcpfin(1),
                           tcppsh(2),
                           tcprst(3),
                           tcpsyn(4),
                           tcpurg(5)
                        }
            MAX-ACCESS read-create
            STATUS current
            DESCRIPTION
                "The TCP Flag Mask.  This is a bit-map of possible conditions.
                The various bit positions are:
                |0        |tcpack                 |
                |1        |tcpfin                 |
                |2        |tcppsh                 |
                |3        |tcprst                 |
                |4        |tcpsyn                 |
                |5        |tcpurg                 |
                "
            ::= { ibAclIPAclNamedAdvEntry 37 }

        ibAclIPAclNamedAdvTCPFlagValue OBJECT-TYPE
            SYNTAX BITS {
                           tcpack(0),
                           tcpfin(1),
                           tcppsh(2),
                           tcprst(3),
                           tcpsyn(4),
                           tcpurg(5)
                        }
            MAX-ACCESS read-create
            STATUS current
            DESCRIPTION
                "The TCP Flag Value.  This is a bit-map of possible conditions.
                The various bit positions are:
                |0        |tcpack                 |
                |1        |tcpfin                 |
                |2        |tcppsh                 |
                |3        |tcprst                 |
                |4        |tcpsyn                 |
                |5        |tcpurg                 |
                "
            ::= { ibAclIPAclNamedAdvEntry 38 }

        ibAclIPAclNamedAdvRouteTypeAny OBJECT-TYPE
            SYNTAX TruthValue
            MAX-ACCESS read-create
            STATUS current
            DESCRIPTION
                "The flag of matching any type of routing header of IPv6 packet.
                "
            DEFVAL { false }
            ::= { ibAclIPAclNamedAdvEntry 39 }

        ibAclIPAclNamedAdvRouteTypeValue OBJECT-TYPE
            SYNTAX Integer32 (0..255|65535)
            MAX-ACCESS read-create
            STATUS current
            DESCRIPTION
                "The type of routing header of IPv6 packet."
            DEFVAL { 65535 }
            ::= { ibAclIPAclNamedAdvEntry 40 }

        ibAclIPAclNamedAdvFlowLabel OBJECT-TYPE
            SYNTAX Unsigned32 (0..1048575|4294967295)
            MAX-ACCESS read-create
            STATUS current
            DESCRIPTION
                "The value of flow label of IPv6 packet header."
            DEFVAL { 4294967295 }
            ::= { ibAclIPAclNamedAdvEntry 41 }

        ibAclIPAclNamedAdvSrcSuffix OBJECT-TYPE
            SYNTAX Unsigned32
            MAX-ACCESS read-create
            STATUS current
            DESCRIPTION
                "Denotes the length of a generic Internet network address suffix.
                 A value of n corresponds to an IP address mask
                 that has n contiguous 1-bits from the least significant bit
                 and all other bits set to 0.
                "
            ::= { ibAclIPAclNamedAdvEntry 42 }

        ibAclIPAclNamedAdvDstSuffix OBJECT-TYPE
            SYNTAX Unsigned32
            MAX-ACCESS read-create
            STATUS current
            DESCRIPTION
                "Denotes the length of a generic Internet network address suffix.
                 A value of n corresponds to an IP address mask
                 that has n contiguous 1-bits from the least significant bit
                 and all other bits set to 0.
                "
            ::= { ibAclIPAclNamedAdvEntry 43 }

--
-- Node of ibAclMACAclGroup
--
        ibAclMACAclGroup OBJECT IDENTIFIER ::= { ibAclMib2Objects 3 }
--
-- Nodes of ibAclMACTable
--
        ibAclMACTable OBJECT-TYPE
            SYNTAX SEQUENCE OF IbAclMACEntry
            MAX-ACCESS not-accessible
            STATUS current
            DESCRIPTION
                "A table of MAC acl group.
                 If some objects of this table are not supported by some products,
                 these objects can't be created, changed or applied.
                 Default value of these objects will be returned when they are read.
                "
            ::= { ibAclMACAclGroup 1 }

        ibAclMACEntry OBJECT-TYPE
            SYNTAX IbAclMACEntry
            MAX-ACCESS not-accessible
            STATUS current
            DESCRIPTION
                "MAC acl group information."
            INDEX
            {
                ibAclNumberGroupType,
                ibAclNumberGroupIndex,
                ibAclMACRuleIndex
            }
            ::= { ibAclMACTable 1 }

        IbAclMACEntry ::=
            SEQUENCE
            {
                ibAclMACRuleIndex
                    Integer32,
                ibAclMACRowStatus
                    RowStatus,
                ibAclMACAct
                    RuleAction,
                ibAclMACTypeCode
                    OCTET STRING,
                ibAclMACTypeMask
                    OCTET STRING,
                ibAclMACSrcMac
                    MacAddress,
                ibAclMACSrcMacWild
                    MacAddress,
                ibAclMACDestMac
                    MacAddress,
                ibAclMACDestMacWild
                    MacAddress,
                ibAclMACLsapCode
                    OCTET STRING,
                ibAclMACLsapMask
                    OCTET STRING,
                ibAclMACCos
                    Integer32,
                ibAclMACTimeRangeName
                    OCTET STRING,
                ibAclMACCount
                    Unsigned32,
                ibAclMACCountClear
                    CounterClear,
                ibAclMACEnable
                    TruthValue,
                ibAclMACComment
                    OCTET STRING,
                ibAclMACLog
                    TruthValue,
                ibAclMACCounting
                    TruthValue
            }

        ibAclMACRuleIndex OBJECT-TYPE
            SYNTAX Integer32 (0..65534)
            MAX-ACCESS not-accessible
            STATUS current
            DESCRIPTION
                "The rule index of MAC-based acl group."
            ::= { ibAclMACEntry 1 }

        ibAclMACRowStatus OBJECT-TYPE
            SYNTAX RowStatus
            MAX-ACCESS read-create
            STATUS current
            DESCRIPTION
                "RowStatus."
            ::= { ibAclMACEntry 2 }

        ibAclMACAct OBJECT-TYPE
            SYNTAX RuleAction
            MAX-ACCESS read-create
            STATUS current
            DESCRIPTION
                "The action of MAC acl rule."
            ::= { ibAclMACEntry 3 }

        ibAclMACTypeCode OBJECT-TYPE
            SYNTAX OCTET STRING (SIZE(0..32))
            MAX-ACCESS read-create
            STATUS current
            DESCRIPTION
                "The type of protocol."
            REFERENCE
                "rfc894, rfc1010."
            ::= { ibAclMACEntry 4 }

        ibAclMACTypeMask OBJECT-TYPE
            SYNTAX OCTET STRING (SIZE(0..32))
            MAX-ACCESS read-create
            STATUS current
            DESCRIPTION
                "The mask of protocol."
            ::= { ibAclMACEntry 5 }

        ibAclMACSrcMac OBJECT-TYPE
            SYNTAX MacAddress
            MAX-ACCESS read-create
            STATUS current
            DESCRIPTION
                "Source MAC of MAC acl rule.
                 Default value is '00:00:00:00:00:00'.
                "
            ::= { ibAclMACEntry 6 }

        ibAclMACSrcMacWild OBJECT-TYPE
            SYNTAX MacAddress
            MAX-ACCESS read-create
            STATUS current
            DESCRIPTION
                "Source MAC wildzard of MAC acl rule.
                 Default value is '00:00:00:00:00:00'.
                "
            ::= { ibAclMACEntry 7 }

        ibAclMACDestMac OBJECT-TYPE
            SYNTAX MacAddress
            MAX-ACCESS read-create
            STATUS current
            DESCRIPTION
                "Destination MAC of MAC acl rule.
                 Default value is '00:00:00:00:00:00'.
                "
            ::= { ibAclMACEntry 8 }

        ibAclMACDestMacWild OBJECT-TYPE
            SYNTAX MacAddress
            MAX-ACCESS read-create
            STATUS current
            DESCRIPTION
                "Destination MAC wildzard of MAC acl rule.
                 Default value is '00:00:00:00:00:00'
                "
            ::= { ibAclMACEntry 9 }

        ibAclMACLsapCode OBJECT-TYPE
            SYNTAX OCTET STRING (SIZE(0..32))
            MAX-ACCESS read-create
            STATUS current
            DESCRIPTION
                "The type of LSAP."
            REFERENCE
                "ANSI/IEEE Std 802.3"
            ::= { ibAclMACEntry 10 }

        ibAclMACLsapMask OBJECT-TYPE
            SYNTAX OCTET STRING (SIZE(0..32))
            MAX-ACCESS read-create
            STATUS current
            DESCRIPTION
                "The mask of LSAP."
            ::= { ibAclMACEntry 11 }

        ibAclMACCos OBJECT-TYPE
            SYNTAX Integer32 (0..7 | 255)
            MAX-ACCESS read-create
            STATUS current
            DESCRIPTION
                "Vlan priority of MAC acl rule."
            DEFVAL { 255 }
            ::= { ibAclMACEntry 12 }

        ibAclMACTimeRangeName OBJECT-TYPE
            SYNTAX OCTET STRING (SIZE(0..32))
            MAX-ACCESS read-create
            STATUS current
            DESCRIPTION
                "The Time-range of MAC acl rule.
                 Default value is zero-length.
                "
            ::= { ibAclMACEntry 13 }

        ibAclMACCount OBJECT-TYPE
            SYNTAX Unsigned32
            MAX-ACCESS read-only
            STATUS current
            DESCRIPTION
                "The count of matched frames by the rule."
            ::= { ibAclMACEntry 14 }

        ibAclMACCountClear OBJECT-TYPE
            SYNTAX CounterClear
            MAX-ACCESS read-write
            STATUS current
            DESCRIPTION
                "Reset the value of counter."
            DEFVAL { nouse }
            ::= { ibAclMACEntry 15 }

        ibAclMACEnable OBJECT-TYPE
            SYNTAX TruthValue
            MAX-ACCESS read-only
            STATUS current
            DESCRIPTION
                "The rule is active or not.
                 true : active
                 false : inactive
                "
            DEFVAL { false }
            ::= { ibAclMACEntry 16 }

        ibAclMACComment OBJECT-TYPE
            SYNTAX OCTET STRING (SIZE(0..127))
            MAX-ACCESS read-create
            STATUS current
            DESCRIPTION
                "The description of ACL rule.
                 Default value is Zero-length String.
                "
            ::= { ibAclMACEntry 17 }

        ibAclMACLog OBJECT-TYPE
            SYNTAX TruthValue
            MAX-ACCESS read-create
            STATUS current
            DESCRIPTION
                "The packet will be logged when it matches the rule.
                 It is disabled by default.
                "
            DEFVAL { false }
            ::= { ibAclMACEntry 18 }

        ibAclMACCounting OBJECT-TYPE
            SYNTAX TruthValue
            MAX-ACCESS read-create
            STATUS current
            DESCRIPTION
                "The packet will be counted when it matches the rule.
                 It is disabled by default.
                "
            DEFVAL { false }
            ::= { ibAclMACEntry 19 }

--
-- Nodes of named MAC ACL group
--
        ibAclNamedMACTable OBJECT-TYPE
            SYNTAX SEQUENCE OF IbAclNamedMACEntry
            MAX-ACCESS not-accessible
            STATUS current
            DESCRIPTION
                "A table of named MAC ACL rule.
                 The name of ACL group will be used as an index in this table,
                 which differs from the table ibAclMACTable.
                 If some objects of this table are not supported by some products,
                 these objects can't be created, changed or applied.
                 Default value of these objects will be returned when they are read.
                "
            ::= { ibAclMACAclGroup 2 }

        ibAclNamedMACEntry OBJECT-TYPE
            SYNTAX IbAclNamedMACEntry
            MAX-ACCESS not-accessible
            STATUS current
            DESCRIPTION
                "MAC acl group information."
            INDEX
            {
                ibAclNumberGroupType,
                ibAclNamedGroupName,
                ibAclMACRuleIndex
            }
            ::= { ibAclNamedMACTable 1 }

        IbAclNamedMACEntry ::=
            SEQUENCE
            {
                ibAclNamedMACRowStatus
                    RowStatus,
                ibAclNamedMACAct
                    RuleAction,
                ibAclNamedMACTypeCode
                    OCTET STRING,
                ibAclNamedMACTypeMask
                    OCTET STRING,
                ibAclNamedMACSrcMac
                    MacAddress,
                ibAclNamedMACSrcMacWild
                    MacAddress,
                ibAclNamedMACDstMac
                    MacAddress,
                ibAclNamedMACDstMacWild
                    MacAddress,
                ibAclNamedMACLsapCode
                    OCTET STRING,
                ibAclNamedMACLsapMask
                    OCTET STRING,
                ibAclNamedMACCos
                    Integer32,
                ibAclNamedMACTimeRangeName
                    OCTET STRING,
                ibAclNamedMACCount
                    Unsigned32,
                ibAclNamedMACCountClear
                    CounterClear,
                ibAclNamedMACEnable
                    TruthValue,
                ibAclNamedMACComment
                    OCTET STRING,
                ibAclNamedMACLog
                    TruthValue,
                ibAclNamedMACCounting
                    TruthValue
             }

        ibAclNamedMACRowStatus OBJECT-TYPE
            SYNTAX RowStatus
            MAX-ACCESS read-create
            STATUS current
            DESCRIPTION
                "RowStatus."
            ::= { ibAclNamedMACEntry 1 }

        ibAclNamedMACAct OBJECT-TYPE
            SYNTAX RuleAction
            MAX-ACCESS read-create
            STATUS current
            DESCRIPTION
                "The action of MAC ACL rule."
            ::= { ibAclNamedMACEntry 2 }

        ibAclNamedMACTypeCode OBJECT-TYPE
            SYNTAX OCTET STRING (SIZE(0..32))
            MAX-ACCESS read-create
            STATUS current
            DESCRIPTION
                "The type of protocol."
            REFERENCE
                "rfc894, rfc1010."
            ::= { ibAclNamedMACEntry 3 }

        ibAclNamedMACTypeMask OBJECT-TYPE
            SYNTAX OCTET STRING (SIZE(0..32))
            MAX-ACCESS read-create
            STATUS current
            DESCRIPTION
                "The mask of protocol."
            ::= { ibAclNamedMACEntry 4 }

        ibAclNamedMACSrcMac OBJECT-TYPE
            SYNTAX MacAddress
            MAX-ACCESS read-create
            STATUS current
            DESCRIPTION
                "Source MAC of MAC ACL rule.
                 Default value is '00:00:00:00:00:00'.
                "
            ::= { ibAclNamedMACEntry 5 }

        ibAclNamedMACSrcMacWild OBJECT-TYPE
            SYNTAX MacAddress
            MAX-ACCESS read-create
            STATUS current
            DESCRIPTION
                "Source MAC wildcard of MAC ACL rule.
                 Default value is '00:00:00:00:00:00'.
                "
            ::= { ibAclNamedMACEntry 6 }

        ibAclNamedMACDstMac OBJECT-TYPE
            SYNTAX MacAddress
            MAX-ACCESS read-create
            STATUS current
            DESCRIPTION
                "Destination MAC of MAC ACL rule.
                 Default value is '00:00:00:00:00:00'.
                "
            ::= { ibAclNamedMACEntry 7 }

        ibAclNamedMACDstMacWild OBJECT-TYPE
            SYNTAX MacAddress
            MAX-ACCESS read-create
            STATUS current
            DESCRIPTION
                "Destination MAC wildcard of MAC ACL rule.
                 Default value is '00:00:00:00:00:00'
                "
            ::= { ibAclNamedMACEntry 8 }

        ibAclNamedMACLsapCode OBJECT-TYPE
            SYNTAX OCTET STRING (SIZE(0..32))
            MAX-ACCESS read-create
            STATUS current
            DESCRIPTION
                "The type of LSAP."
            REFERENCE
                "ANSI/IEEE Std 802.3"
            ::= { ibAclNamedMACEntry 9 }

        ibAclNamedMACLsapMask OBJECT-TYPE
            SYNTAX OCTET STRING (SIZE(0..32))
            MAX-ACCESS read-create
            STATUS current
            DESCRIPTION
                "The mask of LSAP."
            ::= { ibAclNamedMACEntry 10 }

        ibAclNamedMACCos OBJECT-TYPE
            SYNTAX Integer32 (0..7 | 255)
            MAX-ACCESS read-create
            STATUS current
            DESCRIPTION
                "Vlan priority of MAC ACL rule."
            DEFVAL { 255 }
            ::= { ibAclNamedMACEntry 11 }

        ibAclNamedMACTimeRangeName OBJECT-TYPE
            SYNTAX OCTET STRING (SIZE(0..32))
            MAX-ACCESS read-create
            STATUS current
            DESCRIPTION
                "The time-range of MAC ACL rule.
                 Default value is zero-length.
                "
            ::= { ibAclNamedMACEntry 12 }

        ibAclNamedMACCount OBJECT-TYPE
            SYNTAX Unsigned32
            MAX-ACCESS read-only
            STATUS current
            DESCRIPTION
                "The count of matched frames by the rule."
            ::= { ibAclNamedMACEntry 13 }

        ibAclNamedMACCountClear OBJECT-TYPE
            SYNTAX CounterClear
            MAX-ACCESS read-write
            STATUS current
            DESCRIPTION
                "Reset the value of counter."
            DEFVAL { nouse }
            ::= { ibAclNamedMACEntry 14 }

        ibAclNamedMACEnable OBJECT-TYPE
            SYNTAX TruthValue
            MAX-ACCESS read-only
            STATUS current
            DESCRIPTION
                "The rule is active or not.
                 true : active
                 false : inactive
                "
            DEFVAL { false }
            ::= { ibAclNamedMACEntry 15 }

        ibAclNamedMACComment OBJECT-TYPE
            SYNTAX OCTET STRING (SIZE(0..127))
            MAX-ACCESS read-create
            STATUS current
            DESCRIPTION
                "The description of ACL rule.
                 Default value is Zero-length String.
                "
            ::= { ibAclNamedMACEntry 16 }

        ibAclNamedMACLog OBJECT-TYPE
            SYNTAX TruthValue
            MAX-ACCESS read-create
            STATUS current
            DESCRIPTION
                "The packet will be logged when it matches the rule.
                 It is disabled by default.
                "
            DEFVAL { false }
            ::= { ibAclNamedMACEntry 17 }

        ibAclNamedMACCounting OBJECT-TYPE
            SYNTAX TruthValue
            MAX-ACCESS read-create
            STATUS current
            DESCRIPTION
                "The packet will be counted when it matches the rule.
                 It is disabled by default.
                "
            DEFVAL { false }
            ::= { ibAclNamedMACEntry 18 }

--
-- Node of ibAclEnUserGroup
--
        ibAclEnUserAclGroup OBJECT IDENTIFIER ::= { ibAclMib2Objects 4 }
--
-- Nodes of ibAclEnUserTable
--
        ibAclEnUserTable OBJECT-TYPE
            SYNTAX SEQUENCE OF IbAclEnUserEntry
            MAX-ACCESS not-accessible
            STATUS current
            DESCRIPTION
                "A table of user acl group information.
                 If some objects of this table are not supported by some products,
                 these objects can't be created, changed and applied.
                 Default value of these objects will be returned when they are read.
                "
            ::= { ibAclEnUserAclGroup 3 }

        ibAclEnUserEntry OBJECT-TYPE
            SYNTAX IbAclEnUserEntry
            MAX-ACCESS not-accessible
            STATUS current
            DESCRIPTION
                "User defined acl group entry."
            INDEX { ibAclNumberGroupType,
                    ibAclNumberGroupIndex,
                    ibAclEnUserRuleIndex }
            ::= { ibAclEnUserTable 1 }

        IbAclEnUserEntry ::=
            SEQUENCE
            {
                ibAclEnUserRuleIndex
                    Integer32,
                ibAclEnUserRowStatus
                    RowStatus,
                ibAclEnUserAct
                    RuleAction,
                ibAclEnUserStartString
                    OCTET STRING,
                ibAclEnUserL2String
                    OCTET STRING,
                ibAclEnUserMplsString
                    OCTET STRING,
                ibAclEnUserIPv4String
                    OCTET STRING,
                ibAclEnUserIPv6String
                    OCTET STRING,
                ibAclEnUserL4String
                    OCTET STRING,
                ibAclEnUserL5String
                    OCTET STRING,
                ibAclEnUserTimeRangeName
                    OCTET STRING,
                ibAclEnUserCount
                    Unsigned32,
                ibAclEnUserCountClear
                    CounterClear,
                ibAclEnUserEnable
                    TruthValue,
                ibAclEnUserComment
                    OCTET STRING,
                ibAclEnUserLog
                    TruthValue,
                ibAclEnUserCounting
                    TruthValue
             }

        ibAclEnUserRuleIndex OBJECT-TYPE
            SYNTAX Integer32 (0..65534)
            MAX-ACCESS not-accessible
            STATUS current
            DESCRIPTION
                "The subitem of the user acl."
            ::= { ibAclEnUserEntry 1 }

        ibAclEnUserRowStatus OBJECT-TYPE
            SYNTAX RowStatus
            MAX-ACCESS read-create
            STATUS current
            DESCRIPTION
                "RowStatus."
            ::= { ibAclEnUserEntry 2 }

        ibAclEnUserAct OBJECT-TYPE
            SYNTAX RuleAction
            MAX-ACCESS read-create
            STATUS current
            DESCRIPTION
                "The action of user defined acl rule."
            ::= { ibAclEnUserEntry 3 }

        ibAclEnUserStartString OBJECT-TYPE
            SYNTAX OCTET STRING (SIZE(0..255))
            MAX-ACCESS read-create
            STATUS current
            DESCRIPTION
                "The rule, matching packets, input like this:
                 'RuleOffset','RuleString','RuleMask'.

                 RuleOffset: The value of this object is defined by product and
                 it indicates the offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: 10,10af,ffff.

                 Default value is zero-length.
                "
            ::= { ibAclEnUserEntry 4 }

        ibAclEnUserL2String OBJECT-TYPE
            SYNTAX OCTET STRING (SIZE(0..255))
            MAX-ACCESS read-create
            STATUS current
            DESCRIPTION
                "The rule, matching layer 2 packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { ibAclEnUserEntry 5 }

        ibAclEnUserMplsString OBJECT-TYPE
            SYNTAX OCTET STRING (SIZE(0..255))
            MAX-ACCESS read-create
            STATUS current
            DESCRIPTION
                "The rule, matching mpls packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { ibAclEnUserEntry 6 }

        ibAclEnUserIPv4String OBJECT-TYPE
            SYNTAX OCTET STRING (SIZE(0..255))
            MAX-ACCESS read-create
            STATUS current
            DESCRIPTION
                "The rule, matching IPv4 packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { ibAclEnUserEntry 7 }

        ibAclEnUserIPv6String OBJECT-TYPE
            SYNTAX OCTET STRING (SIZE(0..255))
            MAX-ACCESS read-create
            STATUS current
            DESCRIPTION
                "The rule, matching IPv6 packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { ibAclEnUserEntry 8 }

        ibAclEnUserL4String OBJECT-TYPE
            SYNTAX OCTET STRING (SIZE(0..255))
            MAX-ACCESS read-create
            STATUS current
            DESCRIPTION
                "The rule, matching layer 4 packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { ibAclEnUserEntry 9 }

        ibAclEnUserL5String OBJECT-TYPE
            SYNTAX OCTET STRING (SIZE(0..255))
            MAX-ACCESS read-create
            STATUS current
            DESCRIPTION
                "The rule, matching layer 5 packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { ibAclEnUserEntry 10 }

        ibAclEnUserTimeRangeName OBJECT-TYPE
            SYNTAX OCTET STRING (SIZE(0..32))
            MAX-ACCESS read-create
            STATUS current
            DESCRIPTION
                "The Time-range of user acl rule.
                 Default value is zero-length."
            ::= { ibAclEnUserEntry 11 }

        ibAclEnUserCount OBJECT-TYPE
            SYNTAX Unsigned32
            MAX-ACCESS read-only
            STATUS current
            DESCRIPTION
                "The count of matched by the rule."
            ::= { ibAclEnUserEntry 12 }

        ibAclEnUserCountClear OBJECT-TYPE
            SYNTAX CounterClear
            MAX-ACCESS read-write
            STATUS current
            DESCRIPTION
                "Reset the value of counter."
            ::= { ibAclEnUserEntry 13 }

        ibAclEnUserEnable OBJECT-TYPE
            SYNTAX TruthValue
            MAX-ACCESS read-only
            STATUS current
            DESCRIPTION
                "The rule is active or not.
                 true : active
                 false : inactive
                "
            DEFVAL { false }
            ::= { ibAclEnUserEntry 14 }

        ibAclEnUserComment OBJECT-TYPE
            SYNTAX OCTET STRING (SIZE(0..127))
            MAX-ACCESS read-create
            STATUS current
            DESCRIPTION
                "The description of ACL rule.
                 Default value is Zero-length String.
                "
            ::= { ibAclEnUserEntry 15 }

        ibAclEnUserLog OBJECT-TYPE
            SYNTAX TruthValue
            MAX-ACCESS read-create
            STATUS current
            DESCRIPTION
                "The packet will be logged when it matches the rule.
                 It is disabled by default.
                "
            DEFVAL { false }
            ::= { ibAclEnUserEntry 16 }

        ibAclEnUserCounting OBJECT-TYPE
            SYNTAX TruthValue
            MAX-ACCESS read-create
            STATUS current
            DESCRIPTION
                "The packet will be counted when it matches the rule.
                 It is disabled by default.
                "
            DEFVAL { false }
            ::= { ibAclEnUserEntry 17 }

--
-- Nodes of ibAclNamedUserTable
--
        ibAclNamedUserTable OBJECT-TYPE
            SYNTAX SEQUENCE OF IbAclNamedUserEntry
            MAX-ACCESS not-accessible
            STATUS current
            DESCRIPTION
                "A table of named user acl rule.
                 The name of ACL group will be used as an index in this table,
                 which differs from the table ibAclEnUserTable.
                 If some objects of this table are not supported by some products,
                 these objects can't be created, changed and applied.
                 Default value of these objects will be returned when they are read.
                "
            ::= { ibAclEnUserAclGroup 4 }

        ibAclNamedUserEntry OBJECT-TYPE
            SYNTAX IbAclNamedUserEntry
            MAX-ACCESS not-accessible
            STATUS current
            DESCRIPTION
                "User defined acl group entry."
            INDEX
            {
                ibAclNumberGroupType,
                ibAclNamedGroupName,
                ibAclEnUserRuleIndex
            }
            ::= { ibAclNamedUserTable 1 }

        IbAclNamedUserEntry ::=
            SEQUENCE
            {
                ibAclNamedUserRowStatus
                    RowStatus,
                ibAclNamedUserAct
                    RuleAction,
                ibAclNamedUserStartString
                    OCTET STRING,
                ibAclNamedUserL2String
                    OCTET STRING,
                ibAclNamedUserMplsString
                    OCTET STRING,
                ibAclNamedUserIPv4String
                    OCTET STRING,
                ibAclNamedUserIPv6String
                    OCTET STRING,
                ibAclNamedUserL4String
                    OCTET STRING,
                ibAclNamedUserL5String
                    OCTET STRING,
                ibAclNamedUserTimeRangeName
                    OCTET STRING,
                ibAclNamedUserCount
                    Unsigned32,
                ibAclNamedUserCountClear
                    CounterClear,
                ibAclNamedUserEnable
                    TruthValue,
                ibAclNamedUserComment
                    OCTET STRING,
                ibAclNamedUserLog
                    TruthValue,
                ibAclNamedUserCounting
                    TruthValue
             }

        ibAclNamedUserRowStatus OBJECT-TYPE
            SYNTAX RowStatus
            MAX-ACCESS read-create
            STATUS current
            DESCRIPTION
                "RowStatus."
            ::= { ibAclNamedUserEntry 1 }

        ibAclNamedUserAct OBJECT-TYPE
            SYNTAX RuleAction
            MAX-ACCESS read-create
            STATUS current
            DESCRIPTION
                "The action of user defined acl rule."
            ::= { ibAclNamedUserEntry 2 }

        ibAclNamedUserStartString OBJECT-TYPE
            SYNTAX OCTET STRING (SIZE(0..255))
            MAX-ACCESS read-create
            STATUS current
            DESCRIPTION
                "The rule, matching packets, input like this:
                 'RuleOffset','RuleString','RuleMask'.

                 RuleOffset: The value of this object is defined by product and
                 it indicates the offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: 10,10af,ffff.

                 Default value is zero-length.
                "
            ::= { ibAclNamedUserEntry 3 }

        ibAclNamedUserL2String OBJECT-TYPE
            SYNTAX OCTET STRING (SIZE(0..255))
            MAX-ACCESS read-create
            STATUS current
            DESCRIPTION
                "The rule, matching layer 2 packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { ibAclNamedUserEntry 4 }

        ibAclNamedUserMplsString OBJECT-TYPE
            SYNTAX OCTET STRING (SIZE(0..255))
            MAX-ACCESS read-create
            STATUS current
            DESCRIPTION
                "The rule, matching mpls packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { ibAclNamedUserEntry 5 }

        ibAclNamedUserIPv4String OBJECT-TYPE
            SYNTAX OCTET STRING (SIZE(0..255))
            MAX-ACCESS read-create
            STATUS current
            DESCRIPTION
                "The rule, matching IPv4 packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { ibAclNamedUserEntry 6 }

        ibAclNamedUserIPv6String OBJECT-TYPE
            SYNTAX OCTET STRING (SIZE(0..255))
            MAX-ACCESS read-create
            STATUS current
            DESCRIPTION
                "The rule, matching IPv6 packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { ibAclNamedUserEntry 7 }

        ibAclNamedUserL4String OBJECT-TYPE
            SYNTAX OCTET STRING (SIZE(0..255))
            MAX-ACCESS read-create
            STATUS current
            DESCRIPTION
                "The rule, matching layer 4 packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { ibAclNamedUserEntry 8 }

        ibAclNamedUserL5String OBJECT-TYPE
            SYNTAX OCTET STRING (SIZE(0..255))
            MAX-ACCESS read-create
            STATUS current
            DESCRIPTION
                "The rule, matching layer 5 packets, input like this:
                 'RuleOffset','RuleString','RuleMask'.

                 RuleOffset: The value is defined by product and
                 it indicates offset of the rule mask in the packet(unit: byte).

                 RuleString: The length of RuleString is defined by product.
                 The string must be hexadecimal.
                 The length of string must be multiple of 2.

                 RuleMask: The length of RuleMask is defined by product.
                 The string must be hexadecimal.
                 The length of string must be multiple of 2.

                 For example: '10','10af','ffff'.

                 Default value is zero-length.
                "
            ::= { ibAclNamedUserEntry 9 }

        ibAclNamedUserTimeRangeName OBJECT-TYPE
            SYNTAX OCTET STRING (SIZE(0..32))
            MAX-ACCESS read-create
            STATUS current
            DESCRIPTION
                "The Time-range of user acl rule.
                 Default value is zero-length."
            ::= { ibAclNamedUserEntry 10 }

        ibAclNamedUserCount OBJECT-TYPE
            SYNTAX Unsigned32
            MAX-ACCESS read-only
            STATUS current
            DESCRIPTION
                "The count of matched by the rule."
            ::= { ibAclNamedUserEntry 11 }

        ibAclNamedUserCountClear OBJECT-TYPE
            SYNTAX CounterClear
            MAX-ACCESS read-write
            STATUS current
            DESCRIPTION
                "Reset the value of counter."
            ::= { ibAclNamedUserEntry 12 }

        ibAclNamedUserEnable OBJECT-TYPE
            SYNTAX TruthValue
            MAX-ACCESS read-only
            STATUS current
            DESCRIPTION
                "The rule is active or not.
                 true : active
                 false : inactive
                "
            DEFVAL { false }
            ::= { ibAclNamedUserEntry 13 }

        ibAclNamedUserComment OBJECT-TYPE
            SYNTAX OCTET STRING (SIZE(0..127))
            MAX-ACCESS read-create
            STATUS current
            DESCRIPTION
                "The description of ACL rule.
                 Default value is Zero-length String.
                "
            ::= { ibAclNamedUserEntry 14 }

        ibAclNamedUserLog OBJECT-TYPE
            SYNTAX TruthValue
            MAX-ACCESS read-create
            STATUS current
            DESCRIPTION
                "The packet will be logged when it matches the rule.
                 It is disabled by default.
                "
            DEFVAL { false }
            ::= { ibAclNamedUserEntry 15 }

        ibAclNamedUserCounting OBJECT-TYPE
            SYNTAX TruthValue
            MAX-ACCESS read-create
            STATUS current
            DESCRIPTION
                "The packet will be counted when it matches the rule.
                 It is disabled by default.
                "
            DEFVAL { false }
            ::= { ibAclNamedUserEntry 16 }

--
-- Node of ibAclResourceGroup
--
        ibAclResourceGroup OBJECT IDENTIFIER ::= { ibAclMib2Objects 5 }
--
-- Nodes of ibAclResourceUsageTable
--
        ibAclResourceUsageTable OBJECT-TYPE
            SYNTAX SEQUENCE OF IbAclResourceUsageEntry
            MAX-ACCESS not-accessible
            STATUS current
            DESCRIPTION
                "The table shows ACL resource usage information.  Support for
                resource types that are denoted by ibAclResourceType object
                varies with products.  If a type is not supported, the
                corresponding row for the type will not be instantiated
                in this table.
                "
            ::= { ibAclResourceGroup 1 }

        ibAclResourceUsageEntry OBJECT-TYPE
            SYNTAX IbAclResourceUsageEntry
            MAX-ACCESS not-accessible
            STATUS current
            DESCRIPTION
                "Each row contains a brief description of the resource type,
                a port range associated with the chip, total, reserved, and
                configured amount of resource of this type, the percent of
                resource that has been allocated, and so on.
                "
            INDEX
            {
                ibAclResourceChassis,
                ibAclResourceSlot,
                ibAclResourceChip,
                ibAclResourceType
            }
            ::= { ibAclResourceUsageTable 1 }

        IbAclResourceUsageEntry ::=
            SEQUENCE
            {
                ibAclResourceChassis
                    Unsigned32,
                ibAclResourceSlot
                    Unsigned32,
                ibAclResourceChip
                    Unsigned32,
                ibAclResourceType
                    Integer32,
                ibAclPortRange
                    OCTET STRING,
                ibAclResourceTotal
                    Unsigned32,
                ibAclResourceReserved
                    Unsigned32,
                ibAclResourceConfigured
                    Unsigned32,
                ibAclResourceUsagePercent
                    Unsigned32,
                ibAclResourceTypeDescription
                    OCTET STRING
            }

        ibAclResourceChassis OBJECT-TYPE
            SYNTAX Unsigned32
            MAX-ACCESS not-accessible
            STATUS current
            DESCRIPTION
                "The chassis number.  On a centralized or distributed device,
                the value for this node is always zero.
                "
            ::= { ibAclResourceUsageEntry 1 }

        ibAclResourceSlot OBJECT-TYPE
            SYNTAX Unsigned32
            MAX-ACCESS not-accessible
            STATUS current
            DESCRIPTION
                "The slot number.  On a centralized device, the value for
                this node is always zero."
            ::= { ibAclResourceUsageEntry 2 }

        ibAclResourceChip OBJECT-TYPE
            SYNTAX Unsigned32
            MAX-ACCESS not-accessible
            STATUS current
            DESCRIPTION
                "The chip number.  On a single chip device, the value for
                this node is always zero."
            ::= { ibAclResourceUsageEntry 3 }

        ibAclResourceType OBJECT-TYPE
            SYNTAX Integer32 (1..255)
            MAX-ACCESS not-accessible
            STATUS current
            DESCRIPTION
                "The resource type."
            ::= { ibAclResourceUsageEntry 4 }

        ibAclPortRange OBJECT-TYPE
            SYNTAX OCTET STRING (SIZE(0..255))
            MAX-ACCESS read-only
            STATUS current
            DESCRIPTION
                "The port range associated with the chip.  Commas are used to
                separate multiple port ranges, for example, Ethernet1/2 to
                Ethernet1/12, Ethernet1/31 to Ethernet1/48.
                "
            ::= { ibAclResourceUsageEntry 5 }

        ibAclResourceTotal OBJECT-TYPE
            SYNTAX Unsigned32
            MAX-ACCESS read-only
            STATUS current
            DESCRIPTION
                "Total TCAM entries of the resource type."
            ::= { ibAclResourceUsageEntry 6 }

        ibAclResourceReserved OBJECT-TYPE
            SYNTAX Unsigned32
            MAX-ACCESS read-only
            STATUS current
            DESCRIPTION
                "The amount of reserved TCAM entries of the resource type."
            ::= { ibAclResourceUsageEntry 7 }

        ibAclResourceConfigured OBJECT-TYPE
            SYNTAX Unsigned32
            MAX-ACCESS read-only
            STATUS current
            DESCRIPTION
                "The amount of configured TCAM entries of the resource type."
            ::= { ibAclResourceUsageEntry 8 }

        ibAclResourceUsagePercent OBJECT-TYPE
            SYNTAX Unsigned32
            MAX-ACCESS read-only
            STATUS current
            DESCRIPTION
                "The percent of TCAM entries that have been used for
                this resource type.
                "
            ::= { ibAclResourceUsageEntry 9 }

        ibAclResourceTypeDescription OBJECT-TYPE
            SYNTAX OCTET STRING (SIZE(0..31))
            MAX-ACCESS read-only
            STATUS current
            DESCRIPTION
                "The description of this resource type."
            ::= { ibAclResourceUsageEntry 10 }

--
-- Node of ibAclIntervalGroup
--
        ibAclIntervalGroup OBJECT IDENTIFIER ::= { ibAclMib2Objects 6 }
--
-- Nodes of ibAclIntervalTable
--
        ibAclIntervalTable OBJECT-TYPE
            SYNTAX SEQUENCE OF IbAclIntervalEntry
            MAX-ACCESS not-accessible
            STATUS current
            DESCRIPTION
                "Log interval table."
            ::= { ibAclIntervalGroup 1 }

        ibAclIntervalEntry OBJECT-TYPE
            SYNTAX IbAclIntervalEntry
            MAX-ACCESS not-accessible
            STATUS current
            DESCRIPTION
                "Log interval entry."
            INDEX
            {
                ibAclIntervalType
            }
            ::= { ibAclIntervalTable 1 }

        IbAclIntervalEntry ::=
            SEQUENCE
            {
                ibAclIntervalType
                    INTEGER,
                ibAclIntervalValue
                    Integer32,
                ibAclIntervalRowStatus
                    RowStatus
            }

        ibAclIntervalType OBJECT-TYPE
            SYNTAX INTEGER
            {
                logging(1),
                trap(2)
            }
            MAX-ACCESS not-accessible
            STATUS current
            DESCRIPTION
                "The types of the interval specified for generating
                packet filtering logs or traps.
                "
            ::= { ibAclIntervalEntry 1 }

        ibAclIntervalValue OBJECT-TYPE
            SYNTAX Integer32 (5..1440)
            MAX-ACCESS read-create
            STATUS current
            DESCRIPTION
                "The value of interval.
                It must be a multiple of 5 and in the range of 5 to 1440.
                "
            ::= { ibAclIntervalEntry 2 }

        ibAclIntervalRowStatus OBJECT-TYPE
            SYNTAX RowStatus
            MAX-ACCESS read-create
            STATUS current
            DESCRIPTION
                "RowStatus."
            ::= { ibAclIntervalEntry 3 }

--
-- Node of ibAclPacketFilterObjects
--
        ibAclPacketFilterObjects OBJECT IDENTIFIER ::= { ibAcl 3 }

        ibPfilterScalarGroup OBJECT IDENTIFIER ::= { ibAclPacketFilterObjects 1 }

        ibPfilterDefaultAction OBJECT-TYPE
            SYNTAX INTEGER
            {
                permit(1),
                deny(2)
            }
            MAX-ACCESS read-write
            STATUS current
            DESCRIPTION
                "The default action of packet filter.
                By default, the packet filter permits packets that do not match
                any ACL rule to pass.
                "
            ::= { ibPfilterScalarGroup 1 }

        ibPfilterProcessingStatus OBJECT-TYPE
            SYNTAX INTEGER
            {
                processing(1),
                done(2)
            }
            MAX-ACCESS read-only
            STATUS current
            DESCRIPTION
                "This object shows the status of the system when applying packet
                filter.  It is forbidden to set or read in ibAclPacketFilterObjects
                MIB module when the value is processing.
                "
            ::= { ibPfilterScalarGroup 2 }

--
-- Nodes of ibPfilterApplyTable
--
        ibPfilterApplyTable OBJECT-TYPE
            SYNTAX SEQUENCE OF IbPfilterApplyEntry
            MAX-ACCESS not-accessible
            STATUS current
            DESCRIPTION
                "A table of packet filter application.
                It's not supported to set default action on an entity,
                but supported to enable hardware count of default action
                on an entity.
                "
            ::= { ibAclPacketFilterObjects 2 }

        ibPfilterApplyEntry OBJECT-TYPE
            SYNTAX IbPfilterApplyEntry
            MAX-ACCESS not-accessible
            STATUS current
            DESCRIPTION
                "Packet filter application information entry."
            INDEX
            {
                ibPfilterApplyObjType,
                ibPfilterApplyObjIndex,
                ibPfilterApplyDirection,
                ibPfilterApplyAclType,
                ibPfilterApplyAclIndex
            }
            ::= { ibPfilterApplyTable 1 }

        IbPfilterApplyEntry ::=
        SEQUENCE
        {
            ibPfilterApplyObjType
                INTEGER,
            ibPfilterApplyObjIndex
                Integer32,
            ibPfilterApplyDirection
                DirectionType,
            ibPfilterApplyAclType
                INTEGER,
            ibPfilterApplyAclIndex
                Integer32,
            ibPfilterApplyHardCount
                TruthValue,
            ibPfilterApplySequence
                Unsigned32,
            ibPfilterApplyCountClear
                CounterClear,
            ibPfilterApplyRowStatus
                RowStatus
        }

        ibPfilterApplyObjType OBJECT-TYPE
            SYNTAX INTEGER
            {
                interface(1),
                vlan(2),
                global(3)
            }
            MAX-ACCESS not-accessible
            STATUS current
            DESCRIPTION
                "The object type of packet filter application.
                interface: Apply an ACL to the interface to filter packets.
                vlan: Apply an ACL to the VLAN to filter packets.
                global: Apply an ACL globally to filter packets.
                "
            ::= { ibPfilterApplyEntry 1 }

        ibPfilterApplyObjIndex OBJECT-TYPE
            SYNTAX Integer32 (0..2147483647)
            MAX-ACCESS not-accessible
            STATUS current
            DESCRIPTION
                "The object ID of packet filter application.
                Interface: interface index, equal to ifIndex
                VLAN: VLAN ID, 1..4094
                Global: 0
                "
            ::= { ibPfilterApplyEntry 2 }

        ibPfilterApplyDirection OBJECT-TYPE
            SYNTAX DirectionType
            MAX-ACCESS not-accessible
            STATUS current
            DESCRIPTION
                "The direction of packet filter application."
            ::= { ibPfilterApplyEntry 3 }

        ibPfilterApplyAclType OBJECT-TYPE
            SYNTAX INTEGER
            {
                ipv4(1),
                ipv6(2),
                default(3),
                mac(4),
                user(5)
            }
            MAX-ACCESS not-accessible
            STATUS current
            DESCRIPTION
                "ACL Type: IPv4, IPv6, default action, MAC, and user.
                Take default action as a special ACL group.
                "
            ::= { ibPfilterApplyEntry 4 }

        ibPfilterApplyAclIndex OBJECT-TYPE
            SYNTAX Integer32  (0|2000..5999)
            MAX-ACCESS not-accessible
            STATUS current
            DESCRIPTION
                "The ACL group index.
                Basic type: 2000..2999
                Advanced type: 3000..3999
                MAC type: 4000..4999
                User type: 5000..5999
                Default action type: 0
                "
            ::= { ibPfilterApplyEntry 5 }

        ibPfilterApplyHardCount OBJECT-TYPE
            SYNTAX TruthValue
            MAX-ACCESS read-create
            STATUS current
            DESCRIPTION
                "Hardware count flag.
                true: enable hardware count
                false: disable hardware count
                "
            DEFVAL { false }
            ::= { ibPfilterApplyEntry 6 }

        ibPfilterApplySequence OBJECT-TYPE
            SYNTAX Unsigned32
            MAX-ACCESS read-only
            STATUS current
            DESCRIPTION
                "The configure sequence of packet filter application."
            ::= { ibPfilterApplyEntry 7 }

        ibPfilterApplyCountClear OBJECT-TYPE
            SYNTAX CounterClear
            MAX-ACCESS read-write
            STATUS current
            DESCRIPTION
                "Clear the value of counters."
            ::= { ibPfilterApplyEntry 8 }

        ibPfilterApplyRowStatus OBJECT-TYPE
            SYNTAX RowStatus
            MAX-ACCESS read-create
            STATUS current
            DESCRIPTION
                "RowStatus."
            ::= { ibPfilterApplyEntry 9 }

--
-- Nodes of ibPfilterAclGroupRunInfoTable
--
        ibPfilterAclGroupRunInfoTable OBJECT-TYPE
            SYNTAX SEQUENCE OF IbPfilterAclGroupRunInfoEntry
            MAX-ACCESS not-accessible
            STATUS current
            DESCRIPTION
                "A table of group running information of ACLs
                for packet filtering.  If hardware count function is not
                supported or not enabled to the packet filter application, the
                statistics entry will be zero.
                "
            ::= { ibAclPacketFilterObjects 3 }

        ibPfilterAclGroupRunInfoEntry OBJECT-TYPE
            SYNTAX IbPfilterAclGroupRunInfoEntry
            MAX-ACCESS not-accessible
            STATUS current
            DESCRIPTION
                "ACL group running information entry for packet filtering."
            INDEX
            {
                ibPfilterRunApplyObjType,
                ibPfilterRunApplyObjIndex,
                ibPfilterRunApplyDirection,
                ibPfilterRunApplyAclType,
                ibPfilterRunApplyAclIndex
            }
            ::= { ibPfilterAclGroupRunInfoTable 1 }

        IbPfilterAclGroupRunInfoEntry ::=
        SEQUENCE
        {
            ibPfilterRunApplyObjType
                INTEGER,
            ibPfilterRunApplyObjIndex
                Integer32,
            ibPfilterRunApplyDirection
                DirectionType,
            ibPfilterRunApplyAclType
                INTEGER,
            ibPfilterRunApplyAclIndex
                Integer32,
            ibPfilterAclGroupStatus
                INTEGER,
            ibPfilterAclGroupCountStatus
                INTEGER,
            ibPfilterAclGroupPermitPkts
                Counter64,
            ibPfilterAclGroupPermitBytes
                Counter64,
            ibPfilterAclGroupDenyPkts
                Counter64,
            ibPfilterAclGroupDenyBytes
                Counter64
        }

        ibPfilterRunApplyObjType OBJECT-TYPE
            SYNTAX INTEGER
            {
                interface(1),
                vlan(2),
                global(3)
            }
            MAX-ACCESS not-accessible
            STATUS current
            DESCRIPTION
                "The object type of packet filter application.
                interface: Apply an ACL to the interface to filter packets.
                vlan: Apply an ACL to the VLAN to filter packets.
                global: Apply an ACL globally to filter packets.
                "
            ::= { ibPfilterAclGroupRunInfoEntry 1 }

        ibPfilterRunApplyObjIndex OBJECT-TYPE
            SYNTAX Integer32 (0..2147483647)
            MAX-ACCESS not-accessible
            STATUS current
            DESCRIPTION
                "The object ID of packet filter application.
                Interface: interface index, equal to ifIndex
                VLAN: VLAN ID, 1..4094
                Global: 0
                "
            ::= { ibPfilterAclGroupRunInfoEntry 2 }

        ibPfilterRunApplyDirection OBJECT-TYPE
            SYNTAX DirectionType
            MAX-ACCESS not-accessible
            STATUS current
            DESCRIPTION
                "The direction of packet filter application."
            ::= { ibPfilterAclGroupRunInfoEntry 3 }

        ibPfilterRunApplyAclType OBJECT-TYPE
            SYNTAX INTEGER
            {
                ipv4(1),
                ipv6(2),
                default(3),
                mac(4),
                user(5)
            }
            MAX-ACCESS not-accessible
            STATUS current
            DESCRIPTION
                "ACL Type: IPv4, IPv6, default action, MAC, and user.
                Take default action as a special ACL group.
                "
            ::= { ibPfilterAclGroupRunInfoEntry 4 }

        ibPfilterRunApplyAclIndex OBJECT-TYPE
            SYNTAX Integer32  (1..3|2000..5999)
            MAX-ACCESS not-accessible
            STATUS current
            DESCRIPTION
                "The ACL group index.
                Basic type: 2000..2999
                Advanced type: 3000..3999
                MAC type: 4000..4999
                User type: 5000..5999
                MAC default action: 1
                IPv4 default action: 2
                IPv6 default action: 3
                "
            ::= { ibPfilterAclGroupRunInfoEntry 5 }

        ibPfilterAclGroupStatus OBJECT-TYPE
            SYNTAX INTEGER
            {
                success(1),
                failed(2),
                partialSuccess(3)
            }
            MAX-ACCESS read-only
            STATUS current
            DESCRIPTION
                "The status of ACL group applied.
                success: ACL applied successfully on all slots
                failed: failed to apply ACL on all slots
                partialSuccess: failed to apply ACL on some slots
                "
            ::= { ibPfilterAclGroupRunInfoEntry 6 }

        ibPfilterAclGroupCountStatus OBJECT-TYPE
            SYNTAX INTEGER
            {
                success(1),
                failed(2),
                partialSuccess(3)
            }
            MAX-ACCESS read-only
            STATUS current
            DESCRIPTION
                "The status of enabling hardware count.  If hardware count is
                not enabled, it returns success.
                success: enable hardware count successfully on all slots
                failed: failed to enable hardware count on all slots
                partialSuccess: failed to enable hardware count on some slots
                "
            ::= { ibPfilterAclGroupRunInfoEntry 7 }

        ibPfilterAclGroupPermitPkts OBJECT-TYPE
            SYNTAX Counter64
            MAX-ACCESS read-only
            STATUS current
            DESCRIPTION
                "The number of packets permitted."
            ::= { ibPfilterAclGroupRunInfoEntry 8 }

        ibPfilterAclGroupPermitBytes OBJECT-TYPE
            SYNTAX Counter64
            MAX-ACCESS read-only
            STATUS current
            DESCRIPTION
                "The number of bytes permitted."
            ::= { ibPfilterAclGroupRunInfoEntry 9 }

        ibPfilterAclGroupDenyPkts OBJECT-TYPE
            SYNTAX Counter64
            MAX-ACCESS read-only
            STATUS current
            DESCRIPTION
                "The number of packets denied."
            ::= { ibPfilterAclGroupRunInfoEntry 10 }

        ibPfilterAclGroupDenyBytes OBJECT-TYPE
            SYNTAX Counter64
            MAX-ACCESS read-only
            STATUS current
            DESCRIPTION
                "The number of bytes denied."
            ::= { ibPfilterAclGroupRunInfoEntry 11 }

--
-- Nodes of ibPfilterAclRuleRunInfoTable
--
        ibPfilterAclRuleRunInfoTable OBJECT-TYPE
            SYNTAX SEQUENCE OF IbPfilterAclRuleRunInfoEntry
            MAX-ACCESS not-accessible
            STATUS current
            DESCRIPTION
                "A table of rule's running information of ACLs
                for packet filtering.  If hardware count function is not
                supported or not enabled to the packet filter application, the
                ibPfilterAclRuleMatchPackets and ibPfilterAclRuleMatchBytes
                will be zero.
                "
            ::= { ibAclPacketFilterObjects 4 }

        ibPfilterAclRuleRunInfoEntry OBJECT-TYPE
            SYNTAX IbPfilterAclRuleRunInfoEntry
            MAX-ACCESS not-accessible
            STATUS current
            DESCRIPTION
                "ACL rule's running information entry."
            INDEX
            {
                ibPfilterRunApplyObjType,
                ibPfilterRunApplyObjIndex,
                ibPfilterRunApplyDirection,
                ibPfilterRunApplyAclType,
                ibPfilterRunApplyAclIndex,
                ibPfilterAclRuleIndex
            }
            ::= { ibPfilterAclRuleRunInfoTable 1 }

        IbPfilterAclRuleRunInfoEntry ::=
        SEQUENCE
        {
            ibPfilterAclRuleIndex
                Integer32,
            ibPfilterAclRuleStatus
                INTEGER,
            ibPfilterAclRuleCountStatus
                INTEGER,
            ibPfilterAclRuleMatchPackets
                Counter64,
            ibPfilterAclRuleMatchBytes
                Counter64
        }

        ibPfilterAclRuleIndex OBJECT-TYPE
            SYNTAX Integer32 (0..65534)
            MAX-ACCESS not-accessible
            STATUS current
            DESCRIPTION
                "The ACL rule index."
            ::= { ibPfilterAclRuleRunInfoEntry 1 }

        ibPfilterAclRuleStatus OBJECT-TYPE
            SYNTAX INTEGER
            {
                success(1),
                failed(2),
                partialSuccess(3)
            }
            MAX-ACCESS read-only
            STATUS current
            DESCRIPTION
                "The status of rule application.
                success: rule applied successfully on all slots
                failed: failed to apply rule on all slots
                partialSuccess: failed to apply rule on some slots
                "
            ::= { ibPfilterAclRuleRunInfoEntry 2 }

        ibPfilterAclRuleCountStatus OBJECT-TYPE
            SYNTAX INTEGER
            {
                success(1),
                failed(2),
                partialSuccess(3)
            }
            MAX-ACCESS read-only
            STATUS current
            DESCRIPTION
                "The status of enabling rule's hardware count.
                If hardware count is not enabled, it returns success.
                success: enable hardware count successfully on all slots
                failed: failed to enable hardware count on all slots
                partialSuccess: failed to enable hardware count on some slots
                "
            ::= { ibPfilterAclRuleRunInfoEntry 3 }

        ibPfilterAclRuleMatchPackets OBJECT-TYPE
            SYNTAX Counter64
            MAX-ACCESS read-only
            STATUS current
            DESCRIPTION
                "The number of packets matched."
            ::= { ibPfilterAclRuleRunInfoEntry 4 }

       ibPfilterAclRuleMatchBytes OBJECT-TYPE
            SYNTAX Counter64
            MAX-ACCESS read-only
            STATUS current
            DESCRIPTION
                "The number of bytes matched."
            ::= { ibPfilterAclRuleRunInfoEntry 5 }

--
-- Nodes of ibPfilterStatisticSumTable
--
        ibPfilterStatisticSumTable OBJECT-TYPE
            SYNTAX SEQUENCE OF IbPfilterStatisticSumEntry
            MAX-ACCESS not-accessible
            STATUS current
            DESCRIPTION
                "A table of ACL rule's sum statistics information,
                accumulated by all entity application on all slots.
                "
            ::= { ibAclPacketFilterObjects 5 }

        ibPfilterStatisticSumEntry OBJECT-TYPE
            SYNTAX IbPfilterStatisticSumEntry
            MAX-ACCESS not-accessible
            STATUS current
            DESCRIPTION
                "ACL rule's sum statistics information entry."
            INDEX
            {
                ibPfilterSumDirection,
                ibPfilterSumAclType,
                ibPfilterSumAclIndex,
                ibPfilterSumRuleIndex
            }
            ::= { ibPfilterStatisticSumTable 1 }

        IbPfilterStatisticSumEntry ::=
        SEQUENCE
        {
            ibPfilterSumDirection
                DirectionType,
            ibPfilterSumAclType
                INTEGER,
            ibPfilterSumAclIndex
                Integer32,
            ibPfilterSumRuleIndex
                Integer32,
            ibPfilterSumRuleMatchPackets
                Counter64,
            ibPfilterSumRuleMatchBytes
                Counter64
        }

        ibPfilterSumDirection OBJECT-TYPE
            SYNTAX DirectionType
            MAX-ACCESS not-accessible
            STATUS current
            DESCRIPTION
                "The direction of application."
            ::= { ibPfilterStatisticSumEntry 1 }

        ibPfilterSumAclType OBJECT-TYPE
            SYNTAX INTEGER
            {
                ipv4(1),
                ipv6(2),
                mac(3),
                user(4)
            }
            MAX-ACCESS not-accessible
            STATUS current
            DESCRIPTION
                "ACL type: IPv4, IPv6, MAC, and user."
            ::= { ibPfilterStatisticSumEntry 2 }

        ibPfilterSumAclIndex OBJECT-TYPE
            SYNTAX Integer32 (2000..5999)
            MAX-ACCESS not-accessible
            STATUS current
            DESCRIPTION
                "The ACL group index.
                Basic type: 2000..2999
                Advanced type: 3000..3999
                MAC type: 4000..4999
                User type: 5000..5999
                "
            ::= { ibPfilterStatisticSumEntry 3 }

        ibPfilterSumRuleIndex OBJECT-TYPE
            SYNTAX Integer32 (0..65534)
            MAX-ACCESS not-accessible
            STATUS current
            DESCRIPTION
                "The ACL rule index."
            ::= { ibPfilterStatisticSumEntry 4 }

        ibPfilterSumRuleMatchPackets OBJECT-TYPE
            SYNTAX Counter64
            MAX-ACCESS read-only
            STATUS current
            DESCRIPTION
                "The sum number of packets matched the ACL rule."
            ::= { ibPfilterStatisticSumEntry 5 }

        ibPfilterSumRuleMatchBytes OBJECT-TYPE
            SYNTAX Counter64
            MAX-ACCESS read-only
            STATUS current
            DESCRIPTION
                "The sum number of bytes matched the ACL rule."
            ::= { ibPfilterStatisticSumEntry 6 }

--
-- Nodes of ibPfilter2ApplyTable
--
        ibPfilter2ApplyTable OBJECT-TYPE
            SYNTAX SEQUENCE OF IbPfilter2ApplyEntry
            MAX-ACCESS not-accessible
            STATUS current
            DESCRIPTION
                "A table of packet filter application.
                It's not supported to set default action on an entity,
                but supported to enable hardware count of default action
                on an entity.
                "
            ::= { ibAclPacketFilterObjects 6 }

        ibPfilter2ApplyEntry OBJECT-TYPE
            SYNTAX IbPfilter2ApplyEntry
            MAX-ACCESS not-accessible
            STATUS current
            DESCRIPTION
                "Packet filter application information entry."
            INDEX
            {
                ibPfilter2ApplyObjType,
                ibPfilter2ApplyObjIndex,
                ibPfilter2ApplyDirection,
                ibPfilter2ApplyAclType,
                ibPfilter2ApplyAclIndex
            }
            ::= { ibPfilter2ApplyTable 1 }

        IbPfilter2ApplyEntry ::=
        SEQUENCE
        {
            ibPfilter2ApplyObjType
                INTEGER,
            ibPfilter2ApplyObjIndex
                Integer32,
            ibPfilter2ApplyDirection
                DirectionType,
            ibPfilter2ApplyAclType
                INTEGER,
            ibPfilter2ApplyAclIndex
                OCTET STRING,
            ibPfilter2ApplyHardCount
                TruthValue,
            ibPfilter2ApplySequence
                Unsigned32,
            ibPfilter2ApplyCountClear
                CounterClear,
            ibPfilter2ApplyRowStatus
                RowStatus
        }

        ibPfilter2ApplyObjType OBJECT-TYPE
            SYNTAX INTEGER
            {
                interface(1),
                vlan(2),
                global(3)
            }
            MAX-ACCESS accessible-for-notify
            STATUS current
            DESCRIPTION
                "The object type of packet filter application.
                interface: Apply an ACL to the interface to filter packets.
                vlan: Apply an ACL to the VLAN to filter packets.
                global: Apply an ACL globally to filter packets.
                "
            ::= { ibPfilter2ApplyEntry 1 }

        ibPfilter2ApplyObjIndex OBJECT-TYPE
            SYNTAX Integer32 (0..2147483647)
            MAX-ACCESS accessible-for-notify
            STATUS current
            DESCRIPTION
                "The object ID of packet filter application.
                Interface: interface index, equal to ifIndex
                VLAN: VLAN ID, 1..4094
                Global: 0
                "
            ::= { ibPfilter2ApplyEntry 2 }

        ibPfilter2ApplyDirection OBJECT-TYPE
            SYNTAX DirectionType
            MAX-ACCESS accessible-for-notify
            STATUS current
            DESCRIPTION
                "The direction of packet filter application."
            ::= { ibPfilter2ApplyEntry 3 }

        ibPfilter2ApplyAclType OBJECT-TYPE
            SYNTAX INTEGER
            {
                ipv4(1),
                ipv6(2),
                default(3),
                mac(4),
                user(5)
            }
            MAX-ACCESS accessible-for-notify
            STATUS current
            DESCRIPTION
                "ACL Type: IPv4, IPv6, default action, MAC, and user.
                Take default action as a special ACL group.
                "
            ::= { ibPfilter2ApplyEntry 4 }

        ibPfilter2ApplyAclIndex OBJECT-TYPE
            SYNTAX OCTET STRING (SIZE(1..63))
            MAX-ACCESS accessible-for-notify
            STATUS current
            DESCRIPTION
                "The index of ACL group used by packet-filter.
                If the specified string comprises only digits, it is converted
                into a numerical sequence in decimal notation, and regarded as
                an ACL group index or a default action.  If the string is a
                character string beginning with an English letter, it is
                regarded as an ACL group name.

                Group index range and default action:
                    Basic type: 2000..2999
                    Advanced type: 3000..3999
                    MAC type: 4000..4999
                    User type: 5000..5999
                    Default action type: 0
                "
            ::= { ibPfilter2ApplyEntry 5 }

        ibPfilter2ApplyHardCount OBJECT-TYPE
            SYNTAX TruthValue
            MAX-ACCESS read-create
            STATUS current
            DESCRIPTION
                "Hardware count flag.
                true: enable hardware count
                false: disable hardware count
                "
            DEFVAL { false }
            ::= { ibPfilter2ApplyEntry 6 }

        ibPfilter2ApplySequence OBJECT-TYPE
            SYNTAX Unsigned32
            MAX-ACCESS read-only
            STATUS current
            DESCRIPTION
                "The configure sequence of packet filter application."
            ::= { ibPfilter2ApplyEntry 7 }

        ibPfilter2ApplyCountClear OBJECT-TYPE
            SYNTAX CounterClear
            MAX-ACCESS read-write
            STATUS current
            DESCRIPTION
                "Clear the value of counters."
            DEFVAL { nouse }
            ::= { ibPfilter2ApplyEntry 8 }

        ibPfilter2ApplyRowStatus OBJECT-TYPE
            SYNTAX RowStatus
            MAX-ACCESS read-create
            STATUS current
            DESCRIPTION
                "RowStatus."
            ::= { ibPfilter2ApplyEntry 9 }

--
-- Nodes of ibPfilter2AclGroupRunInfoTable
--
        ibPfilter2AclGroupRunInfoTable OBJECT-TYPE
            SYNTAX SEQUENCE OF IbPfilter2AclGroupRunInfoEntry
            MAX-ACCESS not-accessible
            STATUS current
            DESCRIPTION
                "A table of group running information of ACLs
                for packet filtering.  If hardware count function is not
                supported or not enabled to the packet filter application, the
                statistics entry will be zero.
                "
            ::= { ibAclPacketFilterObjects 7 }

        ibPfilter2AclGroupRunInfoEntry OBJECT-TYPE
            SYNTAX IbPfilter2AclGroupRunInfoEntry
            MAX-ACCESS not-accessible
            STATUS current
            DESCRIPTION
                "ACL group running information entry for packet filtering."
            INDEX
            {
                ibPfilter2RunApplyObjType,
                ibPfilter2RunApplyObjIndex,
                ibPfilter2RunApplyDirection,
                ibPfilter2RunApplyAclType,
                ibPfilter2RunApplyAclIndex
            }
            ::= { ibPfilter2AclGroupRunInfoTable 1 }

        IbPfilter2AclGroupRunInfoEntry ::=
        SEQUENCE
        {
            ibPfilter2RunApplyObjType
                INTEGER,
            ibPfilter2RunApplyObjIndex
                Integer32,
            ibPfilter2RunApplyDirection
                DirectionType,
            ibPfilter2RunApplyAclType
                INTEGER,
            ibPfilter2RunApplyAclIndex
                OCTET STRING,
            ibPfilter2AclGroupStatus
                INTEGER,
            ibPfilter2AclGroupCountStatus
                INTEGER,
            ibPfilter2AclGroupPermitPkts
                Counter64,
            ibPfilter2AclGroupPermitBytes
                Counter64,
            ibPfilter2AclGroupDenyPkts
                Counter64,
            ibPfilter2AclGroupDenyBytes
                Counter64
        }

        ibPfilter2RunApplyObjType OBJECT-TYPE
            SYNTAX INTEGER
            {
                interface(1),
                vlan(2),
                global(3)
            }
            MAX-ACCESS not-accessible
            STATUS current
            DESCRIPTION
                "The object type of packet filter application.
                interface: Apply an ACL to the interface to filter packets.
                vlan: Apply an ACL to the VLAN to filter packets.
                global: Apply an ACL globally to filter packets.
                "
            ::= { ibPfilter2AclGroupRunInfoEntry 1 }

        ibPfilter2RunApplyObjIndex OBJECT-TYPE
            SYNTAX Integer32 (0..2147483647)
            MAX-ACCESS not-accessible
            STATUS current
            DESCRIPTION
                "The object ID of packet filter application.
                Interface: interface index, equal to ifIndex
                VLAN: VLAN ID, 1..4094
                Global: 0
                "
            ::= { ibPfilter2AclGroupRunInfoEntry 2 }

        ibPfilter2RunApplyDirection OBJECT-TYPE
            SYNTAX DirectionType
            MAX-ACCESS not-accessible
            STATUS current
            DESCRIPTION
                "The direction of packet filter application."
            ::= { ibPfilter2AclGroupRunInfoEntry 3 }

        ibPfilter2RunApplyAclType OBJECT-TYPE
            SYNTAX INTEGER
            {
                ipv4(1),
                ipv6(2),
                default(3),
                mac(4),
                user(5)
            }
            MAX-ACCESS not-accessible
            STATUS current
            DESCRIPTION
                "ACL Type: IPv4, IPv6, default action, MAC, and user.
                Take default action as a special ACL group.
                "
            ::= { ibPfilter2AclGroupRunInfoEntry 4 }

        ibPfilter2RunApplyAclIndex OBJECT-TYPE
            SYNTAX OCTET STRING (SIZE(1..63))
            MAX-ACCESS not-accessible
            STATUS current
            DESCRIPTION
                "The index of ACL group used by packet-filter.
                If the specified string comprises only digits, it is converted
                into a numerical sequence in decimal notation, and regarded as
                an ACL group index or a default action.  If the string is a
                character string beginning with an English letter, it is
                regarded as an ACL group name.

                Group index range and default action:
                    Basic type: 2000..2999
                    Advanced type: 3000..3999
                    MAC type: 4000..4999
                    User type: 5000..5999
                    MAC default action: 1
                    IPv4 default action: 2
                    IPv6 default action: 3
                "
            ::= { ibPfilter2AclGroupRunInfoEntry 5 }

        ibPfilter2AclGroupStatus OBJECT-TYPE
            SYNTAX INTEGER
            {
                success(1),
                failed(2),
                partialSuccess(3)
            }
            MAX-ACCESS read-only
            STATUS current
            DESCRIPTION
                "The status of ACL group applied.
                success: ACL applied successfully on all slots
                failed: failed to apply ACL on all slots
                partialSuccess: failed to apply ACL on some slots
                "
            ::= { ibPfilter2AclGroupRunInfoEntry 6 }

        ibPfilter2AclGroupCountStatus OBJECT-TYPE
            SYNTAX INTEGER
            {
                success(1),
                failed(2),
                partialSuccess(3)
            }
            MAX-ACCESS read-only
            STATUS current
            DESCRIPTION
                "The status of enabling hardware count.  If hardware count is
                not enabled, it returns success.
                success: enable hardware count successfully on all slots
                failed: failed to enable hardware count on all slots
                partialSuccess: failed to enable hardware count on some slots
                "
            ::= { ibPfilter2AclGroupRunInfoEntry 7 }

        ibPfilter2AclGroupPermitPkts OBJECT-TYPE
            SYNTAX Counter64
            MAX-ACCESS read-only
            STATUS current
            DESCRIPTION
                "The number of packets permitted."
            ::= { ibPfilter2AclGroupRunInfoEntry 8 }

        ibPfilter2AclGroupPermitBytes OBJECT-TYPE
            SYNTAX Counter64
            MAX-ACCESS read-only
            STATUS current
            DESCRIPTION
                "The number of bytes permitted."
            ::= { ibPfilter2AclGroupRunInfoEntry 9 }

        ibPfilter2AclGroupDenyPkts OBJECT-TYPE
            SYNTAX Counter64
            MAX-ACCESS read-only
            STATUS current
            DESCRIPTION
                "The number of packets denied."
            ::= { ibPfilter2AclGroupRunInfoEntry 10 }

        ibPfilter2AclGroupDenyBytes OBJECT-TYPE
            SYNTAX Counter64
            MAX-ACCESS read-only
            STATUS current
            DESCRIPTION
                "The number of bytes denied."
            ::= { ibPfilter2AclGroupRunInfoEntry 11 }

--
-- Nodes of ibPfilter2AclRuleRunInfoTable
--
        ibPfilter2AclRuleRunInfoTable OBJECT-TYPE
            SYNTAX SEQUENCE OF IbPfilter2AclRuleRunInfoEntry
            MAX-ACCESS not-accessible
            STATUS current
            DESCRIPTION
                "A table of rule's running information of ACLs
                for packet filtering.  If hardware count function is not
                supported or not enabled to the packet filter application, the
                ibPfilter2AclRuleMatchPackets and ibPfilter2AclRuleMatchBytes
                will be zero.
                "
            ::= { ibAclPacketFilterObjects 8 }

        ibPfilter2AclRuleRunInfoEntry OBJECT-TYPE
            SYNTAX IbPfilter2AclRuleRunInfoEntry
            MAX-ACCESS not-accessible
            STATUS current
            DESCRIPTION
                "ACL rule's running information entry."
            INDEX
            {
                ibPfilter2RunApplyObjType,
                ibPfilter2RunApplyObjIndex,
                ibPfilter2RunApplyDirection,
                ibPfilter2RunApplyAclType,
                ibPfilter2RunApplyAclIndex,
                ibPfilter2AclRuleIndex
            }
            ::= { ibPfilter2AclRuleRunInfoTable 1 }

        IbPfilter2AclRuleRunInfoEntry ::=
        SEQUENCE
        {
            ibPfilter2AclRuleIndex
                Integer32,
            ibPfilter2AclRuleStatus
                INTEGER,
            ibPfilter2AclRuleCountStatus
                INTEGER,
            ibPfilter2AclRuleMatchPackets
                Counter64,
            ibPfilter2AclRuleMatchBytes
                Counter64
        }

        ibPfilter2AclRuleIndex OBJECT-TYPE
            SYNTAX Integer32 (0..65534)
            MAX-ACCESS accessible-for-notify
            STATUS current
            DESCRIPTION
                "The ACL rule index."
            ::= { ibPfilter2AclRuleRunInfoEntry 1 }

        ibPfilter2AclRuleStatus OBJECT-TYPE
            SYNTAX INTEGER
            {
                success(1),
                failed(2),
                partialSuccess(3)
            }
            MAX-ACCESS read-only
            STATUS current
            DESCRIPTION
                "The status of rule application.
                success: rule applied successfully on all slots
                failed: failed to apply rule on all slots
                partialSuccess: failed to apply rule on some slots
                "
            ::= { ibPfilter2AclRuleRunInfoEntry 2 }

        ibPfilter2AclRuleCountStatus OBJECT-TYPE
            SYNTAX INTEGER
            {
                success(1),
                failed(2),
                partialSuccess(3)
            }
            MAX-ACCESS read-only
            STATUS current
            DESCRIPTION
                "The status of enabling rule's hardware count.
                If hardware count is not enabled, it returns success.
                success: enable hardware count successfully on all slots
                failed: failed to enable hardware count on all slots
                partialSuccess: failed to enable hardware count on some slots
                "
            ::= { ibPfilter2AclRuleRunInfoEntry 3 }

        ibPfilter2AclRuleMatchPackets OBJECT-TYPE
            SYNTAX Counter64
            MAX-ACCESS read-only
            STATUS current
            DESCRIPTION
                "The number of packets matched."
            ::= { ibPfilter2AclRuleRunInfoEntry 4 }

       ibPfilter2AclRuleMatchBytes OBJECT-TYPE
            SYNTAX Counter64
            MAX-ACCESS read-only
            STATUS current
            DESCRIPTION
                "The number of bytes matched."
            ::= { ibPfilter2AclRuleRunInfoEntry 5 }

--
-- Nodes of ibPfilter2StatisticSumTable
--
        ibPfilter2StatisticSumTable OBJECT-TYPE
            SYNTAX SEQUENCE OF IbPfilter2StatisticSumEntry
            MAX-ACCESS not-accessible
            STATUS current
            DESCRIPTION
                "A table of ACL rule's sum statistics information,
                accumulated by all entity application on all slots.
                "
            ::= { ibAclPacketFilterObjects 9 }

        ibPfilter2StatisticSumEntry OBJECT-TYPE
            SYNTAX IbPfilter2StatisticSumEntry
            MAX-ACCESS not-accessible
            STATUS current
            DESCRIPTION
                "ACL rule's sum statistics information entry."
            INDEX
            {
                ibPfilter2SumDirection,
                ibPfilter2SumAclType,
                ibPfilter2SumAclIndex,
                ibPfilter2SumRuleIndex
            }
            ::= { ibPfilter2StatisticSumTable 1 }

        IbPfilter2StatisticSumEntry ::=
        SEQUENCE
        {
            ibPfilter2SumDirection
                DirectionType,
            ibPfilter2SumAclType
                INTEGER,
            ibPfilter2SumAclIndex
                OCTET STRING,
            ibPfilter2SumRuleIndex
                Integer32,
            ibPfilter2SumRuleMatchPackets
                Counter64,
            ibPfilter2SumRuleMatchBytes
                Counter64
        }

        ibPfilter2SumDirection OBJECT-TYPE
            SYNTAX DirectionType
            MAX-ACCESS not-accessible
            STATUS current
            DESCRIPTION
                "The direction of application."
            ::= { ibPfilter2StatisticSumEntry 1 }

        ibPfilter2SumAclType OBJECT-TYPE
            SYNTAX INTEGER
            {
                ipv4(1),
                ipv6(2),
                mac(3),
                user(4)
            }
            MAX-ACCESS not-accessible
            STATUS current
            DESCRIPTION
                "ACL type: IPv4, IPv6, MAC, and user."
            ::= { ibPfilter2StatisticSumEntry 2 }

        ibPfilter2SumAclIndex OBJECT-TYPE
            SYNTAX OCTET STRING (SIZE(1..63))
            MAX-ACCESS not-accessible
            STATUS current
            DESCRIPTION
                "The index of ACL group used by packet-filter.
                If the specified string comprises only digits, it is converted
                into a numerical sequence in decimal notation, and regarded as
                an ACL group index.  If the string is a character string
                beginning with an English letter, it is regarded as an ACL
                group name.

                Group index range and default action:
                    Basic type: 2000..2999
                    Advanced type: 3000..3999
                    MAC type: 4000..4999
                    User type: 5000..5999
                "
            ::= { ibPfilter2StatisticSumEntry 3 }

        ibPfilter2SumRuleIndex OBJECT-TYPE
            SYNTAX Integer32 (0..65534)
            MAX-ACCESS not-accessible
            STATUS current
            DESCRIPTION
                "The ACL rule index."
            ::= { ibPfilter2StatisticSumEntry 4 }

        ibPfilter2SumRuleMatchPackets OBJECT-TYPE
            SYNTAX Counter64
            MAX-ACCESS read-only
            STATUS current
            DESCRIPTION
                "The sum number of packets matched the ACL rule."
            ::= { ibPfilter2StatisticSumEntry 5 }

        ibPfilter2SumRuleMatchBytes OBJECT-TYPE
            SYNTAX Counter64
            MAX-ACCESS read-only
            STATUS current
            DESCRIPTION
                "The sum number of bytes matched the ACL rule."
            ::= { ibPfilter2StatisticSumEntry 6 }

--
-- Nodes of ibPacketfilterTrapObjects
--

        ibAclPacketfilterTrapObjects OBJECT IDENTIFIER ::= { ibAcl 4 }

        ibPfilterInterface OBJECT-TYPE
            SYNTAX OCTET STRING
            MAX-ACCESS accessible-for-notify
            STATUS current
            DESCRIPTION
                "The interface which policy apply."
            ::= { ibAclPacketfilterTrapObjects 1 }

        ibPfilterDirection OBJECT-TYPE
            SYNTAX OCTET STRING (SIZE(0..255))
            MAX-ACCESS accessible-for-notify
            STATUS current
            DESCRIPTION
                "Inbound or outbound."
            ::= { ibAclPacketfilterTrapObjects 2 }

        ibPfilterACLNumber OBJECT-TYPE
            SYNTAX Integer32
            MAX-ACCESS accessible-for-notify
            STATUS current
            DESCRIPTION
                "ACL number."
            ::= { ibAclPacketfilterTrapObjects 3 }

        ibPfilterAction OBJECT-TYPE
            SYNTAX OCTET STRING (SIZE(0..255))
            MAX-ACCESS accessible-for-notify
            STATUS current
            DESCRIPTION
                "Permit or deny."
            ::= { ibAclPacketfilterTrapObjects 4 }

        ibMACfilterSourceMac OBJECT-TYPE
            SYNTAX OCTET STRING (SIZE(0..255))
            MAX-ACCESS accessible-for-notify
            STATUS current
            DESCRIPTION
                "Source MAC address."
            ::= { ibAclPacketfilterTrapObjects 5 }

        ibMACfilterDestinationMac OBJECT-TYPE
            SYNTAX OCTET STRING (SIZE(0..255))
            MAX-ACCESS accessible-for-notify
            STATUS current
            DESCRIPTION
                "Destination MAC address."
            ::= { ibAclPacketfilterTrapObjects 6 }

        ibPfilterPacketNumber OBJECT-TYPE
            SYNTAX Integer32
            MAX-ACCESS accessible-for-notify
            STATUS current
            DESCRIPTION
                "The number of packets permitted or denied by ACL."
            ::= { ibAclPacketfilterTrapObjects 7 }

        ibPfilterReceiveInterface OBJECT-TYPE
            SYNTAX OCTET STRING (SIZE(0..255))
            MAX-ACCESS accessible-for-notify
            STATUS current
            DESCRIPTION
                "The interface where packet come from."
            ::= { ibAclPacketfilterTrapObjects 8 }

        ibAclPacketIfName OBJECT-TYPE
            SYNTAX OCTET STRING (SIZE(0..255))
            MAX-ACCESS accessible-for-notify
            STATUS current
            DESCRIPTION
                "The name of the interface on which the packet is matched."
            ::= { ibAclPacketfilterTrapObjects 9 }

        ibAclPacketDirection OBJECT-TYPE
            SYNTAX DirectionType
            MAX-ACCESS accessible-for-notify
            STATUS current
            DESCRIPTION
                "The direction the packet is going."
            ::= { ibAclPacketfilterTrapObjects 10 }

        ibAclPacketBAGG OBJECT-TYPE
            SYNTAX Integer32 (0..2048)
            MAX-ACCESS accessible-for-notify
            STATUS current
            DESCRIPTION
                "The bridge-aggregation-interface ID the interface belongs to.
                "
            DEFVAL { 0 }
            ::= { ibAclPacketfilterTrapObjects 11 }

        ibAclPacketVlanID OBJECT-TYPE
            SYNTAX Integer32 (1..4094)
            MAX-ACCESS accessible-for-notify
            STATUS current
            DESCRIPTION
                "The vlan the interface belongs to."
            ::= { ibAclPacketfilterTrapObjects 12 }

        ibAclPacketSrcIP OBJECT-TYPE
            SYNTAX OCTET STRING (SIZE(0..255))
            MAX-ACCESS accessible-for-notify
            STATUS current
            DESCRIPTION
                "Source IP address of IPv4/IPv6 packet."
            ::= { ibAclPacketfilterTrapObjects 13 }

        ibAclPacketDstIP OBJECT-TYPE
            SYNTAX OCTET STRING (SIZE(0..255))
            MAX-ACCESS accessible-for-notify
            STATUS current
            DESCRIPTION
                "Destination IP address of IPv4/IPv6 packet."
            ::= { ibAclPacketfilterTrapObjects 14 }

        ibAclPacketProtocol  OBJECT-TYPE
            SYNTAX Integer32 (0..255)
            MAX-ACCESS accessible-for-notify
            STATUS current
            DESCRIPTION
                "The protocol of IPv4/IPv6 packet.
                icmp(1),
                tcp(6),
                udp(17),
                igmp(2),
                gre(47),
                ospf(89),
                ipinip(4),
                icmp6(58),
                ipv6_ah(51),
                ipv6_esp(50)
                "
            ::= { ibAclPacketfilterTrapObjects 15 }

        ibAclPacketDscp  OBJECT-TYPE
            SYNTAX DSCPValue
            MAX-ACCESS accessible-for-notify
            STATUS current
            DESCRIPTION
                "DSCP of IPv4/IPv6 packet."
            DEFVAL { 255 }
            ::= { ibAclPacketfilterTrapObjects 16 }

        ibAclPacketFlowLabel  OBJECT-TYPE
            SYNTAX Unsigned32   (0..1048575|4294967295)
            MAX-ACCESS accessible-for-notify
            STATUS current
            DESCRIPTION
                "Flow label value of IPv6 packet."
            DEFVAL { 4294967295 }
            ::= { ibAclPacketfilterTrapObjects 17 }

        ibAclPacketIcmpIgmpType  OBJECT-TYPE
            SYNTAX Integer32   (0..255|65535)
            MAX-ACCESS accessible-for-notify
            STATUS current
            DESCRIPTION
                "The type of ICMP or IGMP packet."
            DEFVAL { 65535 }
            ::= { ibAclPacketfilterTrapObjects 18 }

        ibAclPacketIcmpIgmpCode  OBJECT-TYPE
            SYNTAX Integer32   (0..255|65535)
            MAX-ACCESS accessible-for-notify
            STATUS current
            DESCRIPTION
                "The code of ICMP or IGMP packet."
            DEFVAL { 65535 }
            ::= { ibAclPacketfilterTrapObjects 19 }

        ibAclPacketTcpFlags  OBJECT-TYPE
            SYNTAX INTEGER
            {
                tcpack(1),
                tcpfin(2),
                tcppsh(3),
                tcprst(4),
                tcpsyn(5),
                tcpurg(6),
                invalid(255)
            }

            MAX-ACCESS accessible-for-notify
            STATUS current
            DESCRIPTION
                "The flags of TCP packet.
                tcpack(1),
                tcpfin(2),
                tcppsh(3),
                tcprst(4),
                tcpsyn(5),
                tcpurg(6),
                invalid(255)
                "
            DEFVAL { 255 }
            ::= { ibAclPacketfilterTrapObjects 20 }

        ibAclPacketSrcPort  OBJECT-TYPE
            SYNTAX Integer32 (0..65535)
            MAX-ACCESS accessible-for-notify
            STATUS current
            DESCRIPTION
                "Source port of TCP or UDP packet."
            DEFVAL { 0 }
            ::= { ibAclPacketfilterTrapObjects 21 }

        ibAclPacketDstPort  OBJECT-TYPE
            SYNTAX Integer32 (0..65535)
            MAX-ACCESS accessible-for-notify
            STATUS current
            DESCRIPTION
                "Destination port of TCP or UDP packet."
            DEFVAL { 65535 }
            ::= { ibAclPacketfilterTrapObjects 22 }

        ibAclPacketSrcMacAddr  OBJECT-TYPE
            SYNTAX MacAddress
            MAX-ACCESS accessible-for-notify
            STATUS current
            DESCRIPTION
                "Source MAC address of Ethernet packet."
            ::= { ibAclPacketfilterTrapObjects 23 }

        ibAclPacketDstMacAddr  OBJECT-TYPE
            SYNTAX MacAddress
            MAX-ACCESS accessible-for-notify
            STATUS current
            DESCRIPTION
                "Destination MAC address of Ethernet packet."
            ::= { ibAclPacketfilterTrapObjects 24 }

        ibAclPacketMacTypeLen  OBJECT-TYPE
            SYNTAX Integer32 (0..65535)
            MAX-ACCESS accessible-for-notify
            STATUS current
            DESCRIPTION
                "The Ethertype or 802.3 length of Ethernet packet."
            DEFVAL { 0 }
            ::= { ibAclPacketfilterTrapObjects 25 }

        ibAclPacketVlanPCP  OBJECT-TYPE
            SYNTAX  Integer32    (0..7|255)
            MAX-ACCESS accessible-for-notify
            STATUS current
            DESCRIPTION
                "802.1p priority code point of Ethernet packet."
            DEFVAL { 255 }
            ::= { ibAclPacketfilterTrapObjects 26 }

--
-- Nodes of ibPacketfilterTrap
--

        ibAclPacketfilterTrap OBJECT IDENTIFIER ::= { ibAcl 5 }

        ibPfilterTrapPrefix OBJECT IDENTIFIER ::= { ibAclPacketfilterTrap 0 }

        ibMACfilterTrap NOTIFICATION-TYPE
            OBJECTS
            {
                ibPfilterInterface,
                ibPfilterDirection,
                ibPfilterACLNumber,
                ibPfilterAction,
                ibMACfilterSourceMac,
                ibMACfilterDestinationMac,
                ibPfilterPacketNumber,
                ibPfilterReceiveInterface
            }
            STATUS current
            DESCRIPTION
                "This notification is generated when a packet was processed
                by MAC address filter, but not every packet will generate one
                notification, the same notification only generate once in 30
                seconds.
                "
            ::= { ibPfilterTrapPrefix 1 }

        ibAclRuleMatchCount NOTIFICATION-TYPE
            OBJECTS
            {
                ibPfilter2ApplyObjType,
                ibPfilter2ApplyObjIndex,
                ibPfilter2ApplyDirection,
                ibPfilter2ApplyAclType,
                ibPfilter2ApplyAclIndex,
                ibPfilter2AclRuleIndex,
                ibPfilter2AclRuleMatchPackets
            }
            STATUS current
            DESCRIPTION
                "This notification is generated periodically due to a timer.
                The interval of the timer is configured in ibAclIntervalTable.
                The notification details the entries about the packet-filter
                object, the matched ACL rule and the number of matching packets.
                "
            ::= { ibPfilterTrapPrefix 2 }

        ibAclFirstIPv4PktCaptured NOTIFICATION-TYPE
            OBJECTS
            {
                ibPfilter2ApplyAclIndex,
                ibPfilter2AclRuleIndex,
                ibAclPacketIfName,
                ibAclPacketDirection,
                ibAclPacketBAGG,
                ibAclPacketVlanID,
                ibAclPacketSrcIP,
                ibAclPacketDstIP,
                ibAclPacketProtocol,
                ibAclPacketDscp,
                ibAclPacketIcmpIgmpType,
                ibAclPacketIcmpIgmpCode,
                ibAclPacketTcpFlags,
                ibAclPacketSrcPort,
                ibAclPacketDstPort
            }
            STATUS current
            DESCRIPTION
                "This notification is generated immediately when the first
                packet of the matched IPv4 flow is captured.  Other packets
                of the matched flow won't be captured.
                "
            ::= { ibPfilterTrapPrefix 3 }

        ibAclFirstIPv6PktCaptured NOTIFICATION-TYPE
            OBJECTS
            {
                ibPfilter2ApplyAclIndex,
                ibPfilter2AclRuleIndex,
                ibAclPacketIfName,
                ibAclPacketDirection,
                ibAclPacketBAGG,
                ibAclPacketVlanID,
                ibAclPacketSrcIP,
                ibAclPacketDstIP,
                ibAclPacketProtocol,
                ibAclPacketDscp,
                ibAclPacketFlowLabel,
                ibAclPacketIcmpIgmpType,
                ibAclPacketIcmpIgmpCode,
                ibAclPacketTcpFlags,
                ibAclPacketSrcPort,
                ibAclPacketDstPort
            }
            STATUS current
            DESCRIPTION
                "This notification is generated immediately when the first
                packet of the matched IPv6 flow is captured.  Other packets
                of the matched flow won't be captured.
                "
            ::= { ibPfilterTrapPrefix 4 }

        ibAclFirstEthernetPktCaptured NOTIFICATION-TYPE
            OBJECTS
            {
                ibPfilter2ApplyAclIndex,
                ibPfilter2AclRuleIndex,
                ibAclPacketIfName,
                ibAclPacketDirection,
                ibAclPacketBAGG,
                ibAclPacketVlanID,
                ibAclPacketSrcMacAddr,
                ibAclPacketDstMacAddr,
                ibAclPacketMacTypeLen,
                ibAclPacketVlanPCP
            }
            STATUS current
            DESCRIPTION
                "This notification is generated immediately when the first
                packet of the matched Ethernet flow is captured.  Other packets
                of the matched flow won't be captured.
                "
            ::= { ibPfilterTrapPrefix 5 }

--
-- Nodes of ibAclTrapObjects
--

        ibAclTrapObjects OBJECT IDENTIFIER ::= { ibAcl 6 }

        ibAclResourceTypeName OBJECT-TYPE
            SYNTAX OCTET STRING (SIZE(1..255))
            MAX-ACCESS accessible-for-notify
            STATUS current
            DESCRIPTION
                "The name of TCAM resources."
            ::= { ibAclTrapObjects 1 }

        ibAclResourceUsage OBJECT-TYPE
            SYNTAX Integer32 (1..100)
            MAX-ACCESS accessible-for-notify
            STATUS current
            DESCRIPTION
                "The current usage of TCAM resources."
            ::= { ibAclTrapObjects 2 }

        ibAclResourceUsedEntries OBJECT-TYPE
            SYNTAX Integer32
            MAX-ACCESS accessible-for-notify
            STATUS current
            DESCRIPTION
                "The used number of entries on TCAM."
            ::= { ibAclTrapObjects 3 }

        ibAclResourceTotalEntries OBJECT-TYPE
            SYNTAX Integer32
            MAX-ACCESS accessible-for-notify
            STATUS current
            DESCRIPTION
                "The total number of entries on TCAM."
            ::= { ibAclTrapObjects 4 }

        ibAclResourceChassisID OBJECT-TYPE
            SYNTAX Integer32
            MAX-ACCESS accessible-for-notify
            STATUS current
            DESCRIPTION
                "The chassis number.  On a centralized or distributed device,
                 the value for this node is always zero."
            ::= { ibAclTrapObjects 5 }

       ibAclResourceSlotID OBJECT-TYPE
            SYNTAX Integer32
            MAX-ACCESS accessible-for-notify
            STATUS current
            DESCRIPTION
                "The slot number.  On a centralized device, the value for
                 this node is always zero."
            ::= { ibAclTrapObjects 6 }

--
-- Nodes of ibAclResourceTrap
--

        ibAclTrap OBJECT IDENTIFIER ::= { ibAcl 7 }

        ibAclTrapPrefix OBJECT IDENTIFIER ::= { ibAclTrap 0 }

        ibAclResourceTrap NOTIFICATION-TYPE
            OBJECTS
            {
                ibAclResourceTypeName,
                ibAclResourceUsage,
                ibAclResourceUsedEntries,
                ibAclResourceTotalEntries,
                ibAclMib2ResourceThreshold,
                ibAclResourceChassisID,
                ibAclResourceSlotID
            }
            STATUS current
            DESCRIPTION
                "This notification is generated when the number of entries on TCAM
                 becomes equal to or greater than a preset threshold level"
            ::= { ibAclTrapPrefix 1 }

END
