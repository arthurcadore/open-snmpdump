-- =========================================================================
-- Copyright (C) 2023 Intelbras S.A. All rights reserved.
--
-- Description:  SPB MIB
-- Reference:  Enterprise MIB
-- Version:V1.00
-- History:
--     initial version 2003-03-06
--     V1.0 6th Nov 2012
-- =========================================================================
IB-SPB-MIB DEFINITIONS ::= BEGIN

IMPORTS
    ifIndex
        FROM IF-MIB
    Unsigned32, OBJECT-TYPE, MODULE-IDENTITY, NOTIFICATION-TYPE
        FROM SNMPv2-SMI
    MacAddress
        FROM SNMPv2-TC
    VlanIdOrNone
        FROM Q-BRIDGE-MIB
    ibCommon
        FROM IB-OID-MIB
    IEEE8021SpbmSPsourceId
        FROM IEEE8021-SPB-MIB;

ibSpb MODULE-IDENTITY
    LAST-UPDATED "201211220000Z"        -- November 22, 2012 at 00:00 GMT
    ORGANIZATION
        "Intelbras S.A. Industria de Telecomunicacao Eletronica Brasileria."
    CONTACT-INFO
        ""
    DESCRIPTION  "802.1 SPB MIB"
    REVISION  "201211220000Z"        -- November 22, 2012 at 00:00 GMT
    DESCRIPTION
        "This MIB describes objects used for managing Shortest Path Bridging
        (SPB)."
    ::= { ibCommon 128 }


ibSpbObjects OBJECT IDENTIFIER ::= { ibSpb 1 }

ibSpbSysObjects OBJECT IDENTIFIER
    ::= { ibSpbObjects 1 }

ibSpbSysStatus OBJECT-TYPE
    SYNTAX      INTEGER
        {
            enabled(1),
            disabled(2)
        }
    MAX-ACCESS read-write
    STATUS current
    DESCRIPTION
        "To descript the status of Shortest Path Bridging MAC Mode(SPBM) is
        Enabled or Disabled."
    DEFVAL { disabled }
    ::= { ibSpbSysObjects 1 }

ibSpbMulticastBVlanStatus OBJECT-TYPE
    SYNTAX      INTEGER
        {
            enabled(1),
            disabled(2)
        }
    MAX-ACCESS read-write
    STATUS current
    DESCRIPTION
        "To descript the status of SPBM multicast bvlan is Enabled or
        Disabled."
    DEFVAL { disabled }
    ::= { ibSpbSysObjects 2 }

ibSpbConfig OBJECT IDENTIFIER
    ::= { ibSpbObjects 2 }

ibSpbIfTable OBJECT-TYPE
    SYNTAX SEQUENCE OF IbSpbIfEntry
    MAX-ACCESS not-accessible
    STATUS current
    DESCRIPTION
        "This table describes the interface status of SPBM is Enabled or
        Disabled."
    ::= { ibSpbConfig 1 }

ibSpbIfEntry OBJECT-TYPE
    SYNTAX IbSpbIfEntry
    MAX-ACCESS not-accessible
    STATUS current
    DESCRIPTION
        "The entry of ibSpbIfEntry."
    INDEX { ifIndex }
    ::= { ibSpbIfTable 1 }

IbSpbIfEntry ::=
    SEQUENCE
    {
        ibSpbIfStatus         INTEGER
    }

ibSpbIfStatus OBJECT-TYPE
    SYNTAX      INTEGER
        {
            enabled(1),
            disabled(2)
        }
    MAX-ACCESS read-write
    STATUS current
    DESCRIPTION
        "To descript the interface status of SPBM is Enabled or Disabled."
    DEFVAL { disabled }
    ::= { ibSpbIfEntry 1 }

ibSpbSrvTable OBJECT-TYPE
    SYNTAX SEQUENCE OF IbSpbSrvEntry
    MAX-ACCESS not-accessible
    STATUS current
    DESCRIPTION
        "This table descript the Base VlanID(VID) associated with the service
        and the service multicast duplicate mode."
    ::= { ibSpbConfig 2 }


ibSpbSrvEntry OBJECT-TYPE
    SYNTAX IbSpbSrvEntry
    MAX-ACCESS not-accessible
    STATUS current
    DESCRIPTION
        "The entry of ibSpbSrvEntry."
    INDEX { ibSpbSrvTableEntryTopIx,
            ibSpbSrvTableEntryIsid }
    ::= { ibSpbSrvTable 1 }

IbSpbSrvEntry ::=
    SEQUENCE {
        ibSpbSrvTableEntryTopIx   Unsigned32,
        ibSpbSrvTableEntryIsid    Unsigned32,
        ibSpbSrvTableEntryBaseVid VlanIdOrNone,
        ibSpbSrvTableEntryMode    INTEGER
        }

ibSpbSrvTableEntryTopIx OBJECT-TYPE
    SYNTAX Unsigned32
    MAX-ACCESS not-accessible
    STATUS current
    DESCRIPTION
        "Unique identifier of this SPB topology
         This is index is allocated for this ISIS/MT instance.
         It is used as an index to most other SPB tables below and to
         select the exact ISIS instance and which MT instance together."
    ::= { ibSpbSrvEntry 1 }

ibSpbSrvTableEntryIsid OBJECT-TYPE
    SYNTAX    Unsigned32 (255..16777215)
    MAX-ACCESS not-accessible
    STATUS current
    DESCRIPTION
        "An ISID (service) originating/terminating on this bridge."
    ::= { ibSpbSrvEntry 2 }

ibSpbSrvTableEntryBaseVid OBJECT-TYPE
    SYNTAX    VlanIdOrNone
    MAX-ACCESS read-write
    STATUS current
    DESCRIPTION
        "The Base VID associated with this service.  The Base VID determines
         the ECT Algorithm that is associated with this service.  Otherwise
         no Base VID associated with the service, should be set = 0."
    ::= { ibSpbSrvEntry 3 }

ibSpbSrvTableEntryMode OBJECT-TYPE
    SYNTAX    INTEGER
        {
            headEnd(1),
            tandem(2)
        }
    MAX-ACCESS read-write
    STATUS current
    DESCRIPTION
        "Indication of supporting multicast replicate mode
         head-end/tandem."
    DEFVAL { headEnd }
    ::= { ibSpbSrvEntry 4 }

-- ==================================================================
--
-- ======================= trap definition begin ====================
--
-- ==================================================================
ibSpbTrap OBJECT IDENTIFIER ::= {  ibSpbObjects 3  }

ibSpbTraps OBJECT IDENTIFIER ::= { ibSpbTrap 0 }

ibSpbTrapsObjects OBJECT IDENTIFIER ::= { ibSpbTrap 1 }

ibSpbSPSourceConflictTrap NOTIFICATION-TYPE
    OBJECTS
        {
            ibSpbConflictSysID,
            ibSpbConflictSPSourceID
        }
    STATUS      current
    DESCRIPTION
        "This notification will be generated when the SPSourceID is conflict
        with another bridge."
    ::= { ibSpbTraps 1 }

ibSpbBMacConflictTrap NOTIFICATION-TYPE
    OBJECTS
        {
            ibSpbConflictSysID,
            ibSpbConflictBMac
        }
    STATUS      current
    DESCRIPTION
        "This notification will be generated when the BMAC is conflict
        with another bridge."
    ::= { ibSpbTraps 2 }

ibSpbConflictSysID OBJECT-TYPE
    SYNTAX MacAddress
    MAX-ACCESS accessible-for-notify
    STATUS current
    DESCRIPTION
        "The bridge's SPSourceID is conflict with this bridge."
    ::= { ibSpbTrapsObjects 1 }

ibSpbConflictSPSourceID OBJECT-TYPE
    SYNTAX IEEE8021SpbmSPsourceId
    MAX-ACCESS accessible-for-notify
    STATUS current
    DESCRIPTION
        "The Shortest Path Source Identifier which is conflict."
    ::= { ibSpbTrapsObjects 2 }

ibSpbConflictBMac OBJECT-TYPE
    SYNTAX MacAddress
    MAX-ACCESS accessible-for-notify
    STATUS current
    DESCRIPTION
        "The BMAC which is conflict."
    ::= { ibSpbTrapsObjects 3 }

END
