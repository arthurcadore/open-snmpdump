-- =============================================================================
-- Copyright (C) 2023 Intelbras S.A. All rights reserved.
--
-- Description:
--   The file defines a MIB to provide WLAN configuration information.
-- Reference:
-- Version: V3.8
-- History:
--   V1.0 2006-05-10 Initial version, created by shiyang (Richard)
--   V1.1 2007-02-01 modified by xingjichen(Daniel)
--        Added ibDot11RadioIntfConfigTable,ibDot11RadioIntfBindTable,
--        ibDot11StaKeepALiveTimerIntvl,ibDot11StaIdleTimerIntvl,
--        ibDot11BroadcastProbeReply.
--   V1.2 2007-04-27 modified by shiyang(Richard)
--        Replace ibDot11UnicastCipherKeyIndex, ibDot11UnicastCipherKey,
--        ibDot11BroadcastCipherKeyIndex and ibDot11BroadcastCipherKey
--        with ibDot11CipherKeyIndex, ibDot11CipherKey as per CLI change.
--        Delete ibDot11MaxTxLifetime as per CLI change.
--        Add ibDot11GlobalCountryCode,ibDot11APScanMode.
--        ibDot11ACCtrlTunnelSecSupport and ibDot11ACDataTunnelSecSupport.
--        Move ibDot11StaKeepALiveTimerIntvl,ibDot11StaIdleTimerIntvl
--        and so on to ibDot11GlobeConfigGroup.
--        Split ibDot11ServicePolicyTable into ibDot11ServicePolicyTable
--        and ibDot11ServicePolicyExtTable.
--        For ibDot11SecurityCiphers node,update its description for case of
--        value equals to zero.
--   V1.3 2007-06-19 modified by Vikas K
--        Add new table of ibDot11DataRateConfigTable for AP Configuration
--        Group.
--        Add new node of ibDot11APName for ibDot11APTemplateTable.
--        Modify the ibDot11APScanMode from read-only to read-write.
--        Add undo functionality to node ibDot11WlanInfBindingID and
--        ibDot11Description.
--        Add ibDot11StatisInterv to the ibDot11APTemplateTable.
--   V1.4 2007-10-9 modified by Jagan K
--        Add new table ibDot11WlanBssIfTable for WLAN BSS interface
--        configuration.
--        Add new table ibDot11WlanEssIfTable for WLAN ESS interface
--        configuration.
--        Add new table ibDot11WlanEthernetIfTable for WLAN Ethernet interface
--        configuration.
--   V1.5 2007-12-21 modified by wanghao (Kumar)
--        Add ibDot11ACAutoAPSupport, ibDot11AutoAPName,
--        ibDot11PersistentName to ibDot11GlobeConfigGroup
--        Add ibDot11ClientMaxCount to ibDot11ServicePolicyTable
--        Add ibDot11APBroadcastProbeReply, ibDot11StaIdleTimerInterv,
--        ibDot11StaKeepAliveTimerInterv, ibDot11APCir, ibDot11APCbs
--        to ibDot11APTemplateTable.
--   V1.6 2008-02-25 modified by wanghao (Kumar)
--        Add ibDot11RdoClientMaxCount to ibDot11RadioPolicyTable.
--   V1.7 2008-04-01 modified by wangbin
--        Add ibDot11PortSecurityTable to ibDot11InterfaceConfigGroup.
--        Add ibDot11PortSecurityMode, ibDot11SecurityUserLoginTxKeyType,
--        ibDot11SecurityPskKeyMode, ibDot11SecurityPskKeyString
--        to ibDot11PortSecurityTable.
--   V1.8 2008-08-01 modified by ChangHuifeng
--        Add ibDot11ACBackupGroup and
--        ibDot11RadioElementConfigGroup.
--        Add ibDot11WlanMeshIfTable to ibDot11InterfaceConfigGroup.
--        Add ibDot11APPriorityLevel and ibDot11APElementID to
--        ibDot11APTemplateTable.
--        Add ibDot11CfgRdElementID to ibDot11RadioToConfigTable.
--        Add ibDot11APDevDetectEnable to ibDot11APTemplateEntry.
--        Obsolete ibDot11StatisInterv
--        Change default value of ibDot11APScanMode to passive.
--        Change units of ibDot11BeaconInterval and
--        ibDot11RadioCfgBeaconIntvl to TU.
--        Remove default value of ibDot11SSIDEncryptionMode.
--        Change MAC-ACCESS of objects in ibDot11RadioToConfigTable
--        from read-create to read-write.
--        Change name of ibDot11IWlanEssRowStatus to ibDot11WlanEssRowStatus.
--        Change description of ibDot11PortSecurityTable.
--   V1.9 2008-11-07 modified by Wang Lu and Li Yugang
--        Add ibDot11IntfTrapThreshold to ibDot11GlobeConfigGroup
--        Add ibDot11SPInCirMode, ibDot11SPInCirValue, ibDot11SPOutCirMode,
--        ibDot11SPOutCirValue to ibDot11ServicePolicyTable
--        Add ibDot11CfgWorkMode to ibDot11RadioToConfigTable
--        Add ibDot11RadioCfgWorkMode to ibDot11RadioIntfConfigTable.
--        Add new traps ibDot11CfgCipherChange and ibDot11CfgPSKChange.
--        Add ibDot11MonitorInterval, ibDot11SampleInterval,
--        ibDot11ChnlSwitChkInterval, ibDot11APUserUplimit,
--        ibDot11APL2IsolateEnable to ibDot11GlobeConfigGroup.
--        Add ibDot11RadioCfgOnly11gEnable to ibDot11RadioIntfConfigTable.
--        Add ibDot11RadioWDSTable to ibDot11RadioElementConfigGroup.
--   V2.0 2009-03-20 modified by caizibin
--        Add value ext(6) to ibDot11PortSecurityMode
--   V2.1 2009-05-07 modified by Li Yugang, Wang Shaojie, Jin Yi
--        Add ibDot11APBSSIDSupportNum, ibDot11APLastUpdateStatTime,
--        ibDot11APDoSProtectEnable, ibDot11MaxAPPerIf to
--        ibDot11GlobeConfigGroup.
--        Add ibDot11WlanInfPVID to ibDot11ServicePolicyTable.
--        Add ibDot11CipherKeyType to ibDot11ServicePolicyExtTable.
--        Add ibDot11CfgPwrAttValue to ibDot11RadioToConfigTable.
--        Add new table ibDot11APSysInfoSetTable to ibDot11APConfigGroup.
--        Add ibDot11SSIDWepIDConflictTrap to ibDot11CfgNotifications.
--        Add new table ibDot11CfgTrapVarObjects to ibDot11CfgNotifyGroup.
--   V2.2 2009-07-29 modified by Heziqi
--        Add new node ibDot11ServiceSetVlanId for ibDot11APServiceSetTable.
--        Add ibDot11UplinkTrackId to ibDot11GlobeConfigGroup.
--        Add ibDot11APLimitTable.
--        Change description of ibDot11StaKeepALiveTimerIntvl.
--        Add new node ibDot11RadioTxArithmetic for IbDot11RadioToConfigTable.
--   V2.3 2009-07-29 modified by Jinyi
--        Add new table ibDot11APIfSetTable
--   V2.4 2009-12-01 modified by Wang Shaojie
--        Add new node ibDot11APGetIPMethod for ibDot11APTemplateTable.
--        Add new group ibDot11CfgTrapConfigGroup.
--        Add new table ibDot11CfgSwitchTrapTable to ibDot11CfgTrapConfigGroup.
--        Add new node ibDot11BeaconIntervalMs to ibDot11RadioPolicyTable.
--        Add new node ibDot11SPInCirStaticValue, ibDot11SPOutCirStaticValue
--        to ibDot11ServicePolicyTable.
--        Modify description of ibDot11SecurityCiphers.
--        Add new node ibDot11StatisIntervMode to ibDot11APTemplateTable.
--        Modify SYNTAX of ibDot11APWorkMode.
--        Modify STATUS of ibDot11StatisInterv.
--        Add new node ibDot11SmartRateSet to ibDot11DataRateConfigTable.
--        2010-02-22 modified by Wang Chunsheng
--        Add new node ibDot11CfgChannelLockStat, ibDot11CfgPowerLockStat,
--        ibDot11CfgLBRdGroupId, ibDot11CfgRRMSDRdGroupId to ibDot11RadioToConfigTable.
--        2010-03-15 modified by Wang Lu
--        Add ibDot11RtCollectSwitch, ibDot11RglCollectIntvl, and
--        ibDot11RtCollectIntvl to ibDot11GlobeConfigGroup
--        Add ibDot11SPIsolate to ibDot11ServicePolicyTable
--        Add ibDot11APServiceVlanTable, ibDot11RadioConfigTable,
--        ibDot11RadioPolicyExtTable and ibDot11RadioSSIDCfgTable
--        Remove ibDot11CfgTrapConfigGroup
--        Add ibDot11SrvPortSecurityTable
--        2010-06-01 Modified by Wang Shaojie, Yin Junjie
--        Add ibDot11RCApPowerLevel, ibDot11RCDynamicChlState,
--        ibDot11RCDynamicPowerState to ibDot11RadioConfigTable.
--        Add ibDot11APSerialIDTable
--        Add ibDot11APSTVlanTable
--        2010-07-08 Modified the index of ibDot11APSysInfoSetTable by jinyi
--        2010-08-05 Modified by Yin Junjie
--        Add new table ibDot11SrvPolicyExtendTable
--        Add ibDot11SPEnable to ibDot11SrvPolicyExtendTable
--        2010-09-02 Modified by Yin Junjie
--        Add new node ibDot11AdjIntfTrapThreshold
--        to ibDot11GlobeConfigGroup
--        Add ibDot11RCRadioStatus to ibDot11RadioConfigTable
--   V2.5 2010-09-25 Modified by Wu Xiaopeng
--        Remove Size list of ibDot11APName.
--   V2.6 2011-05-23 Modified by Cui Kai
--        Add new node ibDot11WlanexAuthServerIP to ibDot11ServicePolicyTable
--        2011-07-08 Modified by Niu Jian
--        Change type of ibDot11CfgSTNASPortID to OCTET STRING
--   V2.7 2011-07-13 Modified by Yu Bo
--        Add new node ibDot11RCRadioRate to ibDot11RadioConfigTable
--        Add new node ibDot11RCPwrAdjustStepLength to ibDot11RadioConfigTable
--        2011-08-08 Modified by Xiao Min
--        Add new table ibDot11nRadioCfg2Table
--        2011-08-10 Modified by limingjin
--        Add ibDot11RadioCfgType2 to ibDot11RadioIntfConfigTable
--        Add ibDot11RCRadioType2 to ibDot11RadioConfigTable
--        Add ibDot11CfgRadioType2 to ibDot11RadioToConfigTable
--   V2.8 2011-09-28 Modified by zhanghu
--        Add ibDot11ApTrapEnabled to ibDot11APTemplateTable
--        Add ibDot11AllAPMonitorMode to ibDot11APTemplateTable
--        Add ibDot11SIDAPTemplateName, ibDot11SIDModelAlias, ibDot11SIDAPDescription, ibDot11SIDRowStatus,
--        ibDot11SIDAPName, ibDot11SIDStatisInterv, ibDot11SIDAPBroadcastProbeReply,
--        ibDot11SIDAPStaIdleTimerInterv, ibDot11SIDStaKeepAliveTimerInterv,
--        ibDot11SIDAPCir, ibDot11SIDAPCbs, ibDot11SIDAPPriorityLevel,
--        ibDot11SIDAPElementID, ibDot11SIDAPDevDetectEnable, ibDot11SIDAPStatisIntervMode
--        to ibDot11APSerialIDTable
--        2011-08-28 Modified by Wang Lu
--        Add ibDot11CfgSaEnable, ibDot11CfgSaBand, ibDot11CfgIDSEnable,
--        ibDot11CfgSaCltRtFFTData to ibDot11RadioToConfigTable
--   V2.9 2012-08-10 by Zhang Cong cong
--        Add new node   ibDot11ConfigureAPMacAddress to ibDot11CfgTrapVarObjects
--        Add new object ibDot11ConfigureAPMacAddress to ibDot11SSIDWepIDConflictTrap
--   V3.0 2013-04-15 by Shao Pengfei & Li Shihao
--        Add new node ibDot11GlobalApFmwUpdState to ibDot11GlobeConfigGroup
--        Add new node ibDot11ApFmwUpdState to ibDot11APTemplateTable
--        Add new node ibDot11SPBeaconMeasEnable to ibDot11ServicePolicyTable
--        Add new node ibDot11SPBeaconMeasType to ibDot11ServicePolicyTable
--        Add new node ibDot11SPBeaconMeasInterval to ibDot11ServicePolicyTable
--   V3.1 2013-08-30 by Xiao Mengmeng & Li Qian & Ji Chunyu & Liu Yawen
--        Add ibDot11AuthenModeCM to ibDot11ServicePolicyTable
--        Add ibDot11SecIEStatusCM to ibDot11ServicePolicyTable
--        Add ibDot11SecurityCiphersCM to ibDot11ServicePolicyTable
--        Add ibDot11SrvPolicyStatusCM to ibDot11ServicePolicyTable
--        Add ibDot11CfgSTNASID to ibDot11APSTVlanTable
--        Add ibDot11RCPreambleLenCM to ibDot11RadioConfigTable
--        Add ibDot11RCDynamicChlStateCM to ibDot11RadioConfigTable
--        Add ibDot11RCRadioStatusCM to ibDot11RadioConfigTable
--        Add ibDot11SIDAPWorkModeCM to ibDot11APSerialIDTable
--        Add ibDot11nRadioCfg2AMpduEnableCM to ibDot11nRadioCfg2Table
--        Add ibDot11nRadioCfg2ChannelBandCM to ibDot11nRadioCfg2Table
--        Add ibDot11nRadioCfg2ShortGiEnableCM to ibDot11nRadioCfg2Table
--        2013-12-24 Modified by Chen Guoxi
--        Add mode80 to ibDot11nChanelBand and ibDot11nRadioCfg2ChannelBand
--        Add new node ibDot11nClientDot11acOnly to ibDot11nRadioCfgTable
--        Add new node ibDot11nRadioCfg2ClientDot11acOnly to ibDot11nRadioCfg2Table
--   V3.2 2014-02-10 by Zhou Weichao
--        Add ibDot11ACNasIDCM to ibDot11GlobeConfigGroup
--        Add ibDot11SSIDHiddenCM to ibDot11ServicePolicyTable
--        Add ibDot11SPIsolateCM to ibDot11ServicePolicyTable
--        Add ibDot11RPBeaconIntervalCM to ibDot11RadioPolicyExtTable
--        Add ibDot11StatisIntervModeCM to ibDot11APTemplateTable
--        Add ibDot11APNasIDCM to ibDot11APTemplateTable
--        Add ibDot11RCDynamicPowerStateCM to ibDot11RadioConfigTable
--        Add ibDot11RCRadioRateCM to ibDot11RadioConfigTable
--        Add ibDot11nRadioCfg2ClientDot11nOnlyCM to ibDot11nRadioCfg2Table
--        Modify ibDot11WlanexAuthServerIP
--        Add ibDot11RadioCfgRssithresholdCM to ibDot11RadioIntfConfigTable
--        Add ibDot11SrvPortSecurityModeCM to ibDot11SrvPortSecurityTable
--   V3.3 2014-5-14 Add by yubo
--        Add ibDot11RCRssiThresholdCM to ibDot11RadioConfigTable
--   V3.4 2014-9-19 Add by wanglu
--        Add ibDot11SrvL2AuthenTable
--        Add ibDot11AkmMode to ibDot11ServicePolicyExtTable
--        Add ibDot11PskKey to ibDot11ServicePolicyExtTable
--        Add ibDot11CfgSaRptDevType to ibDot11RadioToConfigTable
--        Add ibDot11CfgSaTrapDevEnable to ibDot11RadioToConfigTable
--        Add ibDot11CfgSaTrapDevType to ibDot11RadioToConfigTable
--        Add ibDot11CfgSaTrapAQEnable to ibDot11RadioToConfigTable
--        Add ibDot11CfgSaTrapAQThreshold to ibDot11RadioToConfigTable
--        Add ibDot11CfgSaDrivenRRMEnable to ibDot11RadioToConfigTable
--        Add ibDot11CfgSaDrivenRRMSnt to ibDot11RadioToConfigTable
--   V3.5 2016-3-11 Add by wuqinggen
--        Add ibDot11FwdVlanBitMapLow to ibDot11ServicePolicyTable
--        Add ibDot11FwdVlanBitMapHigh to ibDot11ServicePolicyTable
--        Add ibDot11ServicePolicyName to ibDot11ServicePolicyTable
--        2016-3-11 add by yubo 04460
--        Add ibDot11ApCoveragetype to ibDot11APTemplateTable
--        Add ibDot11RCDynamicChlStateSelfDecisiveCM to ibDot11RadioConfigTable
--        Add ibDot11RCDynamicPowerStateSelfDecisiveCM to ibDot11RadioConfigTable
--        2016-06-15 Add by zhouwenshuai zkf6157
--        Add ibDot11LocalACTemplateTable
--        Add new node ibDot11ACRole to ibDot11GlobeConfigGroup
--        Add new node ibDot11GlobalLocalACState to ibDot11GlobeConfigGroup
--        Add new node ibDot11CentralACIPAddress to ibDot11GlobeConfigGroup
--        Add new node ibDot11CentralACIPv6Address to ibDot11GlobeConfigGroup
--        Add new node ibDot11APControlAddressState  to ibDot11APTemplateTable
--        Add new node ibDot11APControlAddressIPv4 to ibDot11APTemplateTable
--        Add new node ibDot11APControlAddressIPv6 to ibDot11APTemplateTable
--        Add new node ibDot11APLocalACName to ibDot11APTemplateTable
--        2016-12-06 Add by zhouwenshuai zkf6157
--        Add value mode160(4) mode80and80(5) to ibDot11nChanelBand
--        Add value mode160(4) mode80and80(5) to ibDot11nRadioCfg2ChannelBand
--        2017-10-09 Add by lixiaoyi, jiaohaina, guozhanhua, chenxueke
--        Add new node ibDot11APEchoInterval to ibDot11APTemplateTable
--        Add new node ibDot11SIDEchoInterval to ibDot11APSerialIDTable
--        Add new node ibDot11SecurityModeCM to ibDot11ServicePolicyTable
--        Add new node ibDot11PreConflictTemplateSSID,ibDot11CurrConflictTemplateSSID
--        to ibDot11SSIDWepIDConflictTrap
--        Add new node ibDot11SPInCbsValue to ibDot11ServicePolicyTable
--        Add new node ibDot11SPOutCbsValue to ibDot11ServicePolicyTable
--        Add value mode80(3), mode160(4), mode80and80(5) to ibDot11nRadioCfg2ChannelBandCM
-- V3.6   Add value 0 to ibDot11EchoInterval
--        2018-06-04 Add by licheng
--        Add new node ibDot11iMcIP to ibDot11GlobeConfigGroup
--        Add new node ibDot11iMcPort to ibDot11GlobeConfigGroup
--        2018-08-08 Add by wanghailong
--        Add new node ibDot11APProvisionAPIPv4 to ibDot11APTemplateTable
--        Add new node ibDot11APProvisionIPv4Mask to ibDot11APTemplateTable
--        Add new node ibDot11APProvisionAPIPv6 to ibDot11APTemplateTable
--        Add new node ibDot11APProvisionIPv6PrefixLen to ibDot11APTemplateTable
--        Add new node ibDot11APProvisionACIPv4 to ibDot11APTemplateTable
--        Add new node ibDot11APProvisionACIpv6 to ibDot11APTemplateTable
--        Add new node ibDot11APProvisionGateWayIPV4 to ibDot11APTemplateTable
--        Add new node ibDot11APProvisionGateWayIPV6 to ibDot11APTemplateTable
--        Add new node ibDot11APProvisionSave to ibDot11GlobeConfigGroup
--        2018-10-17 Add by huanglu,zhangming
--        Add new node ibDot11ServiceSetVlanGroup to ibDot11APServiceSetTable
--        Add macAndDot1x(7) to ibDot11L2AuthenMode
--        2018-12-11 Add by wangshujuan
--        Add new node ibDot11ApRenameCurrentName to ibDot11GlobeConfigGroup
--        Add new node ibDot11ApRenameNewName     to ibDot11GlobeConfigGroup
--        Add ibDot11RemoteCfgApTable
--        Add ibDot11RemoteCfgIFTable
--        2020-08-03 Add by qiuchunxia
--        Add new ibDot11IPLearningTable
--        Add new node ibDot11IPLearningServiceName to ibDot11IPLearningVlanBitMapH
--        2020-08-12 Add by suting
--        Add new node ibDot11APMapConfigFileName to ibDot11APTemplateTable
--        Add ibDot11CfgSPInCirMode to ibDot11RadioToConfigTable
--        Add ibDot11CfgSPInCirValue to ibDot11RadioToConfigTable
--        Add ibDot11CfgSPOutCirMode to ibDot11RadioToConfigTable
--        Add ibDot11CfgSPOutCirValue to ibDot11RadioToConfigTable
--        2020-12-29 Add by zhoucailu,sunchangquan
--        Add ibDot11RmtIfManagement to ibDot11RemoteCfgIFTable
--        Add ibDot11WlanInfCustomerPVID to ibDot11ServicePolicyTable
--   V3.7 2021-06-18 modified by liyapeng
--        Modify description of ibDot11PreambleLen
--        Modify description of ibDot11StatisIntervMode, ibDot11StatisIntervModeCM And ibDot11SIDAPStatisIntervMode
--   V3.8 2023-04-24 modified by qiuchunxia
--        Modify ibDot11CfgSaRptDevType and ibDot11CfgSaTrapDevType
--        2023-08-20 modified by wanggongshuai
--        Modify ibDot11nChanelBand, ibDot11nRadioCfg2ChannelBand and ibDot11nRadioCfg2ChannelBandCM
-- =============================================================================
IB-DOT11-CFG-MIB DEFINITIONS ::= BEGIN

IMPORTS
        TruthValue,
        RowStatus,
        DisplayString,
        DateAndTime,
        MacAddress
    FROM SNMPv2-TC
        ifIndex
    FROM RFC1213-MIB
        MODULE-IDENTITY,
        NOTIFICATION-TYPE,
        OBJECT-TYPE,
        Integer32,
        Unsigned32,
        IpAddress
    FROM SNMPv2-SMI
        InetAddress
    FROM INET-ADDRESS-MIB
        ibDot11,
        IbDot11RadioType,
        IbDot11TxPwrLevelScopeType,
        IbDot11ChannelScopeType,
        IbDot11SSIDStringType,
        IbDot11AuthenType,
        IbDot11RadioScopeType,
        IbDot11SSIDEncryptModeType,
        IbDot11SecIEStatusType,
        IbDot11PreambleType,
        IbDot11ServicePolicyIDType,
        IbDot11TunnelSecSchemType,
        IbDot11RadioElementIndex,
        IbDot11WorkMode,
        IbDot11CirMode,
        ibDot11APElementIndex,
        IbDot11ObjectIDType,
        IbDot11RadioType2,
        IbDot11TruthValueCM
    FROM IB-DOT11-REF-MIB;

ibDot11CFG MODULE-IDENTITY
    LAST-UPDATED "202308201800Z"        -- Aug 20, 2023 at 18:00 GMT
    ORGANIZATION
        "Intelbras S.A. Industria de Telecomunicacao Eletronica Brasileria."
    CONTACT-INFO
        ""
    DESCRIPTION
        "This MIB provides information about WLAN configuration.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Fat AP
        Applied in the home, SOHO and so on, and it could
        work independently without help from AC.

        Fit AP
        Applied in the enterprise environment, it will work
        under the control and management from AC.

        Control And Provisioning of Wireless Access Points Protocol
        The short name of protocol is CAPWAP.  AC will control
        and manage AP by CAPWAP tunnel protocol defined by IETF.
        Also, a data tunnel will be set up between AC and AP.

        BSS
        IEEE 802.11 Basic Service Set (Radio Cell).  The
        BSS of an AP comprises of the stations directly
        associating with the AP.

        Radio
        The chip set to receive and send wireless signal.

        Association
        The service used to establish access point
        or station mapping and enable station invocation
        of the distribution system services.
        (Wireless clients attempt to connect to
        access points.)

        Basic Rate
        A data rate that is mandatory for client
        devices to support in order for them to achieve
        successful association.

        MSDU
        MAC Service Data Unit, it is frame format defined by
        802.11.

        TU
        It is 1,024 microseconds (ms), which is about 1
        millisecond.

        AKM
        The authentication and key management method defined by
        802.11i, and which includes 802.1x and pre-shared key."
    REVISION "202308201800Z"        -- Aug 20, 2023 at 18:00 GMT
    DESCRIPTION
        " Modified to add new values. "
    REVISION "202304241800Z"        -- Apr 24, 2023 at 18:00 GMT
    DESCRIPTION
        " Modified to add new values. "
    REVISION "202106181800Z"        -- Jun 18, 2021 at 18:00 GMT
    DESCRIPTION
        " Modify nodes with incorrect description information "
    REVISION "202012111800Z"        -- Dec 11, 2020 at 18:00 GMT
    DESCRIPTION
        "Modified to add new nodes and new tables."
    REVISION "201710091800Z"        -- Oct 09, 2017 at 18:00 GMT
    DESCRIPTION
        "Modified to add new nodes and new table."
    REVISION "201603111800Z"        -- Mar 11, 2016 at 18:00 GMT
    DESCRIPTION
        "Modified to add new nodes and new table."
    REVISION "201409191800Z"        -- Sep 19, 2014 at 18:00 GMT
    DESCRIPTION
        "Modified to add new nodes and new table."
    REVISION "201009251800Z"        -- Sep 25, 2010 at 18:00 GMT
    DESCRIPTION
        "Modified to remove some issue."
    REVISION "201009021800Z"        -- Sep 2, 2010 at 18:00 GMT
    DESCRIPTION
        "Modified to add new node."
    REVISION "200907291800Z"        -- Jul 29, 2009 at 18:00 GMT
    DESCRIPTION
        "Modified to add new nodes and new table."
    REVISION "200905072000Z"        -- May 7, 2009 at 20:00 GMT
    DESCRIPTION
        "Modified to add new nodes and new table."
    REVISION "200903201530Z"        -- Mar 20, 2009 at 15:30 GMT
    DESCRIPTION
        "Modified to add new value for appointed node."
    REVISION "200811071530Z"        -- Nov 07, 2008 at 15:30 GMT
    DESCRIPTION
        "Modified to add new nodes and new table."
    REVISION "200807091800Z"        -- July 09, 2008 at 18:00 GMT
    DESCRIPTION
        "Modified to add new groups."
    REVISION "200802251800Z"        -- Feb 25, 2008 at 18:00 GMT
    DESCRIPTION
        "Modified to add new nodes."
    REVISION "200712211800Z"        -- Dec 21, 2007 at 18:00 GMT
    DESCRIPTION
        "Modified to add new nodes."
    REVISION "200710091655Z"    -- October 09, 2007 at 16:55 GMT
    DESCRIPTION
        "changed for new requirements"
    REVISION "200706191800Z"        -- June 19, 2007 at 18:00 GMT
    DESCRIPTION
        "Modified to add new table."
    REVISION "200704272000Z"        -- Apr 27, 2007 at 20:00 GMT
    DESCRIPTION
        "Modified to fix some issue."
    REVISION "200702012000Z"        -- February 01, 2007 at 20:00 GMT
    DESCRIPTION
        "Modified to support fat AP."
    REVISION "200605101900Z"        -- May 10, 2006 at 19:00 GMT
    DESCRIPTION
        "The initial revision of this MIB module."
    ::= { ibDot11 4 }

-- *****************************************************************************
-- *  Major sections
-- *****************************************************************************
--  AP Configuration Group
--  DEFINED AS "The group to provide the configuration information
--  for APs.
ibDot11GlobeConfigGroup OBJECT IDENTIFIER  ::= { ibDot11CFG 1 }

ibDot11PolicyConfigGroup OBJECT IDENTIFIER ::= { ibDot11CFG 2 }
--  Policy Configuration Group has the following children:
--  ibDot11RadioPolicyTable            ::= { ibDot11PolicyConfigGroup 1 }
--  ibDot11ServicePolicyTable          ::= { ibDot11PolicyConfigGroup 2 }
--  ibDot11ServicePolicyExtTable       ::= { ibDot11PolicyConfigGroup 3 }
--  ibDot11RadioPolicyExtTable         ::= { ibDot11PolicyConfigGroup 4 }
--  ibDot11SrvPortSecurityTable        ::= { ibDot11PolicyConfigGroup 5 }
--  ibDot11SrvPolicyExtendTable        ::= { ibDot11PolicyConfigGroup 6 }
--  ibDot11SrvL2AuthenTable            ::= { ibDot11PolicyConfigGroup 7 }
--  ibDot11IPLearningTable             ::= { ibDot11PolicyConfigGroup 8 }

ibDot11APConfigGroup OBJECT IDENTIFIER     ::= { ibDot11CFG 3 }
--  AP Configuration Group has the following children:
--  ibDot11APTemplateTable                 ::= { ibDot11APConfigGroup 1 }
--  ibDot11RadioToConfigTable              ::= { ibDot11APConfigGroup 2 }
--  ibDot11APServiceSetTable               ::= { ibDot11APConfigGroup 3 }
--  ibDot11APSysInfoSetTable               ::= { ibDot11APConfigGroup 4 }
--  ibDot11APLimitTable                    ::= { ibDot11APConfigGroup 5 }
--  ibDot11APSerialIDTable                 ::= { ibDot11APConfigGroup 10 }
--  ibDot11APSTVlanTable                   ::= { ibDot11APConfigGroup 11 }
ibDot11RadioIntfConfigGroup OBJECT IDENTIFIER ::= { ibDot11CFG 4 }
--  Radio Interface Group has the following children:
--  ibDot11RadioIntfConfigTable          ::= { ibDot11RadioIntfConfigGroup 1 }
--  ibDot11RadioIntfBindTable            ::= { ibDot11RadioIntfConfigGroup 2 }

ibDot11DataRateConfigGroup OBJECT IDENTIFIER ::= { ibDot11CFG 5 }
--  Data Rate Config Group has the following children:
--  ibDot11DataRateConfigTable           ::= { ibDot11DataRateConfigGroup 1 }

ibDot11InterfaceConfigGroup OBJECT IDENTIFIER ::= { ibDot11CFG 6 }
--  Interface Config Group has the following children:
--  ibDot11WlanEssIfTable               ::= { ibDot11InterfaceConfigGroup 1 }
--  ibDot11WlanBssIfTable               ::= { ibDot11InterfaceConfigGroup 2 }
--  ibDot11WLANEthernetIfTable          ::= { ibDot11InterfaceConfigGroup 3 }
--  ibDot11PortSecurityTable            ::= { ibDot11InterfaceConfigGroup 4 }
--  ibDot11WlanMeshIfTable              ::= { ibDot11InterfaceConfigGroup 5 }

ibDot11ACBackupGroup OBJECT IDENTIFIER ::= { ibDot11CFG 7 }

ibDot11RadioElementConfigGroup OBJECT IDENTIFIER ::= { ibDot11CFG 8 }
--  Radio Element Config Group has the following children:
--  ibDot11nRadioCfgTable           ::= { ibDot11RadioElementConfigGroup 1 }
--  ibDot11RadioWDSTable            ::= { ibDot11RadioElementConfigGroup 2 }
--  ibDot11nRadioCfg2Table          ::= { ibDot11RadioElementConfigGroup 3 }

ibDot11CfgNotifyGroup OBJECT IDENTIFIER ::= { ibDot11CFG 9 }

ibDot11LocalACConfigGroup OBJECT IDENTIFIER     ::= { ibDot11CFG 10 }
--  LocalAC Configuration Group has the following children:
--  ibDot11LocalACTemplateTable                 ::= { ibDot11LocalACConfigGroup 1 }

ibDot11RemoteConfigGroup  OBJECT IDENTIFIER     ::= { ibDot11CFG 11 }
--  Remote Configuration Group has the following children:
--  ibDot11RemoteCfgApTable               ::= { ibDot11RemoteConfigGroup 1 }
--  ibDot11RemoteCfgIFTable               ::= { ibDot11RemoteConfigGroup 2 }

-- *****************************************************************************
-- *  ibDot11GlobeConfigGroup Definition
-- *****************************************************************************
ibDot11GlobalCountryCode OBJECT-TYPE
    SYNTAX      OCTET STRING(SIZE(3))
    MAX-ACCESS  read-write
    STATUS      current
    DESCRIPTION
        "Represents the country code for wireless network."
    ::= { ibDot11GlobeConfigGroup 1 }

ibDot11StaKeepALiveTimerIntvl OBJECT-TYPE
    SYNTAX      Unsigned32
    UNITS       "second"
    MAX-ACCESS  read-write
    STATUS      current
    DESCRIPTION
        "Represents the interval of the keep alive requests sent between
        AP and STA.
        Default value 0 : The keep alive function is disabled."
    DEFVAL      { 0 }
    ::= { ibDot11GlobeConfigGroup 2 }

ibDot11StaIdleTimerIntvl OBJECT-TYPE
    SYNTAX      Integer32
    UNITS       "second"
    MAX-ACCESS  read-write
    STATUS      current
    DESCRIPTION
        "Represents the interval for which the link between AP and STA
        ( power-save or awake ) can be idle."
    ::= { ibDot11GlobeConfigGroup 3 }

ibDot11BroadcastProbeReply OBJECT-TYPE
    SYNTAX      TruthValue
    MAX-ACCESS  read-write
    STATUS      current
    DESCRIPTION
        "Represents enable the AP to reply broadcast probe or not.
        'true' : The AP to reply broadcast probe is enabled.
        'false': The AP to reply broadcast probe is disabled"
    DEFVAL      { true }
    ::= { ibDot11GlobeConfigGroup 4 }

ibDot11APScanMode OBJECT-TYPE
    SYNTAX      INTEGER
        {
            active(1),
            passive(2)
        }
    MAX-ACCESS  read-write
    STATUS      current
    DESCRIPTION
        "Represents the scanning mode for AP.
        The following values are supported:
        active   - AP will actively do scan.
        passive  - AP will passively do scan."
    DEFVAL      { passive }
    ::= { ibDot11GlobeConfigGroup 5 }

ibDot11ACCtrlTunnelSecSupport OBJECT-TYPE
    SYNTAX      IbDot11TunnelSecSchemType
    MAX-ACCESS  read-write
    STATUS      current
    DESCRIPTION
        "Represents what security schemes are supported for CAPWAP Control
        tunnel."
    ::= { ibDot11GlobeConfigGroup 6 }

ibDot11ACDataTunnelSecSupport OBJECT-TYPE
    SYNTAX      IbDot11TunnelSecSchemType
    MAX-ACCESS  read-write
    STATUS      current
    DESCRIPTION
        "Represents what security schemes are supported for CAPWAP data
        tunnel.  The cleartxt is the default scheme."
    DEFVAL      { cleartxt }
    ::= { ibDot11GlobeConfigGroup 7 }

ibDot11ACAutoAPSupport OBJECT-TYPE
    SYNTAX      TruthValue
    MAX-ACCESS  read-write
    STATUS      current
    DESCRIPTION
        "Represents enable the auto AP functionality or not.
        'true' : The auto AP functionality is enabled.
        'false': The auto AP functionality is disabled"
    DEFVAL      { false }
    ::= { ibDot11GlobeConfigGroup 8 }

ibDot11AutoAPName OBJECT-TYPE
    SYNTAX      OCTET STRING(SIZE(0..127))
    MAX-ACCESS  read-write
    STATUS      current
    DESCRIPTION
        "Represents the name of auto AP that needs to be made persistent.
        When read the value from the node, NULL value be returned."
    ::= { ibDot11GlobeConfigGroup 9 }

ibDot11PersistentName OBJECT-TYPE
    SYNTAX      OCTET STRING(SIZE(0..127))
    MAX-ACCESS  read-write
    STATUS      current
    DESCRIPTION
        "Represents the new name of auto AP after being made persistent.
        When read the value from the node, NULL value be returned."
    ::= { ibDot11GlobeConfigGroup 10 }

ibDot11IntfTrapThreshold OBJECT-TYPE
    SYNTAX      Integer32
    UNITS       "dbm"
    MAX-ACCESS  read-write
    STATUS      current
    DESCRIPTION
        "Represents threshold of interference trap.  If signal strength of
        the device exceeds this threshold, corresponding trap will
        be sent."
    ::= { ibDot11GlobeConfigGroup 11 }

ibDot11MonitorInterval OBJECT-TYPE
    SYNTAX      Unsigned32(0 | 5..15)
    UNITS       "minute"
    MAX-ACCESS  read-write
    STATUS      current
    DESCRIPTION
        "Represents the monitoring interval.
        Default value 0 : The monitoring functionality is changed to
        real-time mode."
    DEFVAL      { 0 }
    ::= { ibDot11GlobeConfigGroup 12 }

ibDot11SampleInterval OBJECT-TYPE
    SYNTAX      Unsigned32(0 | 10..300)
    UNITS       "second"
    MAX-ACCESS  read-write
    STATUS      current
    DESCRIPTION
        "Represents the sampling interval.
        Default value 0 : The sampling functionality is disabled."
    DEFVAL      { 0 }
    ::= { ibDot11GlobeConfigGroup 13 }

ibDot11ChnlSwitChkInterval OBJECT-TYPE
    SYNTAX      Unsigned32(8..180)
    UNITS       "minute"
    MAX-ACCESS  read-write
    STATUS      current
    DESCRIPTION
        "Represents the checking interval of channel switch."
    DEFVAL      { 8 }
    ::= { ibDot11GlobeConfigGroup 14 }

ibDot11APUserUplimit OBJECT-TYPE
    SYNTAX      Unsigned32(0..65535)
    MAX-ACCESS  read-write
    STATUS      current
    DESCRIPTION
        "Represents the upper limit of user which has access to this AP."
    ::= { ibDot11GlobeConfigGroup 15 }

ibDot11APL2IsolateEnable OBJECT-TYPE
    SYNTAX      TruthValue
    MAX-ACCESS  read-write
    STATUS      current
    DESCRIPTION
        "Represents enable the layer2 isolation or not.
        'true' : The layer2 isolation functionality is enabled.
        'false': The layer2 isolation functionality is disabled."
    DEFVAL      { false }
    ::= { ibDot11GlobeConfigGroup 16 }

ibDot11APBSSIDSupportNum OBJECT-TYPE
    SYNTAX      Integer32
    MAX-ACCESS  read-only
    STATUS      current
    DESCRIPTION
        "Represents the max number of BSSID supported by Current AP."
    ::= { ibDot11GlobeConfigGroup 17 }

ibDot11APLastUpdateStatTime OBJECT-TYPE
    SYNTAX      DateAndTime
    MAX-ACCESS  read-only
    STATUS      current
    DESCRIPTION
        "Represents date and time update statistic information lately."
    ::= { ibDot11GlobeConfigGroup 18 }

ibDot11APDoSProtectEnable OBJECT-TYPE
    SYNTAX      TruthValue
    MAX-ACCESS  read-write
    STATUS      current
    DESCRIPTION
        "Represents enable the DOS protection or not.
        'true' : The DOS protection functionality is enabled.
        'false': The DOS protection functionality is disabled."
    DEFVAL      { false }
    ::= { ibDot11GlobeConfigGroup 19 }

ibDot11MaxAPPerIf OBJECT-TYPE
    SYNTAX      Unsigned32(0..65535)
    MAX-ACCESS  read-write
    STATUS      current
    DESCRIPTION
        "Represents max AP number that can be connected to AC interface."
    ::= { ibDot11GlobeConfigGroup 20 }

ibDot11SampleTimeStamp OBJECT-TYPE
    SYNTAX      DateAndTime
    MAX-ACCESS  read-only
    STATUS      current
    DESCRIPTION
        "Represents the start time of current sample period."
    ::= { ibDot11GlobeConfigGroup 21 }

ibDot11UplinkTrackId OBJECT-TYPE
    SYNTAX      Unsigned32
    MAX-ACCESS  read-write
    STATUS      current
    DESCRIPTION
        "Represents the track id of AP.
        Default value 0 : The uplink track function for AP is disabled."
    DEFVAL      { 0 }
    ::= { ibDot11GlobeConfigGroup 22 }

ibDot11RtCollectSwitch OBJECT-TYPE
    SYNTAX      TruthValue
    MAX-ACCESS  read-write
    STATUS      current
    DESCRIPTION
        "This object is used to turn on/off real-time statistics collection
         between AC and AP.  If the value is true, ibDot11RtCollectIntvl will
         take effect.  Otherwise, ibDot11RglCollectIntvl will take effect."
    DEFVAL      { false }
    ::= { ibDot11GlobeConfigGroup 23 }

ibDot11RglCollectIntvl OBJECT-TYPE
    SYNTAX      Integer32
    UNITS       "second"
    MAX-ACCESS  read-write
    STATUS      current
    DESCRIPTION
        "This object represents interval to regularly collect statistics from
         AC to AP."
    ::= { ibDot11GlobeConfigGroup 24 }

ibDot11RtCollectIntvl OBJECT-TYPE
    SYNTAX      Integer32
    UNITS       "second"
    MAX-ACCESS  read-write
    STATUS      current
    DESCRIPTION
        "This object represents interval to collect real-time statistics from
         AC to AP."
    ::= { ibDot11GlobeConfigGroup 25 }

ibDot11AllAPCpuUsageThreshold OBJECT-TYPE
    SYNTAX      Integer32(0..100)
    UNITS       "onepercent"
    MAX-ACCESS  read-write
    STATUS      current
    DESCRIPTION
        "The CPU usage threshold for all AP."
    ::= { ibDot11GlobeConfigGroup 26 }

ibDot11AllAPMemUsageThreshold OBJECT-TYPE
    SYNTAX      Integer32(0..100)
    UNITS       "onepercent"
    MAX-ACCESS  read-write
    STATUS      current
    DESCRIPTION
        "The memory usage threshold for all AP."
    ::= { ibDot11GlobeConfigGroup 27 }

ibDot11AdjIntfTrapThreshold OBJECT-TYPE
    SYNTAX      Integer32
    UNITS       "dbm"
    MAX-ACCESS  read-write
    STATUS      current
    DESCRIPTION
        "Represents threshold of adjacent interference trap.  If signal strength
        of the device exceeds this threshold, corresponding trap will be sent."
    ::= { ibDot11GlobeConfigGroup 28 }

ibDot11AllAPMonitorMode OBJECT-TYPE
    SYNTAX      INTEGER
        {
            normal(1),
            monitor(2),
            hybrid(3)
        }
    MAX-ACCESS  read-write
    STATUS      current
    DESCRIPTION
        "Represents what work mode for All AP.
        The following values are supported:
        normal,     - AP will supply WLAN service.
        monitor     - AP will be a monitor to find attack.
        hybrid      - AP will supply WLAN service and Device detection is
        enabled."
    DEFVAL      { normal }
    ::= { ibDot11GlobeConfigGroup 29 }

ibDot11GlobalApFmwUpdState OBJECT-TYPE
    SYNTAX      INTEGER
        {
            enable(1),
            disable(2)
        }
    MAX-ACCESS  read-write
    STATUS      current
    DESCRIPTION
        "Represents the status of version auto-update for an AP.
        The following values are supported:
        enable      - AP version will be updated automatically.
        disable     - AP version will not be updated automatically."
    DEFVAL      { enable }
    ::= { ibDot11GlobeConfigGroup 30 }

ibDot11ACNasIDCM OBJECT-TYPE
    SYNTAX      OCTET STRING
    MAX-ACCESS  read-write
    STATUS      current
    DESCRIPTION
        "Represents the NAS-ID of current AC."
    ::= { ibDot11GlobeConfigGroup 31 }

ibDot11ACRole OBJECT-TYPE
    SYNTAX      INTEGER
        {
            normal(1),
            central(2),
            local(3)
        }
    MAX-ACCESS  read-only
    STATUS      current
    DESCRIPTION
        "Current network status of AC.
        The following values are supported:
        normal,     - normal ac.
        central     - A central AC is an AC where local ACs are
                      configured, and it establishes CAPWAP tunnels
                      with the local ACs.
        local       - Local ACs provide network access to APs
                      and process client traffic. They are managed
                      by the central AC."
    DEFVAL      { normal }
    ::= { ibDot11GlobeConfigGroup 32 }

ibDot11GlobalLocalACState OBJECT-TYPE
    SYNTAX      INTEGER
        {
            enable(1),
            disable(2)
        }
    MAX-ACCESS  read-write
    STATUS      current
    DESCRIPTION
        "Represents the status of local-ac for an AC.
        The following values are supported:
        enable      - LocalAC state will be enabled.
        disable     - LocalAC state will not be enabled."
    DEFVAL      { disable }
    ::= { ibDot11GlobeConfigGroup 33 }

ibDot11CentralACIPAddress OBJECT-TYPE
    SYNTAX      IpAddress
    MAX-ACCESS  read-write
    STATUS      current
    DESCRIPTION
        "Represents the CentralAC IP address of LocalAC."
    ::= { ibDot11GlobeConfigGroup 34 }

ibDot11CentralACIPv6Address OBJECT-TYPE
    SYNTAX      OCTET STRING
    MAX-ACCESS  read-write
    STATUS      current
    DESCRIPTION
        "Represents the CentralAC IPv6 address of LocalAC."
    ::= { ibDot11GlobeConfigGroup 35 }

ibDot11iMcIP OBJECT-TYPE
    SYNTAX      IpAddress
    MAX-ACCESS  read-write
    STATUS      current
    DESCRIPTION
        "Represents the iMc IP address."
    ::= { ibDot11GlobeConfigGroup 36 }

ibDot11iMcPort OBJECT-TYPE
    SYNTAX      Integer32
    MAX-ACCESS  read-write
    STATUS      current
    DESCRIPTION
        "Represents the iMc Port."
    ::= { ibDot11GlobeConfigGroup 37 }

ibDot11APProvisionSave OBJECT-TYPE
    SYNTAX      OCTET STRING(SIZE(0..127))
    MAX-ACCESS  read-write
    STATUS      current
    DESCRIPTION
        "Sends the provisioned configuration to APs.
        When you read from this node, the system returns NULL."
    ::= { ibDot11GlobeConfigGroup 38 }

ibDot11ApRenameCurrentName OBJECT-TYPE
    SYNTAX      OCTET STRING(SIZE(0..127))
    MAX-ACCESS  read-write
    STATUS      current
    DESCRIPTION
        "Represents the current name of the AP that needs to be changed.
         When you read from the node, the system returns NULL."
    ::= { ibDot11GlobeConfigGroup 39 }

ibDot11ApRenameNewName OBJECT-TYPE
    SYNTAX      OCTET STRING(SIZE(0..127))
    MAX-ACCESS  read-write
    STATUS      current
    DESCRIPTION
        "Represents the new name of the AP.
         When you read from the node, the system returns NULL."
    ::= { ibDot11GlobeConfigGroup 40 }

ibDot11ACDescription OBJECT-TYPE
    SYNTAX      OCTET STRING
    MAX-ACCESS  read-write
    STATUS      current
    DESCRIPTION
        "This attribute will give more information about AC.
        Administrator could suggest the location, owner or
        other information for each AC.
        If the value is set to NULL, the description will be removed."
    ::= { ibDot11GlobeConfigGroup 41 }
-- *****************************************************************************
-- * End of ibDot11GlobeConfigGroup Definition
-- *****************************************************************************

-- *****************************************************************************
-- *  ibDot11RadioPolicyTable Definition
-- *****************************************************************************
ibDot11RadioPolicyTable OBJECT-TYPE
    SYNTAX      SEQUENCE OF IbDot11RadioPolicyEntry
    MAX-ACCESS  not-accessible
    STATUS      current
    DESCRIPTION
        "The table defines the parameters for radio policy, as per
        radio policy of CLI.
        One radio policy could be assigned to the different radios (AP)."
    ::= { ibDot11PolicyConfigGroup 1 }

ibDot11RadioPolicyEntry OBJECT-TYPE
    SYNTAX      IbDot11RadioPolicyEntry
    MAX-ACCESS  not-accessible
    STATUS      current
    DESCRIPTION
        "Each entry contains information of each radio policy."
    INDEX
        {
            IMPLIED ibDot11RadioPolicyName
        }
    ::= { ibDot11RadioPolicyTable 1 }

IbDot11RadioPolicyEntry ::= SEQUENCE
    {
        ibDot11RadioPolicyName        OCTET STRING,
        ibDot11BeaconInterval         Integer32,
        ibDot11DtimInterval           Integer32,
        ibDot11RtsThreshold           Integer32,
        ibDot11FragThreshold          Integer32,
        ibDot11ShortRetryThreshold    Integer32,
        ibDot11LongRetryThreshold     Integer32,
        ibDot11MaxRxLifetime          Unsigned32,
        ibDot11RdoPolicyRowStatus     RowStatus,
        ibDot11RdoClientMaxCount      Integer32,
        ibDot11BeaconIntervalMs       Integer32
    }

ibDot11RadioPolicyName OBJECT-TYPE
    SYNTAX      OCTET STRING(SIZE(0..127))
    MAX-ACCESS  not-accessible
    STATUS      current
    DESCRIPTION
        "Represents the name of radio policy."
    ::= { ibDot11RadioPolicyEntry 1 }

ibDot11BeaconInterval OBJECT-TYPE
    SYNTAX      Integer32
    UNITS       "TU"
    MAX-ACCESS  read-create
    STATUS      current
    DESCRIPTION
        "Represents the interval for Beacon management frame."
    DEFVAL      { 100 }
    ::= { ibDot11RadioPolicyEntry 2 }

ibDot11DtimInterval OBJECT-TYPE
    SYNTAX      Integer32
    MAX-ACCESS  read-create
    STATUS      current
    DESCRIPTION
        "Represents the number of beacon intervals that shall elapse
        between transmission of Beacons frames containing a Traffic
        Indication Map (TIM) element whose DTIM Count field is 0.
        This value is transmitted in the Delivery TIM (DTIM) Period
        field of Beacon frames."
    DEFVAL      { 1 }
    ::= { ibDot11RadioPolicyEntry 3 }

ibDot11RtsThreshold OBJECT-TYPE
    SYNTAX      Integer32
    UNITS       "byte"
    MAX-ACCESS  read-create
    STATUS      current
    DESCRIPTION
        "Represents the current minimum size, in octets, of the MAC
        protocol data unit (MPDU), below which a Request to send/Clear
        to send (RTS/CTS) handshake shall not be performed."
    DEFVAL      { 2346 }
    ::= { ibDot11RadioPolicyEntry 4 }

ibDot11FragThreshold OBJECT-TYPE
    SYNTAX      Integer32
    UNITS       "byte"
    MAX-ACCESS  read-create
    STATUS      current
    DESCRIPTION
        "Represents the current maximum size, in octets, of the MPDU that
        may be delivered to the PHY.  A MSDU shall be broken into
        fragments if its size exceeds the value of this attribute after
        adding MAC headers and trailers."
    DEFVAL      { 2346 }
    ::= { ibDot11RadioPolicyEntry 5 }

ibDot11ShortRetryThreshold OBJECT-TYPE
    SYNTAX      Integer32
    MAX-ACCESS  read-create
    STATUS      current
    DESCRIPTION
        "Represents the maximum number of transmission attempts of a
        frame, the length of which is less than or equal to
        ibDot11RTSThreshold, which shall be made before a failure
        condition is indicated."
    DEFVAL      { 7 }
    ::= { ibDot11RadioPolicyEntry 6 }

ibDot11LongRetryThreshold OBJECT-TYPE
    SYNTAX      Integer32
    MAX-ACCESS  read-create
    STATUS      current
    DESCRIPTION
        "Represents the maximum number of transmission attempts of a
        frame, the length of which is longer than ibDot11RTSThreshold,
        that shall be made before a failure condition is indicated."
    DEFVAL      { 4 }
    ::= { ibDot11RadioPolicyEntry 7 }

ibDot11MaxRxLifetime OBJECT-TYPE
    SYNTAX      Unsigned32
    UNITS       "millisecond"
    MAX-ACCESS  read-create
    STATUS      current
    DESCRIPTION
        "Represents the elapsed time.  After the time specified by
        ibDot11MaxRxLifetime, the further attempts to reassemble the
        MSDU shall be terminated."
    DEFVAL      { 2000 }
    ::= { ibDot11RadioPolicyEntry 8 }

ibDot11RdoPolicyRowStatus OBJECT-TYPE
    SYNTAX      RowStatus
    MAX-ACCESS  read-create
    STATUS      current
    DESCRIPTION
        "The status of this table entry."
    ::= { ibDot11RadioPolicyEntry 9 }

ibDot11RdoClientMaxCount OBJECT-TYPE
    SYNTAX      Integer32(0..2147483647)
    MAX-ACCESS  read-create
    STATUS      current
    DESCRIPTION
        "Represent the maximum number of stations supported by
        this radio policy."
    ::= { ibDot11RadioPolicyEntry 10 }

ibDot11BeaconIntervalMs OBJECT-TYPE
    SYNTAX      Integer32
    UNITS       "ms"
    MAX-ACCESS  read-create
    STATUS      current
    DESCRIPTION
        "Represents the interval for Beacon management frame."
    ::= { ibDot11RadioPolicyEntry 11 }
-- *****************************************************************************
-- * End of ibDot11RadioPolicyTable Definition
-- *****************************************************************************

-- *****************************************************************************
-- *  ibDot11ServicePolicyTable Definition
-- *****************************************************************************
ibDot11ServicePolicyTable OBJECT-TYPE
    SYNTAX      SEQUENCE OF IbDot11ServicePolicyEntry
    MAX-ACCESS  not-accessible
    STATUS      current
    DESCRIPTION
        "The table defines the parameters for ESS, as per service policy
        of CLI.
        One service policy could be assigned to the different radios
        (AP)."
    ::= { ibDot11PolicyConfigGroup 2 }

ibDot11ServicePolicyEntry OBJECT-TYPE
    SYNTAX      IbDot11ServicePolicyEntry
    MAX-ACCESS  not-accessible
    STATUS      current
    DESCRIPTION
        "Each entry contains information of each service policy."
    INDEX
        {
            ibDot11ServicePolicyID
        }
    ::= { ibDot11ServicePolicyTable 1 }

IbDot11ServicePolicyEntry ::= SEQUENCE
    {
        ibDot11ServicePolicyID       IbDot11ServicePolicyIDType,
        ibDot11SSIDName              IbDot11SSIDStringType,
        ibDot11SSIDHidden            TruthValue,
        ibDot11AuthenMode            IbDot11AuthenType,
        ibDot11SSIDEncryptionMode    IbDot11SSIDEncryptModeType,
        ibDot11WlanInfBindingType    OCTET STRING,
        ibDot11WlanInfBindingID      Integer32,
        ibDot11SrvPolicyRowStatus    RowStatus,
        ibDot11ClientMaxCount        Integer32,
        ibDot11SPInCirMode           IbDot11CirMode,
        ibDot11SPInCirValue          Integer32,
        ibDot11SPOutCirMode          IbDot11CirMode,
        ibDot11SPOutCirValue         Integer32,
        ibDot11WlanInfPVID           Integer32,
        ibDot11SPInCirStaticValue    Integer32,
        ibDot11SPOutCirStaticValue   Integer32,
        ibDot11SPIsolate             TruthValue,
        ibDot11WlanexAuthServerIP    IpAddress,
        ibDot11SPBeaconMeasEnable    TruthValue,
        ibDot11SPBeaconMeasType      INTEGER,
        ibDot11SPBeaconMeasInterval  Integer32,
        ibDot11AuthenModeCM          INTEGER,
        ibDot11SecIEStatusCM         INTEGER,
        ibDot11SecurityCiphersCM     INTEGER,
        ibDot11SrvPolicyStatusCM     INTEGER,
        ibDot11SSIDHiddenCM          IbDot11TruthValueCM,
        ibDot11SPIsolateCM           IbDot11TruthValueCM,
        ibDot11FwdVlanBitMapLow      OCTET STRING,
        ibDot11FwdVlanBitMapHigh     OCTET STRING,
        ibDot11ServicePolicyName     OCTET STRING,
        ibDot11SecurityModeCM        INTEGER,
        ibDot11SPInCbsValue          Integer32,
        ibDot11SPOutCbsValue         Integer32,
        ibDot11WlanInfCustomerPVID   Integer32
    }

ibDot11ServicePolicyID OBJECT-TYPE
    SYNTAX      IbDot11ServicePolicyIDType
    MAX-ACCESS  not-accessible
    STATUS      current
    DESCRIPTION
        "Represents the ID of each service policy."
    ::= { ibDot11ServicePolicyEntry 1 }

ibDot11SSIDName OBJECT-TYPE
    SYNTAX      IbDot11SSIDStringType
    MAX-ACCESS  read-create
    STATUS      current
    DESCRIPTION
        "Represents the ESS.  As per CLI, the value of
        service policy name will be SSID."
    ::= { ibDot11ServicePolicyEntry 2 }

ibDot11SSIDHidden OBJECT-TYPE
    SYNTAX      TruthValue
    MAX-ACCESS  read-create
    STATUS      current
    DESCRIPTION
        "This attribute controls whether the SSID will be advertised in
        the beacon frame.
        If it is true, then SSID will not be advertised in the beacon
        frame."
    DEFVAL      { false }
    ::= { ibDot11ServicePolicyEntry 3 }

ibDot11AuthenMode OBJECT-TYPE
    SYNTAX      IbDot11AuthenType
    MAX-ACCESS  read-create
    STATUS      current
    DESCRIPTION
        "Represents the Authentication mode defined by 802.11."
    ::= { ibDot11ServicePolicyEntry 4 }

ibDot11SSIDEncryptionMode OBJECT-TYPE
    SYNTAX      IbDot11SSIDEncryptModeType
    MAX-ACCESS  read-create
    STATUS      current
    DESCRIPTION
        "Represents the encryption mode for this ESS."
    ::= { ibDot11ServicePolicyEntry 5 }

ibDot11WlanInfBindingType OBJECT-TYPE
    SYNTAX      OCTET STRING
    MAX-ACCESS  read-create
    STATUS      current
    DESCRIPTION
        "Represents the service policy will bind to what kind of
        data forwarding interface."
    DEFVAL      { "WLAN-ESS" }
    ::= { ibDot11ServicePolicyEntry 6 }

ibDot11WlanInfBindingID OBJECT-TYPE
    SYNTAX      Integer32
    MAX-ACCESS  read-create
    STATUS      current
    DESCRIPTION
        "Represents the interface ID of the interface that ESS will
        bind to.
        If the value is set to -1, the binding will be removed."
    ::= { ibDot11ServicePolicyEntry 7 }

ibDot11SrvPolicyRowStatus OBJECT-TYPE
    SYNTAX      RowStatus
    MAX-ACCESS  read-create
    STATUS      current
    DESCRIPTION
        "The status of this table entry."
    ::= { ibDot11ServicePolicyEntry 8 }

ibDot11ClientMaxCount OBJECT-TYPE
    SYNTAX      Integer32(0..2147483647)
    MAX-ACCESS  read-create
    STATUS      current
    DESCRIPTION
        "Represent the maximum number of stations supported by
        this service policy."
    ::= { ibDot11ServicePolicyEntry 9 }

ibDot11SPInCirMode OBJECT-TYPE
    SYNTAX      IbDot11CirMode
    MAX-ACCESS  read-create
    STATUS      current
    DESCRIPTION
        "
        CIR(committed information rate) mode of inbound direction.
        This object is useful only when the corresponding CIR is nonzero.
        If value of this object is changed, corresponding CIR will be reset."
    DEFVAL      { static }
    ::= { ibDot11ServicePolicyEntry 10 }

ibDot11SPInCirValue OBJECT-TYPE
    SYNTAX      Integer32
    UNITS       "Kbps"
    MAX-ACCESS  read-create
    STATUS      current
    DESCRIPTION
        "Represents the CIR of inbound direction of this service policy.
        If the value is 0, it means that no flow control is applied to
        the service policy, and the corresponding CIR mode is meaningless."
    DEFVAL      { 0 }
    ::= { ibDot11ServicePolicyEntry 11 }

ibDot11SPOutCirMode OBJECT-TYPE
    SYNTAX      IbDot11CirMode
    MAX-ACCESS  read-create
    STATUS      current
    DESCRIPTION
        "
        CIR(committed information rate) mode of outbound direction.
        This object is useful only when the corresponding CIR is nonzero.
        If value of this object is changed, corresponding CIR will be reset."
    DEFVAL      { static }
    ::= { ibDot11ServicePolicyEntry 12 }

ibDot11SPOutCirValue OBJECT-TYPE
    SYNTAX      Integer32
    UNITS       "Kbps"
    MAX-ACCESS  read-create
    STATUS      current
    DESCRIPTION
        "Represents the CIR of outbound direction of this service policy.
        If the value is 0, it means that no flow control is applied to
        the service policy, and the corresponding CIR mode is meaningless."
    DEFVAL      { 0 }
    ::= { ibDot11ServicePolicyEntry 13 }

ibDot11WlanInfPVID OBJECT-TYPE
    SYNTAX      Integer32
    MAX-ACCESS  read-create
    STATUS      current
    DESCRIPTION
        "Represents the VLAN ID of SSID."
    DEFVAL      { 1 }
    ::= { ibDot11ServicePolicyEntry 14 }

ibDot11SPInCirStaticValue  OBJECT-TYPE
    SYNTAX      Integer32
    UNITS       "Kbps"
    MAX-ACCESS  read-create
    STATUS      current
    DESCRIPTION
        "Represents the CIR of inbound direction for static CIR mode."
    DEFVAL      { 0 }
        ::= { ibDot11ServicePolicyEntry 15 }

ibDot11SPOutCirStaticValue  OBJECT-TYPE
    SYNTAX      Integer32
    UNITS       "Kbps"
    MAX-ACCESS  read-create
    STATUS      current
    DESCRIPTION
        "Represents the CIR of outbound direction for static CIR mode."
    DEFVAL      { 0 }
        ::= { ibDot11ServicePolicyEntry 16 }

ibDot11SPIsolate OBJECT-TYPE
    SYNTAX      TruthValue
    MAX-ACCESS  read-create
    STATUS      current
    DESCRIPTION
        "If it is true, then stations connected with the service policy are
         isolated."
    DEFVAL      { false }
    ::= { ibDot11ServicePolicyEntry 17 }

ibDot11WlanexAuthServerIP OBJECT-TYPE
    SYNTAX     IpAddress
    MAX-ACCESS read-create
    STATUS     current
    DESCRIPTION
        "Represents the IP address of the Wlanex Authentication server"
    ::= {  ibDot11ServicePolicyEntry 18 }

ibDot11SPBeaconMeasEnable OBJECT-TYPE
    SYNTAX      TruthValue
    MAX-ACCESS  read-create
    STATUS      current
    DESCRIPTION
        "If it is true, then beacon-measurement is enabled."
    DEFVAL      { false }
    ::= { ibDot11ServicePolicyEntry 19  }

ibDot11SPBeaconMeasType OBJECT-TYPE
      SYNTAX      INTEGER
        {
            passive(1),
            active(2),
            beaconTable(3)
        }
    MAX-ACCESS  read-create
    STATUS      current
    DESCRIPTION
        "Represents what the work mode for BeaconMeasurement type.
        The following values are supported:
        passive,      - BeaconMeasurement will use the passive type.
        active        - BeaconMeasurement will use the active type.
        beaconTable   - BeaconMeasurement will use the beacon table type."
    DEFVAL      { beaconTable }
    ::= { ibDot11ServicePolicyEntry 20 }

ibDot11SPBeaconMeasInterval OBJECT-TYPE
    SYNTAX      Integer32(10..200)
    UNITS       "second"
    MAX-ACCESS  read-create
    STATUS      current
    DESCRIPTION
        "Represents the beacon-measurement interval."
    DEFVAL      { 60 }
    ::= { ibDot11ServicePolicyEntry 21 }

ibDot11AuthenModeCM OBJECT-TYPE
    SYNTAX      INTEGER
        {
            opensystem(0),
            sharedkey(1)
        }
    MAX-ACCESS  read-create
    STATUS      current
    DESCRIPTION
        "Represents the Authentication mode defined by 802.11."
    ::= { ibDot11ServicePolicyEntry 22 }

ibDot11SecIEStatusCM OBJECT-TYPE
    SYNTAX      INTEGER
        {
            none(0),
            wpa(1),
            wpa2(2),
            wlanex(3)
        }
    MAX-ACCESS  read-create
    STATUS      current
    DESCRIPTION
        "To enable the security Information element in the beacon and
        probe response frames sent by AP."
    ::= { ibDot11ServicePolicyEntry 23 }

ibDot11SecurityCiphersCM OBJECT-TYPE
    SYNTAX      INTEGER
        {
            none(0),
            wep40(1),
            wep104(2),
            tkip(3),
            aesccmp(4),
            wpisms4(5)
        }
    MAX-ACCESS  read-create
    STATUS      current
    DESCRIPTION
        "The WLAN system support the following cipher type for data frame
        encryption.
        none
        wep40
        wep104
        tkip
        aesccmp
        wpi-SMS4
        When the value of node equals to zero, it means no configuration or
        undo operation."
    ::= { ibDot11ServicePolicyEntry 24 }

ibDot11SrvPolicyStatusCM OBJECT-TYPE
    SYNTAX      INTEGER
        {
            off(0),
            on(1)
        }
    MAX-ACCESS read-create
    STATUS     current
    DESCRIPTION
        "The status of the Service Policy."
    ::= {  ibDot11ServicePolicyEntry 25 }

ibDot11SSIDHiddenCM OBJECT-TYPE
    SYNTAX      IbDot11TruthValueCM
    MAX-ACCESS  read-create
    STATUS      current
    DESCRIPTION
        "This attribute controls whether the SSID will be advertised in
        beacon frames.
        If it is dot11true, the SSID will not be advertised in beacon
        frames."
    DEFVAL      { dot11false }
    ::= { ibDot11ServicePolicyEntry 26 }

ibDot11SPIsolateCM OBJECT-TYPE
    SYNTAX      IbDot11TruthValueCM
    MAX-ACCESS  read-create
    STATUS      current
    DESCRIPTION
        "If it is dot11true, the clients connected with the service policy are
        isolated to each other."
    DEFVAL      { dot11false }
    ::= { ibDot11ServicePolicyEntry 27 }

ibDot11FwdVlanBitMapLow OBJECT-TYPE
    SYNTAX OCTET STRING (SIZE(0..256))
    MAX-ACCESS read-create
    STATUS current
    DESCRIPTION
        "Each octet within this value specifies a set of eight
         VLANs, with the first octet specifying VLANs 1 through 8,
         the second octet specifying VLANs 9 through 16, etc.
         Within each octet, the most significant bit represents
         the highest numbered VLAN, and the least significant bit
         represents the lowest numbered VLAN. Thus, each untagged
         VLAN of the hybrid port is represented by a single bit
         within the value of this object. If that bit has a value
         of '1' then that VLAN is untagged in the set of VLANs; the
         VLAN is not untagged if its bit has a value of '0'."
    ::= { ibDot11ServicePolicyEntry 28 }

ibDot11FwdVlanBitMapHigh OBJECT-TYPE
    SYNTAX OCTET STRING (SIZE(0..256))
    MAX-ACCESS read-create
    STATUS current
    DESCRIPTION
        "Each octet within this value specifies a set of eight
         VLANs, with the first octet specifying VLANs 1 through 8,
         the second octet specifying VLANs 9 through 16, etc.
         Within each octet, the most significant bit represents
         the highest numbered VLAN, and the least significant bit
         represents the lowest numbered VLAN. Thus, each untagged
         VLAN of the hybrid port is represented by a single bit
         within the value of this object. If that bit has a value
         of '1' then that VLAN is untagged in the set of VLANs; the
         VLAN is not untagged if its bit has a value of '0'."
    ::= { ibDot11ServicePolicyEntry 29 }

ibDot11ServicePolicyName OBJECT-TYPE
    SYNTAX      OCTET STRING
    MAX-ACCESS  read-create
    STATUS      current
    DESCRIPTION
        "Represents the name of each service policy."
    ::= { ibDot11ServicePolicyEntry 30 }

ibDot11SecurityModeCM OBJECT-TYPE
    SYNTAX INTEGER
        {
            none(0),
            psk(1),
            radius(2),
            wlanex(3)
        }
    MAX-ACCESS read-write
    STATUS current
    DESCRIPTION
        "Determines the security modes of the WLAN port.

        none  - The default value. No security mode is set.

        psk  - Access to the port is denied until the port client is
        authorized (by 802.1X key negotiation).

        radius  - Access to the port is denied until the port
        client is authorized (by 802.1X).

        wlanex  - Access to the port is denied until the port client is
        authenticated by wlan cert."
    ::= { ibDot11ServicePolicyEntry 31 }

 ibDot11SPInCbsValue  OBJECT-TYPE
    SYNTAX      Integer32
    UNITS       "byte"
    MAX-ACCESS  read-create
    STATUS      current
    DESCRIPTION
        "Represents the CBS of inbound direction of this service policy.
        If the value is 0, it means that the CBS is automatically calculated
        from the value of CIR."
    DEFVAL      { 0 }
    ::= { ibDot11ServicePolicyEntry 32 }

ibDot11SPOutCbsValue  OBJECT-TYPE
    SYNTAX      Integer32
    UNITS       "byte"
    MAX-ACCESS  read-create
    STATUS      current
    DESCRIPTION
        "Represents the CBS of outbound direction of this service policy.
        If the value is 0, it means that the CBS is automatically calculated
        from the value of CIR."
    DEFVAL      { 0 }
    ::= { ibDot11ServicePolicyEntry 33 }

ibDot11WlanInfCustomerPVID OBJECT-TYPE
    SYNTAX      Integer32
    MAX-ACCESS  read-create
    STATUS      current
    DESCRIPTION
        "Represents the customer PVID."
    ::= { ibDot11ServicePolicyEntry 34 }
-- *****************************************************************************
-- * End of ibDot11ServicePolicyTable Definition
-- *****************************************************************************

-- *****************************************************************************
-- *  ibDot11ServicePolicyExtTable Definition
-- *****************************************************************************
ibDot11ServicePolicyExtTable OBJECT-TYPE
    SYNTAX      SEQUENCE OF IbDot11ServicePolicyExtEntry
    MAX-ACCESS  not-accessible
    STATUS      current
    DESCRIPTION
        "The table defines the parameters for ESS, as per service policy
        of CLI.
        When the value of ibDot11SSIDEncryptionMode equals to cipher(2),
        more configuration for a ESS will be put into the table."
    ::= { ibDot11PolicyConfigGroup 3 }

ibDot11ServicePolicyExtEntry OBJECT-TYPE
    SYNTAX      IbDot11ServicePolicyExtEntry
    MAX-ACCESS  not-accessible
    STATUS      current
    DESCRIPTION
        "Each entry contains information of each service policy under cipher(2)
        mode."
    INDEX
        {
            ibDot11ServicePolicyExtID
        }
    ::= { ibDot11ServicePolicyExtTable 1 }

IbDot11ServicePolicyExtEntry ::= SEQUENCE
    {
        ibDot11ServicePolicyExtID       IbDot11ServicePolicyIDType,
        ibDot11SecIEStatus              IbDot11SecIEStatusType,
        ibDot11SecurityCiphers          Integer32,
        ibDot11CipherKeyIndex           Integer32,
        ibDot11CipherKey                OCTET STRING,
        ibDot11SrvPolicyExtRowStatus    RowStatus,
        ibDot11CipherKeyType            INTEGER,
        ibDot11AkmMode                  INTEGER,
        ibDot11PskKey                   OCTET STRING
    }

ibDot11ServicePolicyExtID OBJECT-TYPE
    SYNTAX      IbDot11ServicePolicyIDType
    MAX-ACCESS  not-accessible
    STATUS      current
    DESCRIPTION
        "Represents the ID of each service policy."
    ::= { ibDot11ServicePolicyExtEntry 1 }

ibDot11SecIEStatus OBJECT-TYPE
    SYNTAX      IbDot11SecIEStatusType
    MAX-ACCESS  read-create
    STATUS      current
    DESCRIPTION
        "To enable the security Information element in the beacon and
        probe response frames sent by AP."
    ::= { ibDot11ServicePolicyExtEntry 2 }

ibDot11SecurityCiphers OBJECT-TYPE
    SYNTAX      Integer32
    MAX-ACCESS  read-create
    STATUS      current
    DESCRIPTION
        "The WLAN system support the following cipher type for data frame
        encryption.
        wep40(2)
        tkip(4)
        aesccmp(16)
        wep104(32)
        wpisms4(64)
        wep128(128)
        For each service policy, it could support multiple cipher types at
        the same time.  So the value of object could combine multiple value
        of cipher type above.
        When the value of node equals to zero, it means no configuration or
        undo operation."
    ::= { ibDot11ServicePolicyExtEntry 3 }

ibDot11CipherKeyIndex OBJECT-TYPE
    SYNTAX      Integer32
    MAX-ACCESS  read-create
    STATUS      current
    DESCRIPTION
        "Represents the key index of cipher key for packet.
        When ibDot11SecurityCiphers value is wep40 or wep104,
        the configuration will take effective."
    DEFVAL      { 1 }
    ::= { ibDot11ServicePolicyExtEntry 4 }

ibDot11CipherKey OBJECT-TYPE
    SYNTAX      OCTET STRING
    MAX-ACCESS  read-create
    STATUS      current
    DESCRIPTION
        "Represents the cipher key for packet.
        When ibDot11SecurityCiphers value is wep40 or wep104,
        the configuration will take effective."
    ::= { ibDot11ServicePolicyExtEntry 5 }

ibDot11SrvPolicyExtRowStatus OBJECT-TYPE
    SYNTAX      RowStatus
    MAX-ACCESS  read-create
    STATUS      current
    DESCRIPTION
        "The status of this table entry."
    ::= { ibDot11ServicePolicyExtEntry 6 }

ibDot11CipherKeyType OBJECT-TYPE
    SYNTAX      INTEGER
    {
        char(1),
        hex(2)
    }
    MAX-ACCESS  read-create
    STATUS      current
    DESCRIPTION
        "Represents the cipher key type of ibDot11CipherKey."
    DEFVAL    {1}
    ::= { ibDot11ServicePolicyExtEntry 7 }

ibDot11AkmMode OBJECT-TYPE
    SYNTAX      INTEGER
    {
        none(0),
        dot1x(1),
        psk(2)
    }
    MAX-ACCESS  read-create
    STATUS      current
    DESCRIPTION
        "The authentication and key management mode."
    DEFVAL    {0}
    ::= { ibDot11ServicePolicyExtEntry 8 }

ibDot11PskKey OBJECT-TYPE
    SYNTAX      OCTET STRING
    MAX-ACCESS  read-create
    STATUS      current
    DESCRIPTION
        "Represents the preshared key.  This configuration takes effect
        if the ibDot11AkmMode value is psk."
    ::= { ibDot11ServicePolicyExtEntry 9 }

-- *****************************************************************************
-- * End of ibDot11ServicePolicyExtTable Definition
-- *****************************************************************************

-- *****************************************************************************
-- *  ibDot11RadioPolicyExtTable Definition
-- *****************************************************************************
ibDot11RadioPolicyExtTable OBJECT-TYPE
    SYNTAX      SEQUENCE OF IbDot11RadioPolicyExtEntry
    MAX-ACCESS  not-accessible
    STATUS      current
    DESCRIPTION
        "The table defines the radio policy of each radio.
        It can't be modified if the radio policy is a default radio policy."
    ::= { ibDot11PolicyConfigGroup 4 }

ibDot11RadioPolicyExtEntry OBJECT-TYPE
    SYNTAX      IbDot11RadioPolicyExtEntry
    MAX-ACCESS  not-accessible
    STATUS      current
    DESCRIPTION
        "Each entry contains information of each radio policy."
    INDEX
        {
            ibDot11RPAPSerialID,
            ibDot11RPRadioID
        }
    ::= { ibDot11RadioPolicyExtTable 1 }

IbDot11RadioPolicyExtEntry ::= SEQUENCE
    {
        ibDot11RPAPSerialID             OCTET STRING,
        ibDot11RPRadioID                IbDot11RadioScopeType,
        ibDot11RPBeaconInterval         Integer32,
        ibDot11RPDtimInterval           Integer32,
        ibDot11RPRtsThreshold           Integer32,
        ibDot11RPFragThreshold          Integer32,
        ibDot11RPShortRetryThreshold    Integer32,
        ibDot11RPLongRetryThreshold     Integer32,
        ibDot11RPClientMaxCount         Integer32,
        ibDot11RPBeaconIntervalCM       Integer32
    }

ibDot11RPAPSerialID OBJECT-TYPE
    SYNTAX      OCTET STRING(SIZE(0..127))
    MAX-ACCESS  not-accessible
    STATUS      current
    DESCRIPTION
        "This object represents the Serial ID of AP."
    ::= { ibDot11RadioPolicyExtEntry 1 }

ibDot11RPRadioID OBJECT-TYPE
    SYNTAX      IbDot11RadioScopeType
    MAX-ACCESS  not-accessible
    STATUS      current
    DESCRIPTION
        "This object represents each radio."
    ::= { ibDot11RadioPolicyExtEntry 2 }

ibDot11RPBeaconInterval OBJECT-TYPE
    SYNTAX      Integer32
    UNITS       "milliseconds"
    MAX-ACCESS  read-write
    STATUS      current
    DESCRIPTION
        "This object represents the interval for Beacon management frame."
    DEFVAL      { 100 }
    ::= { ibDot11RadioPolicyExtEntry 3 }

ibDot11RPDtimInterval OBJECT-TYPE
    SYNTAX      Integer32
    MAX-ACCESS  read-write
    STATUS      current
    DESCRIPTION
        "This object represents the number of beacon intervals that shall elapse
        between transmissions of Beacons frames containing a Traffic
        Indication Map (TIM) element whose DTIM count field is 0.
        This value is transmitted in the Delivery TIM (DTIM) Period
        field of Beacon frames."
    DEFVAL      { 1 }
    ::= { ibDot11RadioPolicyExtEntry 4 }

ibDot11RPRtsThreshold OBJECT-TYPE
    SYNTAX      Integer32
    UNITS       "byte"
    MAX-ACCESS  read-write
    STATUS      current
    DESCRIPTION
        "This object represents the current minimum size, in octets, of the MAC
        protocol data unit (MPDU), below which a Request to send/Clear
        to send (RTS/CTS) handshake shall not be performed."
    DEFVAL      { 2346 }
    ::= { ibDot11RadioPolicyExtEntry 5 }

ibDot11RPFragThreshold OBJECT-TYPE
    SYNTAX      Integer32
    UNITS       "byte"
    MAX-ACCESS  read-write
    STATUS      current
    DESCRIPTION
        "This object represents the current maximum size, in octets, of the MPDU
         that may be delivered to the PHY.  A MSDU shall be broken into
        fragments if its size exceeds the value of this attribute after
        adding MAC headers and trailers."
    DEFVAL      { 2346 }
    ::= { ibDot11RadioPolicyExtEntry 6 }

ibDot11RPShortRetryThreshold OBJECT-TYPE
    SYNTAX      Integer32
    MAX-ACCESS  read-write
    STATUS      current
    DESCRIPTION
        "This object represents the maximum number of transmission attempts of a
        frame, the length of which is less than or equal to
        ibDot11RTSThreshold, that shall be made before a failure
        condition is indicated."
    DEFVAL      { 7 }
    ::= { ibDot11RadioPolicyExtEntry 7 }

ibDot11RPLongRetryThreshold OBJECT-TYPE
    SYNTAX      Integer32
    MAX-ACCESS  read-write
    STATUS      current
    DESCRIPTION
        "This object represents the maximum number of transmission attempts of a
        frame, the length of which is longer than ibDot11RTSThreshold,
        and that shall be made before a failure condition is indicated."
    DEFVAL      { 4 }
    ::= { ibDot11RadioPolicyExtEntry 8 }

ibDot11RPClientMaxCount OBJECT-TYPE
    SYNTAX      Integer32(0..2147483647)
    MAX-ACCESS  read-write
    STATUS      current
    DESCRIPTION
        "This object represents the maximum number of stations supported by
        this radio policy."
    ::= { ibDot11RadioPolicyExtEntry 9 }

ibDot11RPBeaconIntervalCM OBJECT-TYPE
    SYNTAX      Integer32
    UNITS       "timeunit"
    MAX-ACCESS  read-write
    STATUS      current
    DESCRIPTION
        "This object represents beacon interval."
    DEFVAL      { 100 }
    ::= { ibDot11RadioPolicyExtEntry 10 }

-- *****************************************************************************
-- * End of ibDot11RadioPolicyTable Definition
-- *****************************************************************************
-- *****************************************************************************
-- *  ibDot11ServicePolicyPortSecurityTable Definition
-- *****************************************************************************
ibDot11SrvPortSecurityTable OBJECT-TYPE
    SYNTAX      SEQUENCE OF IbDot11SrvPortSecurityEntry
    MAX-ACCESS  not-accessible
    STATUS      current
    DESCRIPTION
        "This table defines the WLAN security status for ESS, BSS and
        WLAN-Ethernet interface which binding the crypto service-template.
        Otherwise, when binding the clear service-template,
        ibPortSecurityTables should be used to configure port security."
    ::= { ibDot11PolicyConfigGroup 5 }

ibDot11SrvPortSecurityEntry OBJECT-TYPE
    SYNTAX      IbDot11SrvPortSecurityEntry
    MAX-ACCESS  not-accessible
    STATUS      current
    DESCRIPTION
        "There is a row in this table for service policy."
    INDEX
        {
            ibDot11SecurityServicePolicyID
        }
    ::= { ibDot11SrvPortSecurityTable 1 }

IbDot11SrvPortSecurityEntry ::= SEQUENCE
    {
        ibDot11SecurityServicePolicyID           IbDot11ServicePolicyIDType,
        ibDot11SrvPortSecurityMode               INTEGER,
        ibDot11SrvSecurityKeyType                INTEGER,
        ibDot11SrvSecurityPskKeyMode             INTEGER,
        ibDot11SrvSecurityPskKeyString           DisplayString,
        ibDot11SrvPortSecurityModeCM             INTEGER
    }

ibDot11SecurityServicePolicyID OBJECT-TYPE
    SYNTAX      IbDot11ServicePolicyIDType
    MAX-ACCESS  not-accessible
    STATUS      current
    DESCRIPTION
        "Represents the ID of each service policy."
    ::= { ibDot11SrvPortSecurityEntry 1 }

ibDot11SrvPortSecurityMode OBJECT-TYPE
    SYNTAX      INTEGER
        {
            noRestrictions(1),
            userLoginSecureExt(2),
            psk(3),
            macAddressAndPsk(4),
            userLoginSecureExtOrPsk(5),
            ext(6)
        }
    MAX-ACCESS  read-write
    STATUS      current
    DESCRIPTION
        "Determines the security modes of the WLAN port.

        noRestrictions  The default value, no any security mode is set.

        userLoginSecureExt  Access to the port is denied until the port
        client is authorized (by 802.1X).

        psk  Access to the port is denied until the port client is
        authorized (by 802.1X key negotiation).

        macAddressAndPsk  The MAC address is first authenticated and only if
        this succeeds does the psk then attempt user authentication.

        userLoginSecureExtOrPsk  This selects both the userLoginSecureExt and
        psk modes together such that either is allowed to authorized access.
        Which mode works for client depends on the client's choice.

        ext  Access to the port is denied until the port client is
        authenticated (by ext)."
    ::= { ibDot11SrvPortSecurityEntry 2 }

ibDot11SrvSecurityKeyType OBJECT-TYPE
    SYNTAX      INTEGER
        {
            userLoginTxKeyTypeNone(1),
            userLoginTxKeyTypeDot11Key(2),
            userLoginTxKeyTypeRsaRC4Key(3)
        }
    MAX-ACCESS  read-write
    STATUS      current
    DESCRIPTION
        "This indicates the key type in the 802.1X EAPOL_Key packet.

        userLoginTxKeyTypeNone  - This means the key type is not set yet.

        userLoginTxKeyTypeDot11Key  - This selects the 802.11 key type.

        userLoginTxKeyTypeRsaRC4Key  - This selects the RC4 key for RSA RC4
        session encryption."
    ::= { ibDot11SrvPortSecurityEntry 3 }

ibDot11SrvSecurityPskKeyMode OBJECT-TYPE
    SYNTAX      INTEGER
        {
            pskKeyModeNone(1),
            pskKeyModePassPhrase(2),
            pskKeyModeRawKey(3)
        }
    MAX-ACCESS  read-write
    STATUS      current
    DESCRIPTION
        "This is the password input mode.  When input as pskKeyModePassPhrase,
        ibDot11SrvSecurityPskKeyString must be 8 to 63 characters;
        when input as pskKeyModeRawKey, ibDot11SrvSecurityPskKeyString
        must be 64 characters and each character must be '0'-'9', 'a'-'f' and
        'A'-'F'."
    ::= { ibDot11SrvPortSecurityEntry 4 }

ibDot11SrvSecurityPskKeyString OBJECT-TYPE
    SYNTAX      DisplayString(SIZE(0..64))
    MAX-ACCESS  read-write
    STATUS      current
    DESCRIPTION
        "This is the password string used for psk authentication."
    ::= { ibDot11SrvPortSecurityEntry 5 }

ibDot11SrvPortSecurityModeCM OBJECT-TYPE
    SYNTAX INTEGER
        {
            none(0),
            psk(1),
            radius(2),
            wlanex(3)
        }
    MAX-ACCESS read-write
    STATUS current
    DESCRIPTION
        "Determines the security modes of the WLAN port.

        none  - The default value, no any security mode is set.

        psk  - Access to the port is denied until the port client is
        authorized (by 802.1X key negotiation).

        radius  - Access to the port is denied until the port
        client is authorized (by 802.1X).

        wlanex  - Access to the port is denied until the port client is
        authenticated by wlan cert."
    ::= { ibDot11SrvPortSecurityEntry 6 }

ibDot11SrvL2AuthenTable OBJECT-TYPE
    SYNTAX      SEQUENCE OF IbDot11SrvL2AuthenEntry
    MAX-ACCESS  not-accessible
    STATUS      current
    DESCRIPTION
        "This table defines the Layer 2 authentication status of service
         templates."
    ::= { ibDot11PolicyConfigGroup 7 }

ibDot11SrvL2AuthenEntry OBJECT-TYPE
    SYNTAX      IbDot11SrvL2AuthenEntry
    MAX-ACCESS  not-accessible
    STATUS      current
    DESCRIPTION
        "There is a row for a service template."
    INDEX
        {
            ibDot11SrvL2AuthenID
        }
    ::= { ibDot11SrvL2AuthenTable 1 }

IbDot11SrvL2AuthenEntry ::= SEQUENCE
    {
        ibDot11SrvL2AuthenID               IbDot11ServicePolicyIDType,
        ibDot11L2AuthenMode                INTEGER,
        ibDot11L2IntrusProtectEnable       TruthValue,
        ibDot11L2IntrusProtectOpt          INTEGER,
        ibDot11TempServiceStopTimer        Integer32,
        ibDot11TempBlockMACTimer           Integer32,
        ibDot11L2IgnoreAuthorization       TruthValue,
        ibDot11L2FailVLAN                  Integer32,
        ibDot11L2CriticalVLAN              Integer32,
        ibDot11L2AuthorFailOffline         TruthValue,
        ibDot11L2AccountFailOffline        TruthValue,
        ibDot11Dot1xHSEnable               TruthValue,
        ibDot11Dot1xSecureHSEnable         TruthValue,
        ibDot11Dot1xReauthenEnable         TruthValue,
        ibDot11Dot1xMandatoryDomain        OCTET STRING,
        ibDot11Dot1xMaxUserCount           Integer32,
        ibDot11MACAuthenDomain             OCTET STRING,
        ibDot11MACAuthenMaxUserCount       Integer32
    }

ibDot11SrvL2AuthenID OBJECT-TYPE
    SYNTAX      IbDot11ServicePolicyIDType
    MAX-ACCESS  not-accessible
    STATUS      current
    DESCRIPTION
        "Represents the ID of a service template."
    ::= { ibDot11SrvL2AuthenEntry 1 }

ibDot11L2AuthenMode OBJECT-TYPE
    SYNTAX      INTEGER
        {
            bypass(1),
            macAuthentication(2),
            macThenDot1xAuthentication(3),
            dot1xAuthentication(4),
            dot1xThenMacAuthentication(5),
            ouiThenDot1x(6),
            macAndDot1x(7)
        }
    MAX-ACCESS  read-write
    STATUS      current
    DESCRIPTION
        "Authentication mode of the service template.

        bypass  No authentication is required.

        macAuthentication  MAC authentication.

        macThenDot1xAuthentication  MAC authentication is executed first.
        If MAC authentication fails, 802.1X authentication is executed.

        dot1xAuthentication  Access to the port is denied until the client
        is authorized by 802.1X.

        dot1xThenMacAuthentication  802.1X authentication is executed first.
        If 802.1X authentication fails , MAC authentication is executed.

        ouiThenDot1x  OUI authentication is first executed.
        If OUI authentication fails, 802.1X authentication is executed."
    ::= { ibDot11SrvL2AuthenEntry 2 }

ibDot11L2IntrusProtectEnable OBJECT-TYPE
    SYNTAX      TruthValue
    MAX-ACCESS  read-write
    STATUS      current
    DESCRIPTION
        "Enables intrusion protection for the service template."
    ::= { ibDot11SrvL2AuthenEntry 3 }

ibDot11L2IntrusProtectOpt OBJECT-TYPE
    SYNTAX      INTEGER
        {
            blockMACTemporarily(1),
            stopServiceTemporarily(2),
            stopService(3)
        }
    MAX-ACCESS  read-write
    STATUS      current
    DESCRIPTION
        "Operation mode when intrusion is detected."
    ::= { ibDot11SrvL2AuthenEntry 4 }

ibDot11TempServiceStopTimer OBJECT-TYPE
    SYNTAX      Integer32(10..300)
    MAX-ACCESS  read-write
    STATUS      current
    DESCRIPTION
        "Time period for temporarily stopping service."
    ::= { ibDot11SrvL2AuthenEntry 5 }

ibDot11TempBlockMACTimer OBJECT-TYPE
    SYNTAX      Integer32(60..300)
    MAX-ACCESS  read-write
    STATUS      current
    DESCRIPTION
        "Time period for temporarily blocking user MACs."
    ::= { ibDot11SrvL2AuthenEntry 6 }

ibDot11L2IgnoreAuthorization OBJECT-TYPE
    SYNTAX      TruthValue
    MAX-ACCESS  read-write
    STATUS      current
    DESCRIPTION
        "Ignores all authorization information set by the server."
    ::= { ibDot11SrvL2AuthenEntry 7 }

ibDot11L2FailVLAN OBJECT-TYPE
    SYNTAX      Integer32(0..4094)
    MAX-ACCESS  read-write
    STATUS      current
    DESCRIPTION
        "VLAN for authentication failure.  0 means not configured."
    ::= { ibDot11SrvL2AuthenEntry 8 }

ibDot11L2CriticalVLAN OBJECT-TYPE
    SYNTAX      Integer32(0..4094)
    MAX-ACCESS  read-write
    STATUS      current
    DESCRIPTION
        "VLAN for server unavailability situation.  0 means not configured."
    ::= { ibDot11SrvL2AuthenEntry 9 }

ibDot11L2AuthorFailOffline OBJECT-TYPE
    SYNTAX      TruthValue
    MAX-ACCESS  read-write
    STATUS      current
    DESCRIPTION
        "Users are logged off if authorization fails."
    ::= { ibDot11SrvL2AuthenEntry 10 }

ibDot11L2AccountFailOffline OBJECT-TYPE
    SYNTAX      TruthValue
    MAX-ACCESS  read-write
    STATUS      current
    DESCRIPTION
        "Users are logged off if accounting fails."
    ::= { ibDot11SrvL2AuthenEntry 11 }

ibDot11Dot1xHSEnable OBJECT-TYPE
    SYNTAX      TruthValue
    MAX-ACCESS  read-write
    STATUS      current
    DESCRIPTION
        "Enables 802.1X handshake."
    ::= { ibDot11SrvL2AuthenEntry 12 }

ibDot11Dot1xSecureHSEnable OBJECT-TYPE
    SYNTAX      TruthValue
    MAX-ACCESS  read-write
    STATUS      current
    DESCRIPTION
        "Enables secure 802.1X handshake."
    ::= { ibDot11SrvL2AuthenEntry 13 }

ibDot11Dot1xReauthenEnable OBJECT-TYPE
    SYNTAX      TruthValue
    MAX-ACCESS  read-write
    STATUS      current
    DESCRIPTION
        "Enables 802.1X reauthentication."
    ::= { ibDot11SrvL2AuthenEntry 14 }

ibDot11Dot1xMandatoryDomain OBJECT-TYPE
    SYNTAX      OCTET STRING
    MAX-ACCESS  read-write
    STATUS      current
    DESCRIPTION
        "802.1X authentication domain of users for the service template."
    ::= { ibDot11SrvL2AuthenEntry 15 }

ibDot11Dot1xMaxUserCount OBJECT-TYPE
    SYNTAX      Integer32
    MAX-ACCESS  read-write
    STATUS      current
    DESCRIPTION
        "Maximum number of 802.1X users supported by the BSS bound to the service
        template."
    ::= { ibDot11SrvL2AuthenEntry 16 }

ibDot11MACAuthenDomain OBJECT-TYPE
    SYNTAX      OCTET STRING
    MAX-ACCESS  read-write
    STATUS      current
    DESCRIPTION
        "MAC authentication domain of users for the service template."
    ::= { ibDot11SrvL2AuthenEntry 17 }

ibDot11MACAuthenMaxUserCount OBJECT-TYPE
    SYNTAX      Integer32
    MAX-ACCESS  read-write
    STATUS      current
    DESCRIPTION
        "Maximum number of MAC authentication users supported by the BSS bound to
         the service template."
    ::= { ibDot11SrvL2AuthenEntry 18 }
-- *****************************************************************************
-- *  End of ibDot11PortSecurityTable Definition
-- *****************************************************************************

ibDot11IPLearningTable OBJECT-TYPE
    SYNTAX      SEQUENCE OF IbDot11IPLearningEntry
    MAX-ACCESS  not-accessible
    STATUS      current
    DESCRIPTION
        "The table specifies the IP learning type and status
        of service templates."
    ::= { ibDot11PolicyConfigGroup 8 }
ibDot11IPLearningEntry OBJECT-TYPE
    SYNTAX      IbDot11IPLearningEntry
    MAX-ACCESS  not-accessible
    STATUS      current
    DESCRIPTION
        "Each entry contains information about an IP learning entry."
    INDEX
        {
            ibDot11IPLearningServiceName,
            ibDot11IPLearningType
        }
    ::= { ibDot11IPLearningTable 1 }
IbDot11IPLearningEntry ::=
    SEQUENCE {
        ibDot11IPLearningServiceName      OCTET STRING,
        ibDot11IPLearningType             INTEGER,
        ibDot11IPLearningStatus           TruthValue,
        ibDot11IPLearningVlanBitMapL      OCTET STRING,
        ibDot11IPLearningVlanBitMapH      OCTET STRING
    }
ibDot11IPLearningServiceName  OBJECT-TYPE
    SYNTAX      OCTET STRING(SIZE (1..255))
    MAX-ACCESS  not-accessible
    STATUS      current
    DESCRIPTION
        "Represents the service name."
::= { ibDot11IPLearningEntry 1 }
ibDot11IPLearningType OBJECT-TYPE
    SYNTAX      INTEGER {
                invalid(1),
                arp(2),
                dhcp(3),
                dhcp6(4),
                nd(5)
                }
    MAX-ACCESS  not-accessible
    STATUS      current
    DESCRIPTION
        "Represents the IP learning type."
    ::= { ibDot11IPLearningEntry 2 }
ibDot11IPLearningStatus OBJECT-TYPE
    SYNTAX      TruthValue
    MAX-ACCESS  read-write
    STATUS      current
    DESCRIPTION
        "Represents the ip learning status of the interface.
         Setting this attribute to true enables IP learning on the interface."
    ::= { ibDot11IPLearningEntry 3 }
ibDot11IPLearningVlanBitMapL OBJECT-TYPE
    SYNTAX      OCTET STRING(SIZE(1..256))
    MAX-ACCESS  read-write
    STATUS      current
    DESCRIPTION
        "Each octet within this value specifies a set of eight
         VLANs, with the first octet specifying VLANs 1 through 8 and
         the second octet specifying VLANs 9 through 16, etc.
         Within each octet, the most significant bit represents
         the highest numbered VLAN, and the least significant bit
         represents the lowest numbered VLAN. Thus, each untagged
         VLAN of the hybrid port is represented by a single bit
         within the value of this object. If that bit has a value
         of '1', that VLAN is untagged in the set of VLANs; the
         VLAN is not untagged if its bit has a value of '0'."
    ::= { ibDot11IPLearningEntry 4 }
ibDot11IPLearningVlanBitMapH OBJECT-TYPE
    SYNTAX      OCTET STRING(SIZE(1..256))
    MAX-ACCESS  read-write
    STATUS      current
    DESCRIPTION
        "Each octet within this value specifies a set of eight
         VLANs, with the first octet specifying VLANs 1 through 8 and
         the second octet specifying VLANs 9 through 16, etc.
         Within each octet, the most significant bit represents
         the highest numbered VLAN, and the least significant bit
         represents the lowest numbered VLAN. Thus, each untagged
         VLAN of the hybrid port is represented by a single bit
         within the value of this object. If that bit has a value
         of '1', that VLAN is untagged in the set of VLANs; the
         VLAN is not untagged if its bit has a value of '0'."
    ::= { ibDot11IPLearningEntry 5 }
-- *****************************************************************************
-- *  ibDot11SrvPolicyExtendTable Definition
-- *****************************************************************************
ibDot11SrvPolicyExtendTable OBJECT-TYPE
    SYNTAX      SEQUENCE OF IbDot11SrvPolicyExtendEntry
    MAX-ACCESS  not-accessible
    STATUS      current
    DESCRIPTION
        "The table defines the parameters of each service policy."
    ::= { ibDot11PolicyConfigGroup 6 }

ibDot11SrvPolicyExtendEntry OBJECT-TYPE
    SYNTAX      IbDot11SrvPolicyExtendEntry
    MAX-ACCESS  not-accessible
    STATUS      current
    DESCRIPTION
        "Each entry contains information of each service policy."
    INDEX
        {
            ibDot11ServicePolicyID
        }
    ::= { ibDot11SrvPolicyExtendTable 1 }

IbDot11SrvPolicyExtendEntry ::= SEQUENCE
    {
        ibDot11SPEnable              INTEGER
    }

ibDot11SPEnable OBJECT-TYPE
    SYNTAX      INTEGER
    {
        enable(1),
        disable(2)
    }
    MAX-ACCESS  read-write
    STATUS      current
    DESCRIPTION
        "Represents whether the service policy is enabled."
    ::= { ibDot11SrvPolicyExtendEntry 1 }

-- *****************************************************************************
-- *  End of ibDot11ServicePolicyExtendTable Definition
-- *****************************************************************************

-- *****************************************************************************
-- *  ibDot11APTemplateTable Definition
-- *****************************************************************************
ibDot11APTemplateTable OBJECT-TYPE
    SYNTAX      SEQUENCE OF IbDot11APTemplateEntry
    MAX-ACCESS  not-accessible
    STATUS      current
    DESCRIPTION
        "By AP template CLI, administrator will configure the parameters of AP
        by convenience.
        Before AP boot up and connect to AC by CAPWAP tunnel, administrator
        will create AP template for each AP.  When AP connect to AC,
        AC will assign configuration to AP by ibDot11APSerialID
        information in AP template."
    ::= { ibDot11APConfigGroup 1 }

ibDot11APTemplateEntry OBJECT-TYPE
    SYNTAX      IbDot11APTemplateEntry
    MAX-ACCESS  not-accessible
    STATUS      current
    DESCRIPTION
        "Each entry contains configuration information for each AP."
    INDEX
        {
            ibDot11APTemplateName
        }
    ::= { ibDot11APTemplateTable 1 }

IbDot11APTemplateEntry ::= SEQUENCE
    {
        ibDot11APTemplateName             OCTET STRING,
        ibDot11APSerialID                 OCTET STRING,
        ibDot11TemplateAPModelAlias       OCTET STRING,
        ibDot11Description                OCTET STRING,
        ibDot11APWorkMode                 INTEGER,
        ibDot11APTemplateRowStatus        RowStatus,
        ibDot11APName                     OCTET STRING,
        ibDot11StatisInterv               Integer32,
        ibDot11APBroadcastProbeReply      TruthValue,
        ibDot11StaIdleTimerInterv         Integer32,
        ibDot11StaKeepAliveTimerInterv    Integer32,
        ibDot11APCir                      Integer32,
        ibDot11APCbs                      Integer32,
        ibDot11APPriorityLevel            Integer32,
        ibDot11APElementID                Integer32,
        ibDot11APDevDetectEnable          TruthValue,
        ibDot11APGetIPMethod              INTEGER,
        ibDot11StatisIntervMode           INTEGER,
        ibDot11ApTrapEnabled              TruthValue,
        ibDot11ApFmwUpdState              INTEGER,
        ibDot11StatisIntervModeCM         INTEGER,
        ibDot11ApNasIDCM                  OCTET STRING,
        ibDot11ApCoveragetype             INTEGER,
        ibDot11APControlAddressState      INTEGER,
        ibDot11APControlAddressIPv4       IpAddress,
        ibDot11APControlAddressIPv6       OCTET STRING,
        ibDot11APLocalACName              OCTET STRING,
        ibDot11APEchoInterval             Integer32,
        ibDot11APProvisionAPIPv4          IpAddress,
        ibDot11APProvisionIPv4Mask        Integer32,
        ibDot11APProvisionAPIPv6          OCTET STRING,
        ibDot11APProvisionIPv6PrefixLen   Integer32,
        ibDot11APProvisionACIPv4          IpAddress,
        ibDot11APProvisionACIpv6          OCTET STRING,
        ibDot11APProvisionGateWayIPV4     IpAddress,
        ibDot11APProvisionGateWayIPV6     OCTET STRING,
        ibDot11APMapConfigFileName        OCTET STRING
    }

ibDot11APTemplateName OBJECT-TYPE
    SYNTAX      OCTET STRING(SIZE(0..127))
    MAX-ACCESS  not-accessible
    STATUS      current
    DESCRIPTION
        "Represents the name of AP template."
    ::= { ibDot11APTemplateEntry 1 }

ibDot11APSerialID OBJECT-TYPE
    SYNTAX      OCTET STRING
    MAX-ACCESS  read-create
    STATUS      current
    DESCRIPTION
        "Represents AP serial id."
    ::= { ibDot11APTemplateEntry 2 }

ibDot11TemplateAPModelAlias OBJECT-TYPE
    SYNTAX      OCTET STRING
    MAX-ACCESS  read-create
    STATUS      current
    DESCRIPTION
        "Represents the alias of AP model name."
    ::= { ibDot11APTemplateEntry 3 }

ibDot11Description OBJECT-TYPE
    SYNTAX      OCTET STRING
    MAX-ACCESS  read-create
    STATUS      current
    DESCRIPTION
        "This attribute will give more information about AP.
        Administrator could suggest the location, owner or
        other information for each AP.
        If the value is set to NULL, the description will be removed."
    ::= { ibDot11APTemplateEntry 4 }

ibDot11APWorkMode OBJECT-TYPE
    SYNTAX      INTEGER
        {
            normal(1),
            monitor(2),
            hybrid(3)
        }
    MAX-ACCESS  read-create
    STATUS      current
    DESCRIPTION
        "Represents what work mode for AP.
        The following values are supported:
        normal      - AP will supply WLAN service.
        monitor     - AP will be a monitor to find attack.
        hybrid      - AP will supply WLAN service and Device detection is
        enabled."
    DEFVAL      { normal }
    ::= { ibDot11APTemplateEntry 5 }

ibDot11APTemplateRowStatus OBJECT-TYPE
    SYNTAX      RowStatus
    MAX-ACCESS  read-create
    STATUS      current
    DESCRIPTION
        "The status of this table entry."
    ::= { ibDot11APTemplateEntry 6 }

ibDot11APName OBJECT-TYPE
    SYNTAX      OCTET STRING
    MAX-ACCESS  read-create
    STATUS      current
    DESCRIPTION
        "Represents the AP name."
    ::= { ibDot11APTemplateEntry 7 }

ibDot11StatisInterv OBJECT-TYPE
    SYNTAX      Integer32
    UNITS       "second"
    MAX-ACCESS  read-create
    STATUS      current
    DESCRIPTION
        "Represents the interval of radio statistic."
    ::= { ibDot11APTemplateEntry 8 }

ibDot11APBroadcastProbeReply OBJECT-TYPE
    SYNTAX      TruthValue
    MAX-ACCESS  read-create
    STATUS      current
    DESCRIPTION
        "Represents enable the AP to reply broadcast probe or not.
        'true' : The AP to reply broadcast probe is enabled.
        'false': The AP to reply broadcast probe is disabled"
    DEFVAL      { true }
    ::= { ibDot11APTemplateEntry 9 }

ibDot11StaIdleTimerInterv OBJECT-TYPE
    SYNTAX      Integer32
    UNITS       "second"
    MAX-ACCESS  read-create
    STATUS      current
    DESCRIPTION
        "Represents the interval for which the link between AP and STA
        ( power-save or awake ) can be idle."
    ::= { ibDot11APTemplateEntry 10 }

ibDot11StaKeepAliveTimerInterv OBJECT-TYPE
    SYNTAX      Integer32
    UNITS       "second"
    MAX-ACCESS  read-create
    STATUS      current
    DESCRIPTION
        "Represents the interval of the keep alive requests sent between
        AP and STA."
    ::= { ibDot11APTemplateEntry 11 }

ibDot11APCir OBJECT-TYPE
    SYNTAX      Integer32
    UNITS       "Kbps"
    MAX-ACCESS  read-create
    STATUS      current
    DESCRIPTION
        "Represents the committed information rate between AP and AC."
    ::= { ibDot11APTemplateEntry 12 }

ibDot11APCbs OBJECT-TYPE
    SYNTAX      Integer32
    UNITS       "Bytes"
    MAX-ACCESS  read-create
    STATUS      current
    DESCRIPTION
        "Represents the committed burst size between AP and AC."
    ::= { ibDot11APTemplateEntry 13 }

ibDot11APPriorityLevel OBJECT-TYPE
    SYNTAX      Integer32 (0..7)
    MAX-ACCESS  read-create
    STATUS      current
    DESCRIPTION
        "This object represents the connection priority for the AP.
        If the connection priority is 7, the AC is considered as the
        primary AC for the AP."
    DEFVAL      { 4 }
    ::= { ibDot11APTemplateEntry 14 }

ibDot11APElementID OBJECT-TYPE
    SYNTAX      Integer32
    MAX-ACCESS  read-only
    STATUS      current
    DESCRIPTION
        "This object represents the AP element ID."
    ::= { ibDot11APTemplateEntry 15 }

ibDot11APDevDetectEnable OBJECT-TYPE
    SYNTAX      TruthValue
    MAX-ACCESS  read-create
    STATUS      current
    DESCRIPTION
        "Represents whether device detection is enabled or not.
         'true' : Device detection is enabled.
         'false': Device detection is disabled.
         If device detection is enabled, the AP will provide both device
         detection and WLAN data services.
         By default, the AP only provides WLAN data services.  When an AP works
         in monitor mode, that is, the value of object ibDot11APWorkMode is
         monitor, device detection cannot be enabled with object
         ibDot11APDevDetectEnable."
    DEFVAL      { false }
    ::= { ibDot11APTemplateEntry 16 }

ibDot11APGetIPMethod OBJECT-TYPE
    SYNTAX      INTEGER
    {
        dhcpAlloc(1),
        static(2)
    }
    MAX-ACCESS  read-create
    STATUS      current
    DESCRIPTION
        "This object represents the method how AP gets IP address."
    DEFVAL      { dhcpAlloc }
    ::= { ibDot11APTemplateEntry 17 }

ibDot11StatisIntervMode OBJECT-TYPE
    SYNTAX      INTEGER
    {
        normal(1),
        realtime(2)
    }
    MAX-ACCESS  read-create
    STATUS      current
    DESCRIPTION
        "This object represents the mode of statics interval.
         normal    - statics interval value between 10s to 240s
         realtime  - statics interval value between 0s to 5s"
    DEFVAL      { normal }
    ::= { ibDot11APTemplateEntry 18 }

ibDot11ApTrapEnabled OBJECT-TYPE
    SYNTAX      TruthValue
    MAX-ACCESS  read-write
    STATUS      current
    DESCRIPTION
        "Represents whether the trap status is enabled or not.
        'true'  : Enable  the trap status;
        'false' : Disable the trap status."
    DEFVAL      { true }
    ::= { ibDot11APTemplateEntry 19 }

ibDot11ApFmwUpdState OBJECT-TYPE
    SYNTAX      INTEGER
    {
        enable(1),
        disable(2),
        inherit(3)
    }
    MAX-ACCESS  read-create
    STATUS      current
    DESCRIPTION
        "Represents the status of version auto-update for an AP.
        The following values are supported:
        enable   - AP version will be updated automatically.
        disable  - AP version will not be updated automatically.
        inherit  - The status will inherit value from apgroup-view or system-view."
    DEFVAL      { inherit }
    ::= { ibDot11APTemplateEntry 20 }

ibDot11StatisIntervModeCM OBJECT-TYPE
    SYNTAX      INTEGER
    {
        off(0),
        on(1)
    }
    MAX-ACCESS  read-create
    STATUS      current
    DESCRIPTION
        "This object represents the mode of statistic interval.
        off    - statistic interval value between 10s to 240s
        on     - statistic interval value between 0s to 5s"
    DEFVAL      { off }
    ::= { ibDot11APTemplateEntry 21 }

ibDot11ApNasIDCM OBJECT-TYPE
    SYNTAX      OCTET STRING
    MAX-ACCESS  read-create
    STATUS      current
    DESCRIPTION
        "Represents the NAS-ID of current service policy for each
        specific radio of AP."
    ::= { ibDot11APTemplateEntry 22 }

ibDot11ApCoveragetype OBJECT-TYPE
    SYNTAX      INTEGER
    {
        school(1),
        traffic(2),
        shopping(3),
        company(4)
    }
    MAX-ACCESS  read-create
    STATUS      current
    DESCRIPTION
        "This object represents the coverage type of AP.
        school - the coverage type is school
        traffic - the coverage type is traffic
        shop - the coverage type is shop
        company - the coverage type is company"
    DEFVAL      { school }
    ::= { ibDot11APTemplateEntry 23 }

ibDot11APControlAddressState OBJECT-TYPE
    SYNTAX      INTEGER
        {
            enable(1),
            disable(2)
        }
    MAX-ACCESS  read-create
    STATUS      current
    DESCRIPTION
        "Represents the status of control address for an AP.
        The following values are supported:
        enable      - AC rediscovery will be enabled.
        disable     - AC rediscovery will be disabled."
        DEFVAL      { disable }
    ::= { ibDot11APTemplateEntry 24 }

ibDot11APControlAddressIPv4 OBJECT-TYPE
    SYNTAX      IpAddress
    MAX-ACCESS  read-create
    STATUS      current
    DESCRIPTION
        "Represents an AC IPv4 address for AC rediscovery."
    ::= { ibDot11APTemplateEntry 25 }

ibDot11APControlAddressIPv6 OBJECT-TYPE
    SYNTAX      OCTET STRING
    MAX-ACCESS  read-create
    STATUS      current
    DESCRIPTION
        "Represents an AC IPv6 address for AC rediscovery."
    ::= { ibDot11APTemplateEntry 26 }

ibDot11APLocalACName OBJECT-TYPE
    SYNTAX      OCTET STRING
    MAX-ACCESS  read-only
    STATUS      current
    DESCRIPTION
        "Represents the local AC name the AP belongs to."
    ::= { ibDot11APTemplateEntry 27 }

ibDot11APEchoInterval OBJECT-TYPE
    SYNTAX      Integer32
    MAX-ACCESS  read-write
    STATUS      current
    DESCRIPTION
        "This object represents the echo-interval of the AP."
    ::= { ibDot11APTemplateEntry 28 }

ibDot11APProvisionAPIPv4 OBJECT-TYPE
    SYNTAX      IpAddress
    MAX-ACCESS  read-write
    STATUS      current
    DESCRIPTION
        "Represents the IPv4 address of an AP."
    ::= { ibDot11APTemplateEntry 29 }

ibDot11APProvisionIPv4Mask OBJECT-TYPE
    SYNTAX      Integer32(1..31)
    MAX-ACCESS  read-write
    STATUS      current
    DESCRIPTION
        "Represents the IPv4 address mask of an AP."
    ::= { ibDot11APTemplateEntry 30 }

ibDot11APProvisionAPIPv6 OBJECT-TYPE
    SYNTAX      OCTET STRING
    MAX-ACCESS  read-write
    STATUS      current
    DESCRIPTION
        "Represents the IPv6 address of an AP."
    ::= { ibDot11APTemplateEntry 31 }

ibDot11APProvisionIPv6PrefixLen OBJECT-TYPE
    SYNTAX      Integer32(1..128)
    MAX-ACCESS  read-write
    STATUS      current
    DESCRIPTION
        "Represents the IPv6 address prefix length of an AP."
    ::= { ibDot11APTemplateEntry 32 }

ibDot11APProvisionACIPv4 OBJECT-TYPE
    SYNTAX      IpAddress
    MAX-ACCESS  read-write
    STATUS      current
    DESCRIPTION
        "Represents an AC IPv4 address for discovery."
    ::= { ibDot11APTemplateEntry 33 }

ibDot11APProvisionACIpv6 OBJECT-TYPE
    SYNTAX      OCTET STRING
    MAX-ACCESS  read-create
    STATUS      current
    DESCRIPTION
        "Represents an AC IPv6 address for discovery."
    ::= { ibDot11APTemplateEntry 34 }

ibDot11APProvisionGateWayIPV4 OBJECT-TYPE
    SYNTAX      IpAddress
    MAX-ACCESS  read-write
    STATUS      current
    DESCRIPTION
        "Represents the gateway IPv4 address for an AP."
    ::= { ibDot11APTemplateEntry 35 }

ibDot11APProvisionGateWayIPV6 OBJECT-TYPE
    SYNTAX      OCTET STRING
    MAX-ACCESS  read-create
    STATUS      current
    DESCRIPTION
        "Represents thre gateway IPv6 address for an AP."
    ::= { ibDot11APTemplateEntry 36 }

ibDot11APMapConfigFileName OBJECT-TYPE
    SYNTAX      OCTET STRING
    MAX-ACCESS  read-create
    STATUS      current
    DESCRIPTION
        "Represents the name of the AP MapConfigFile."
    ::= { ibDot11APTemplateEntry 37 }
-- *****************************************************************************
-- *  End of  ibDot11APTemplateTable Definition
-- *****************************************************************************

-- *****************************************************************************
-- *  ibDot11RadioToConfigTable Definition
-- *****************************************************************************
ibDot11RadioToConfigTable OBJECT-TYPE
    SYNTAX      SEQUENCE OF IbDot11RadioToConfigEntry
    MAX-ACCESS  not-accessible
    STATUS      current
    DESCRIPTION
        "Before AP connects to AC, administrator will configure radio
        parameter to each radio."
    ::= { ibDot11APConfigGroup 2 }

ibDot11RadioToConfigEntry OBJECT-TYPE
    SYNTAX      IbDot11RadioToConfigEntry
    MAX-ACCESS  not-accessible
    STATUS      current
    DESCRIPTION
        "Each entry contains configuration information for each radio."
    INDEX
        {
            ibDot11APTemplateNameCfg,
            ibDot11CfgRadioID
        }
    ::= { ibDot11RadioToConfigTable 1 }

IbDot11RadioToConfigEntry ::= SEQUENCE
    {
        ibDot11APTemplateNameCfg     OCTET STRING,
        ibDot11CfgRadioID            IbDot11RadioScopeType,
        ibDot11CfgRadioPolicyName    OCTET STRING,
        ibDot11CfgRadioType          IbDot11RadioType,
        ibDot11CfgChannel            IbDot11ChannelScopeType,
        ibDot11CfgMaxTxPowerLevel    IbDot11TxPwrLevelScopeType,
        ibDot11PreambleLen           IbDot11PreambleType,
        ibDot11CfgRadioStatus        TruthValue,
        ibDot11CfgRdElementID        Unsigned32,
        ibDot11CfgWorkMode           IbDot11WorkMode,
        ibDot11CfgPwrAttValue        Integer32,
        ibDot11RadioTxArithmetic     INTEGER,
        ibDot11CfgChannelLockStat    INTEGER,
        ibDot11CfgPowerLockStat      INTEGER,
        ibDot11CfgLBRdGroupId        Unsigned32,
        ibDot11CfgRRMSDRdGroupId     Unsigned32,
        ibDot11CfgRadioType2         IbDot11RadioType2,
        ibDot11CfgIDSEnable          TruthValue,
        ibDot11CfgSaEnable           TruthValue,
        ibDot11CfgSaCltRtFFTData     TruthValue,
        ibDot11CfgSaBand             INTEGER,
        ibDot11CfgSaRptDevType       BITS,
        ibDot11CfgSaTrapDevEnable    TruthValue,
        ibDot11CfgSaTrapDevType      BITS,
        ibDot11CfgSaTrapAQEnable     TruthValue,
        ibDot11CfgSaTrapAQThreshold  Integer32,
        ibDot11CfgSaDrivenRRMEnable  TruthValue,
        ibDot11CfgSaDrivenRRMSnt     INTEGER,
        ibDot11CfgSPInCirMode        IbDot11CirMode,
        ibDot11CfgSPInCirValue       Integer32,
        ibDot11CfgSPOutCirMode       IbDot11CirMode,
        ibDot11CfgSPOutCirValue      Integer32
    }

ibDot11APTemplateNameCfg OBJECT-TYPE
    SYNTAX      OCTET STRING(SIZE(0..127))
    MAX-ACCESS  not-accessible
    STATUS      current
    DESCRIPTION
        "Represents the name of AP template."
    ::= { ibDot11RadioToConfigEntry 1 }

ibDot11CfgRadioID OBJECT-TYPE
    SYNTAX      IbDot11RadioScopeType
    MAX-ACCESS  not-accessible
    STATUS      current
    DESCRIPTION
        "Represents each radio."
    ::= { ibDot11RadioToConfigEntry 2 }

ibDot11CfgRadioPolicyName OBJECT-TYPE
    SYNTAX      OCTET STRING
    MAX-ACCESS  read-write
    STATUS      current
    DESCRIPTION
        "Represents the name of radio policy."
    ::= { ibDot11RadioToConfigEntry 3 }

ibDot11CfgRadioType OBJECT-TYPE
    SYNTAX      IbDot11RadioType
    MAX-ACCESS  read-write
    STATUS      current
    DESCRIPTION
        "Represents the radio will work with which 802.11 radio type."
    ::= { ibDot11RadioToConfigEntry 4 }

ibDot11CfgChannel OBJECT-TYPE
    SYNTAX      IbDot11ChannelScopeType
    MAX-ACCESS  read-write
    STATUS      current
    DESCRIPTION
        "Represents the channel allocation of radio."
    ::= { ibDot11RadioToConfigEntry 5 }

ibDot11CfgMaxTxPowerLevel OBJECT-TYPE
    SYNTAX      IbDot11TxPwrLevelScopeType
    UNITS       "dbm"
    MAX-ACCESS  read-write
    STATUS      current
    DESCRIPTION
        "Represents the maximal transmit power scope for AP."
    ::= { ibDot11RadioToConfigEntry 6 }

ibDot11PreambleLen OBJECT-TYPE
    SYNTAX      IbDot11PreambleType
    MAX-ACCESS  read-write
    STATUS      current
    DESCRIPTION
        "Represents whether use long or short preamble for 802.11 MAC
        frame.
        When ibDot11CfgRadioType is either dot11b, dot11g or dot11gn,
        then value for ibDot11PreambleLen will be valid.
        Otherwise, the value for it will be invalid."
    DEFVAL      { short }
    ::= { ibDot11RadioToConfigEntry 7 }

ibDot11CfgRadioStatus OBJECT-TYPE
    SYNTAX      TruthValue
    MAX-ACCESS  read-write
    STATUS      current
    DESCRIPTION
        "Represents the radio admin status whether is enabled
        or disabled."
    ::= { ibDot11RadioToConfigEntry 8 }

ibDot11CfgRdElementID OBJECT-TYPE
    SYNTAX      Unsigned32
    MAX-ACCESS  read-only
    STATUS      current
    DESCRIPTION
        "Represents the element ID of this radio.  It comprises two parts.
        The highest 24 bits are AP element ID and the lowest 8 bits are
        radio ID."
    ::= { ibDot11RadioToConfigEntry 9 }

ibDot11CfgWorkMode OBJECT-TYPE
    SYNTAX      IbDot11WorkMode
    MAX-ACCESS  read-write
    STATUS      current
    DESCRIPTION
        "Represents work mode of the radio."
    ::= { ibDot11RadioToConfigEntry 10 }

ibDot11CfgPwrAttValue OBJECT-TYPE
    SYNTAX      Integer32
    MAX-ACCESS  read-write
    STATUS      current
    DESCRIPTION
        "Represents the value of power attenuation."
    ::= { ibDot11RadioToConfigEntry 11 }

ibDot11RadioTxArithmetic OBJECT-TYPE
    SYNTAX      INTEGER
        {
            quality(1),
            bandwidth(2)
        }
    MAX-ACCESS  read-write
    STATUS      current
    DESCRIPTION
        "Represents the transmission arithmetic of the radio.
        The following values are supported:
        quality   - Consider the quality first during the transmission.
        bandwidth - Consider the bandwidth first during the transmission."
    DEFVAL      { quality }
    ::= { ibDot11RadioToConfigEntry 12 }

ibDot11CfgChannelLockStat OBJECT-TYPE
    SYNTAX      INTEGER
        {
            unlocked(1),
            locked(2)
        }
    MAX-ACCESS  read-write
    STATUS      current
    DESCRIPTION
        "Represents locked status of channel on the radio."
    DEFVAL      { unlocked }
    ::= { ibDot11RadioToConfigEntry 13 }

ibDot11CfgPowerLockStat OBJECT-TYPE
    SYNTAX      INTEGER
        {
            unlocked(1),
            locked(2)
        }
    MAX-ACCESS  read-write
    STATUS      current
    DESCRIPTION
        "Represents locked status of power on the radio."
    DEFVAL      { unlocked }
    ::= { ibDot11RadioToConfigEntry 14 }

ibDot11CfgLBRdGroupId OBJECT-TYPE
    SYNTAX      Unsigned32
    MAX-ACCESS  read-write
    STATUS      current
    DESCRIPTION
        "Represents the load balance group ID allocated for the radio."
    ::= { ibDot11RadioToConfigEntry 15 }

ibDot11CfgRRMSDRdGroupId OBJECT-TYPE
    SYNTAX      Unsigned32
    MAX-ACCESS  read-write
    STATUS      current
    DESCRIPTION
        "Represents the RRM self-decisive group ID allocated for the radio."
    ::= { ibDot11RadioToConfigEntry 16 }

ibDot11CfgRadioType2 OBJECT-TYPE
    SYNTAX      IbDot11RadioType2
    MAX-ACCESS  read-write
    STATUS      current
    DESCRIPTION
        "Represents the radio will work with which 802.11 radio type."
    ::= { ibDot11RadioToConfigEntry 17 }

ibDot11CfgIDSEnable OBJECT-TYPE
    SYNTAX      TruthValue
    MAX-ACCESS  read-write
    STATUS      current
    DESCRIPTION
        "Represents whether intrusion detection is enabled for this radio."
    ::= { ibDot11RadioToConfigEntry 18 }

ibDot11CfgSaEnable OBJECT-TYPE
    SYNTAX      TruthValue
    MAX-ACCESS  read-write
    STATUS      current
    DESCRIPTION
        "Represents whether spectrum analysis is enabled."
    ::= { ibDot11RadioToConfigEntry 19 }

ibDot11CfgSaCltRtFFTData OBJECT-TYPE
    SYNTAX      TruthValue
    MAX-ACCESS  read-write
    STATUS      current
    DESCRIPTION
        "Represents whether to collect real-time FFT data for this radio."
    ::= { ibDot11RadioToConfigEntry 20 }

ibDot11CfgSaBand OBJECT-TYPE
    SYNTAX      INTEGER{
       dot11g(1),
       dot11aLower(2),
       dot11aMiddle(3),
       dot11aUpper(4)
    }
    MAX-ACCESS  read-write
    STATUS      current
    DESCRIPTION
        "Represents which band of channels will be monitored when collection
        real-time FFT data is enabled for this radio.  Detection of
        interference devices and air quality will also be affected.  Each band
        responds to the following channels.
         dot11g (Channels 1-14)
         dot11aLower (channels 36-64)
         dot11aMiddle (channels 100-140)
         dot11aUpper (channels 149-165)."
    ::= { ibDot11RadioToConfigEntry 21 }

ibDot11CfgSaRptDevType OBJECT-TYPE
    SYNTAX BITS
        {
            microwave(0),
            microwaveInverter(1),
            bluetooth(2),
            fixedFreqOthers(3),
            fixedFreqCordlessPhone(4),
            fixedFreqVideo(5),
            fixedFreqAudio(6),
            freqHopperOthers(7),
            freqHopperCordlessBase(8),
            freqHopperCordlessNetwork(9),
            freqHopperXbox(10),
            genericInterferer(11),
            freqHopperCordlessNetwork5g(12)
        }
    MAX-ACCESS read-write
    STATUS current
    DESCRIPTION
        "Represents which types of interference devices should be reported."
    ::= { ibDot11RadioToConfigEntry 22 }

ibDot11CfgSaTrapDevEnable OBJECT-TYPE
    SYNTAX TruthValue
    MAX-ACCESS read-write
    STATUS current
    DESCRIPTION
        "Represents whether trap is enabled for an interference device type."
    ::= { ibDot11RadioToConfigEntry 23 }

ibDot11CfgSaTrapDevType OBJECT-TYPE
    SYNTAX BITS
        {
            microwave(0),
            microwaveInverter(1),
            bluetooth(2),
            fixedFreqOthers(3),
            fixedFreqCordlessPhone(4),
            fixedFreqVideo(5),
            fixedFreqAudio(6),
            freqHopperOthers(7),
            freqHopperCordlessBase(8),
            freqHopperCordlessNetwork(9),
            freqHopperXbox(10),
            genericInterferer(11),
            freqHopperCordlessNetwork5g(12)
        }
    MAX-ACCESS read-write
    STATUS current
    DESCRIPTION
        "Represents for which interference device types the AP will send traps
         when trap sending is enabled."
    ::= { ibDot11RadioToConfigEntry 24 }

ibDot11CfgSaTrapAQEnable OBJECT-TYPE
    SYNTAX TruthValue
    MAX-ACCESS read-write
    STATUS current
    DESCRIPTION
        "Represents whether the channel quality trap is enabled."
    ::= { ibDot11RadioToConfigEntry 25 }

ibDot11CfgSaTrapAQThreshold OBJECT-TYPE
    SYNTAX Integer32(1..100)
    MAX-ACCESS read-write
    STATUS current
    DESCRIPTION
        "Represents the channel quality threshold.  When the channel quality
        is below this value, the channel quality trap will be sent."
    ::= { ibDot11RadioToConfigEntry 26 }

ibDot11CfgSaDrivenRRMEnable OBJECT-TYPE
    SYNTAX TruthValue
    MAX-ACCESS read-write
    STATUS current
    DESCRIPTION
        "Configures whether to run RRM when the AP detects
         a certain level of interference."
    ::= { ibDot11RadioToConfigEntry 27 }

ibDot11CfgSaDrivenRRMSnt OBJECT-TYPE
    SYNTAX INTEGER
    {
        low(1),
        medium(2),
        high(3)
    }
    MAX-ACCESS read-write
    STATUS current
    DESCRIPTION
        "Configures the threshold for triggering RRM.  When the
         interference level for the AP exceeds the threshold
         , RRM initiates local dynamic frequency selection (DFS)
         and changes the channel of the affected radio
         to improve network performance.  Low represents a decreased
         sensitivity to changes in the environment while high represents an
         increased sensitivity."
    ::= { ibDot11RadioToConfigEntry 28 }

ibDot11CfgSPInCirMode OBJECT-TYPE
   SYNTAX      IbDot11CirMode
    MAX-ACCESS  read-create
    STATUS      current
    DESCRIPTION
        "
        Specifies the committed information rate(CIR) mode for the inbound direction.
        This object is useful only when the corresponding CIR has a nonzero value.
        If the value of this object is changed, the corresponding CIR will be reset."
    DEFVAL      { static }
    ::= { ibDot11RadioToConfigEntry 29 }

ibDot11CfgSPInCirValue OBJECT-TYPE
    SYNTAX      Integer32
    UNITS       "Kbps"
    MAX-ACCESS  read-create
    STATUS      current
    DESCRIPTION
        "Represents the CIR for the inbound direction of this service policy.
        If the value is 0, it means that no flow control is applied to
        the service policy, and the corresponding CIR mode is meaningless."
    DEFVAL      { 0 }
    ::= { ibDot11RadioToConfigEntry 30 }

ibDot11CfgSPOutCirMode OBJECT-TYPE
    SYNTAX      IbDot11CirMode
    MAX-ACCESS  read-create
    STATUS      current
    DESCRIPTION
        "
        Represents the committed information rate(CIR) mode for the outbound direction.
        This object is useful only when the corresponding CIR has a nonzero value.
        If the value of this object is changed, the corresponding CIR will be reset."
    DEFVAL      { static }
    ::= { ibDot11RadioToConfigEntry 31 }

ibDot11CfgSPOutCirValue OBJECT-TYPE
    SYNTAX      Integer32
    UNITS       "Kbps"
    MAX-ACCESS  read-create
    STATUS      current
    DESCRIPTION
        "Represents the CIR for the outbound direction of this service policy.
        If the value is 0, it means that no flow control is applied to
        the service policy, and the corresponding CIR mode is meaningless."
    DEFVAL      { 0 }
    ::= { ibDot11RadioToConfigEntry 32 }

-- *****************************************************************************
-- *  End of  ibDot11RadioToConfigTable Definition
-- *****************************************************************************

-- *****************************************************************************
-- *  ibDot11APServiceSetTable Definition
-- *****************************************************************************
ibDot11APServiceSetTable OBJECT-TYPE
    SYNTAX      SEQUENCE OF IbDot11APServiceSetEntry
    MAX-ACCESS  not-accessible
    STATUS      current
    DESCRIPTION
        "For each radio, it could configure multiple service policies.
        The table describes the relationship between radio and
        service policies."
    ::= { ibDot11APConfigGroup 3 }

ibDot11APServiceSetEntry OBJECT-TYPE
    SYNTAX      IbDot11APServiceSetEntry
    MAX-ACCESS  not-accessible
    STATUS      current
    DESCRIPTION
        "Each entry contains service policy information for each
        specific radio of AP."
    INDEX
        {
            ibDot11APTemplateNameCfg,
            ibDot11CfgRadioID,
            ibDot11CfgServicePolicyID
        }
    ::= { ibDot11APServiceSetTable 1 }

IbDot11APServiceSetEntry ::= SEQUENCE
    {
        ibDot11CfgServicePolicyID    IbDot11ServicePolicyIDType,
        ibDot11SrvSetRowStatus       RowStatus,
        ibDot11ServiceSetVlanId      Integer32,
        ibDot11ServiceSetVlanGroup   OCTET STRING
    }

ibDot11CfgServicePolicyID OBJECT-TYPE
    SYNTAX      IbDot11ServicePolicyIDType
    MAX-ACCESS  not-accessible
    STATUS      current
    DESCRIPTION
        "Represents the ID of each service policy used by the AP."
    ::= { ibDot11APServiceSetEntry 1 }

ibDot11SrvSetRowStatus OBJECT-TYPE
    SYNTAX      RowStatus
    MAX-ACCESS  read-create
    STATUS      current
    DESCRIPTION
        "The status of this table entry."
    ::= { ibDot11APServiceSetEntry 2 }

ibDot11ServiceSetVlanId OBJECT-TYPE
    SYNTAX      Integer32(0..4094)
    MAX-ACCESS  read-create
    STATUS      current
    DESCRIPTION
        "Represents the Vlan ID of BSS which is generated when service policy
        is binded with the Radio."
    ::= { ibDot11APServiceSetEntry 3 }

ibDot11ServiceSetVlanGroup OBJECT-TYPE
    SYNTAX      OCTET STRING(SIZE(0..31))
    MAX-ACCESS  read-create
    STATUS      current
    DESCRIPTION
        "Represents the VLAN group of the BSS generated when a service policy
        is bound to the radio."
    ::= { ibDot11APServiceSetEntry 4 }
-- *****************************************************************************
-- * End of ibDot11APServiceSetTable Definition
-- *****************************************************************************

-- *****************************************************************************
-- *  ibDot11APSTVlanTable Definition
-- *****************************************************************************
ibDot11APSTVlanTable OBJECT-TYPE
    SYNTAX      SEQUENCE OF IbDot11APSTVlanEntry
    MAX-ACCESS  not-accessible
    STATUS      current
    DESCRIPTION
        "For each service policy, it could be bind to several VLANs.
        The table describes the relationship between VLAN and
        service policies."
    ::= { ibDot11APConfigGroup 11 }

ibDot11APSTVlanEntry OBJECT-TYPE
    SYNTAX      IbDot11APSTVlanEntry
    MAX-ACCESS  not-accessible
    STATUS      current
    DESCRIPTION
        "Each entry contains VLAN and service policy information for each
        specific radio of AP."
    INDEX
        {
            ibDot11SIDAPSerialID,
            ibDot11CfgRadioID,
            ibDot11CfgServicePolicyID
        }
    ::= { ibDot11APSTVlanTable 1 }

IbDot11APSTVlanEntry ::= SEQUENCE
    {
        ibDot11CfgSTVLANID           Integer32,
        ibDot11CfgSTNASPortID        OCTET STRING,
        ibDot11CfgServiceSetRowStatus    RowStatus,
        ibDot11CfgSTNASID            OCTET STRING
    }

ibDot11CfgSTVLANID OBJECT-TYPE
    SYNTAX      Integer32(0..4094)
    MAX-ACCESS  read-create
    STATUS      current
    DESCRIPTION
        "Represents the VLAN that current Service Policy have bind to."
    ::= { ibDot11APSTVlanEntry 1 }

ibDot11CfgSTNASPortID OBJECT-TYPE
    SYNTAX      OCTET STRING(SIZE(0..127))
    MAX-ACCESS  read-only
    STATUS      current
    DESCRIPTION
        "Represents the NAS Port ID of current Service Policy for each
        specific radio of AP."
    ::= { ibDot11APSTVlanEntry 2 }

ibDot11CfgServiceSetRowStatus OBJECT-TYPE
    SYNTAX      RowStatus
    MAX-ACCESS  read-create
    STATUS      current
    DESCRIPTION
        "The status of this table entry."
    ::= { ibDot11APSTVlanEntry 3 }

ibDot11CfgSTNASID OBJECT-TYPE
    SYNTAX      OCTET STRING(SIZE(0..127))
    MAX-ACCESS  read-only
    STATUS      current
    DESCRIPTION
        "Represents the NAS ID of current Service Policy for each
        specific radio of AP."
    ::= { ibDot11APSTVlanEntry 4 }
-- *****************************************************************************
-- * End of ibDot11APSTVlanTable Definition
-- *****************************************************************************

-- *****************************************************************************
-- *  ibDot11APSysInfoSetTable Definition
-- *****************************************************************************
ibDot11APSysInfoSetTable OBJECT-TYPE
    SYNTAX      SEQUENCE OF IbDot11APSysInfoSetEntry
    MAX-ACCESS  not-accessible
    STATUS      current
    DESCRIPTION
        "The table of the system information for each AP."
    ::= { ibDot11APConfigGroup 4 }

ibDot11APSysInfoSetEntry OBJECT-TYPE
    SYNTAX      IbDot11APSysInfoSetEntry
    MAX-ACCESS  not-accessible
    STATUS      current
    DESCRIPTION
        "The system information configuration for each AP."
    INDEX
        {
            ibDot11SIDAPSerialID
        }
    ::= { ibDot11APSysInfoSetTable 1 }

IbDot11APSysInfoSetEntry ::= SEQUENCE
    {
        ibDot11APSysNetID            OCTET STRING,
        ibDot11APCpuUsageThreshold   Integer32,
        ibDot11APMemUsageThreshold   Integer32
    }

ibDot11APSysNetID OBJECT-TYPE
    SYNTAX      OCTET STRING(SIZE(0..127))
    MAX-ACCESS  read-write
    STATUS      current
    DESCRIPTION
        "Represents the system Net ID for AP."
    ::= { ibDot11APSysInfoSetEntry 1 }

ibDot11APCpuUsageThreshold OBJECT-TYPE
    SYNTAX      Integer32(0..100)
    UNITS       "onepercent"
    MAX-ACCESS  read-write
    STATUS      current
    DESCRIPTION
        "The CPU usage threshold for AP."
    ::= { ibDot11APSysInfoSetEntry 2 }

ibDot11APMemUsageThreshold OBJECT-TYPE
    SYNTAX      Integer32(0..100)
    UNITS       "onepercent"
    MAX-ACCESS  read-write
    STATUS      current
    DESCRIPTION
        "The memory usage threshold for AP."
    ::= { ibDot11APSysInfoSetEntry 3 }

-- *****************************************************************************
-- * End of ibDot11APSysInfoSetTable Definition
-- *****************************************************************************

-- *****************************************************************************
-- *  ibDot11APLimitTable Definition
-- *****************************************************************************
ibDot11APLimitTable OBJECT-TYPE
    SYNTAX      SEQUENCE OF IbDot11APLimitEntry
    MAX-ACCESS  not-accessible
    STATUS      current
    DESCRIPTION
        "For each connected APs, administrator could configure a series of
        limits.  This table describes the limit information for AP(s)."
    ::= { ibDot11APConfigGroup 5 }

ibDot11APLimitEntry OBJECT-TYPE
    SYNTAX      IbDot11APLimitEntry
    MAX-ACCESS  not-accessible
    STATUS      current
    DESCRIPTION
        "Each entry contains the limit information for each AP."
    INDEX
        {
            ibDot11APElementIndex
        }
    ::= { ibDot11APLimitTable 1 }

IbDot11APLimitEntry ::= SEQUENCE
    {
        ibDot11APSsidNumLimit     Integer32,
        ibDot11APUserCntLimit     Integer32,
        ibDot11APUserThreshold    Integer32
    }

ibDot11APSsidNumLimit OBJECT-TYPE
    SYNTAX      Integer32(0..65535)
    MAX-ACCESS  read-write
    STATUS      current
    DESCRIPTION
        "Represents the upper limit of service template binded
        with this AP.  All radios of AP share this limit.
        Default value 0 : There is no upper limit of service template
        binded with this AP."
    DEFVAL      { 0 }
    ::= { ibDot11APLimitEntry 1 }

ibDot11APUserCntLimit OBJECT-TYPE
    SYNTAX      Integer32(0..65535)
    MAX-ACCESS  read-write
    STATUS      current
    DESCRIPTION
        "Represents the upper limit of user which has access to this AP.
        All BSSs binded with AP share this limit.
        Default value 0 : There is no upper limit of user which has access
        to this AP."
    DEFVAL      { 0 }
    ::= { ibDot11APLimitEntry 2 }

ibDot11APUserThreshold OBJECT-TYPE
    SYNTAX      Integer32(0..65535)
    MAX-ACCESS  read-write
    STATUS      current
    DESCRIPTION
        "Represents the threshold of user which has access to this
        AP.  All BSSs binded with AP share this limit.  If the user counter
        is overflow, the trap will be sent.
        Default value 0 : There is no threshold of user which has access
        to this AP."
    DEFVAL      { 0 }
    ::= { ibDot11APLimitEntry 3 }
-- *****************************************************************************
-- * End of ibDot11APLimitTable Definition
-- *****************************************************************************

-- *****************************************************************************
-- * ibDot11APIfSetTable Definition
-- *****************************************************************************
ibDot11APIfSetTable OBJECT-TYPE
    SYNTAX      SEQUENCE OF IbDot11APIfSetEntry
    MAX-ACCESS  not-accessible
    STATUS      current
    DESCRIPTION
        "The table of the interface information for each AP."
    ::= { ibDot11APConfigGroup 6 }

ibDot11APIfSetEntry OBJECT-TYPE
    SYNTAX      IbDot11APIfSetEntry
    MAX-ACCESS  not-accessible
    STATUS      current
    DESCRIPTION
        "The interface information configuration for each AP."
    INDEX
        {
            ibDot11APElementIndex,
            ibDot11APSetIfIndex
        }
    ::= { ibDot11APIfSetTable 1 }

IbDot11APIfSetEntry ::= SEQUENCE
    {
        ibDot11APSetIfIndex      Integer32,
        ibDot11APIfAlias         DisplayString
    }

ibDot11APSetIfIndex OBJECT-TYPE
    SYNTAX      Integer32
    MAX-ACCESS  not-accessible
    STATUS      current
    DESCRIPTION
        "Represents the index for a interface."
    ::= { ibDot11APIfSetEntry 1 }

ibDot11APIfAlias OBJECT-TYPE
    SYNTAX      DisplayString
    MAX-ACCESS  read-write
    STATUS      current
    DESCRIPTION
        "This object is an 'alias' name for the interface as specified
        by a network manager for AP."
    ::= { ibDot11APIfSetEntry 2 }

-- *****************************************************************************
-- * End of ibDot11APIfSetTable Definition
-- *****************************************************************************

-- *****************************************************************************
-- *  ibDot11APServiceVlanTable Definition
-- *****************************************************************************
ibDot11APServiceVlanTable OBJECT-TYPE
    SYNTAX      SEQUENCE OF IbDot11APServiceVlanEntry
    MAX-ACCESS  not-accessible
    STATUS      current
    DESCRIPTION
        "For all the radios on the AP, it could configure multiple service policies.
        The table describes the relationship between AP and
        service policies."
    ::= { ibDot11APConfigGroup 7 }

ibDot11APServiceVlanEntry OBJECT-TYPE
    SYNTAX      IbDot11APServiceVlanEntry
    MAX-ACCESS  not-accessible
    STATUS      current
    DESCRIPTION
        "Each entry contains service policy information for each AP."
    INDEX
        {
            ibDot11APServiceVlanSerialID,
            ibDot11APServiceVlanSPID
        }
    ::= { ibDot11APServiceVlanTable 1 }

IbDot11APServiceVlanEntry ::= SEQUENCE
    {
        ibDot11APServiceVlanSerialID          OCTET STRING,
        ibDot11APServiceVlanSPID              IbDot11ServicePolicyIDType,
        ibDot11APServiceVlanId                Integer32,
        ibDot11APServiceVlanRowStatus         RowStatus

    }

ibDot11APServiceVlanSerialID OBJECT-TYPE
    SYNTAX      OCTET STRING
    MAX-ACCESS  not-accessible
    STATUS      current
    DESCRIPTION
        "This object represents AP serial id."
    ::= { ibDot11APServiceVlanEntry 1 }

ibDot11APServiceVlanSPID OBJECT-TYPE
    SYNTAX      IbDot11ServicePolicyIDType
    MAX-ACCESS  not-accessible
    STATUS      current
    DESCRIPTION
        "This object represents the ID of each service policy used by the AP."
    ::= { ibDot11APServiceVlanEntry 2 }

ibDot11APServiceVlanId OBJECT-TYPE
    SYNTAX      Integer32(0..4094)
    MAX-ACCESS  read-create
    STATUS      current
    DESCRIPTION
        "This object represents the VLAN ID of BSS which is generated when the
         service policy is bound to the radio."
    ::= { ibDot11APServiceVlanEntry 3 }

ibDot11APServiceVlanRowStatus OBJECT-TYPE
    SYNTAX      RowStatus
    MAX-ACCESS  read-create
    STATUS      current
    DESCRIPTION
        "This object represents the status of this table entry."
    ::= { ibDot11APServiceVlanEntry 4 }

-- *****************************************************************************
-- * End of ibDot11APServiceSetTable Definition
-- *****************************************************************************

-- *****************************************************************************
-- *  ibDot11RadioConfigTable Definition
-- *****************************************************************************
ibDot11RadioConfigTable OBJECT-TYPE
    SYNTAX      SEQUENCE OF IbDot11RadioConfigEntry
    MAX-ACCESS  not-accessible
    STATUS      current
    DESCRIPTION
        "Before AP connects to AC, administrator will configure radio
        parameter to each radio."
    ::= { ibDot11APConfigGroup 8 }

ibDot11RadioConfigEntry OBJECT-TYPE
    SYNTAX      IbDot11RadioConfigEntry
    MAX-ACCESS  not-accessible
    STATUS      current
    DESCRIPTION
        "Each entry contains configuration information for each radio."
    INDEX
        {
            ibDot11RCAPSerialID,
            ibDot11RCRadioID
        }
    ::= { ibDot11RadioConfigTable 1 }

IbDot11RadioConfigEntry ::= SEQUENCE
    {
        ibDot11RCAPSerialID               OCTET STRING,
        ibDot11RCRadioID                  IbDot11RadioScopeType,
        ibDot11RCRadioType                IbDot11RadioType,
        ibDot11RCChannel                  IbDot11ChannelScopeType,
        ibDot11RCPreambleLen              IbDot11PreambleType,
        ibDot11RCPwrAttValue              Integer32,
        ibDot11RCApPowerLevel             IbDot11TxPwrLevelScopeType,
        ibDot11RCDynamicChlState          TruthValue,
        ibDot11RCDynamicPowerState        TruthValue,
        ibDot11RCRadioStatus              TruthValue,
        ibDot11RCRadioRate                OCTET STRING,
        ibDot11RCPwrAdjustStepLength      Integer32,
        ibDot11RCRadioType2               IbDot11RadioType2,
        ibDot11RCPreambleLenCM            INTEGER,
        ibDot11RCDynamicChlStateCM        INTEGER,
        ibDot11RCRadioStatusCM            INTEGER,
        ibDot11RCRadioRateCM              OCTET STRING,
        ibDot11RCDynamicPowerStateCM      IbDot11TruthValueCM,
        ibDot11RCRssiThresholdCM          Integer32,
        ibDot11RCDynamicChlStateSelfDecisiveCM    IbDot11TruthValueCM,
        ibDot11RCDynamicPowerStateSelfDecisiveCM  IbDot11TruthValueCM
    }

ibDot11RCAPSerialID OBJECT-TYPE
    SYNTAX      OCTET STRING(SIZE(0..127))
    MAX-ACCESS  not-accessible
    STATUS      current
    DESCRIPTION
        "This object represents the Serial ID of AP."
    ::= { ibDot11RadioConfigEntry 1 }

ibDot11RCRadioID OBJECT-TYPE
    SYNTAX      IbDot11RadioScopeType
    MAX-ACCESS  not-accessible
    STATUS      current
    DESCRIPTION
        "This object represents each radio."
    ::= { ibDot11RadioConfigEntry 2 }

ibDot11RCRadioType OBJECT-TYPE
    SYNTAX      IbDot11RadioType
    MAX-ACCESS  read-write
    STATUS      current
    DESCRIPTION
        "This object represents the radio will work with which 802.11 radio
         type."
    ::= { ibDot11RadioConfigEntry 3 }

ibDot11RCChannel OBJECT-TYPE
    SYNTAX      IbDot11ChannelScopeType
    MAX-ACCESS  read-write
    STATUS      current
    DESCRIPTION
        "This object represents the channel allocation of radio."
    ::= { ibDot11RadioConfigEntry 4 }

ibDot11RCPreambleLen OBJECT-TYPE
    SYNTAX      IbDot11PreambleType
    MAX-ACCESS  read-write
    STATUS      current
    DESCRIPTION
        "This object represents whether use long or short preamble for 802.11
         MAC frame.
        When ibDot11CfgRadioType is either dot11b, dot11g or dot11gn,
        then value for ibDot11PreambleLen will be valid.
        Otherwise, the value for it will be invalid."
    DEFVAL      { short }
    ::= { ibDot11RadioConfigEntry 5 }

ibDot11RCPwrAttValue OBJECT-TYPE
    SYNTAX      Integer32
    MAX-ACCESS  read-write
    STATUS      current
    DESCRIPTION
        "This object represents the value of power attenuation."
    ::= { ibDot11RadioConfigEntry 6 }

ibDot11RCApPowerLevel OBJECT-TYPE
    SYNTAX      IbDot11TxPwrLevelScopeType
    UNITS       "dbm"
    MAX-ACCESS  read-write
    STATUS      current
    DESCRIPTION
        "Represents the maximal transmit power scope for AP."
    ::= { ibDot11RadioConfigEntry 7 }

ibDot11RCDynamicChlState OBJECT-TYPE
    SYNTAX      TruthValue
    MAX-ACCESS  read-write
    STATUS      current
    DESCRIPTION
        "Enable/Disable dynamic channel selection."
    ::= { ibDot11RadioConfigEntry 8 }

ibDot11RCDynamicPowerState OBJECT-TYPE
    SYNTAX      TruthValue
    MAX-ACCESS  read-write
    STATUS      current
    DESCRIPTION
        "Enable/Disable dynamic power selection for the band."
    ::= { ibDot11RadioConfigEntry 9 }

ibDot11RCRadioStatus OBJECT-TYPE
    SYNTAX      TruthValue
    MAX-ACCESS  read-write
    STATUS      current
    DESCRIPTION
        "Represents the radio admin status whether is enabled
        or disabled."
    ::= { ibDot11RadioConfigEntry 10 }

ibDot11RCRadioRate OBJECT-TYPE
    SYNTAX      OCTET STRING(SIZE(0..255))
    MAX-ACCESS  read-write
    STATUS      current
    DESCRIPTION
        "Set data transmit rates for the radio, in the format of 1,2,5.5...
        For 802.11n radios, the format can be MCS X.  The data transmit rates
        between AP and STA must fall into the configured rates.
        (Note: For 802.11n radios, the first value will be treated as a mandatory rate,
        and the second value will be treated as a supported rate.
        If you configure more than two rates, the configuration cannot take effect.
        If you configure only one rate, it is considered as the mandatory rate by default.)"
    ::= { ibDot11RadioConfigEntry 11 }

ibDot11RCPwrAdjustStepLength OBJECT-TYPE
    SYNTAX      Integer32
    MAX-ACCESS  read-only
    STATUS      current
    DESCRIPTION
        "Power adjustment step-length in dBm."
    ::= { ibDot11RadioConfigEntry 12 }

ibDot11RCRadioType2 OBJECT-TYPE
    SYNTAX      IbDot11RadioType2
    MAX-ACCESS  read-write
    STATUS      current
    DESCRIPTION
        "This object represents the radio will work with which 802.11 radio
         type."
    ::= { ibDot11RadioConfigEntry 13 }

ibDot11RCPreambleLenCM OBJECT-TYPE
    SYNTAX      INTEGER
        {
            long(0),
            short(1)
        }
    MAX-ACCESS  read-write
    STATUS      current
    DESCRIPTION
        "This object represents whether use long or short preamble for 802.11
         MAC frame.
        When ibDot11CfgRadioType is either dot11b, dot11g or dot11gn,
        then value for ibDot11PreambleLenCM will be valid.
        Otherwise, the value for it will be invalid."
    DEFVAL      { short }
    ::= { ibDot11RadioConfigEntry 14 }

ibDot11RCDynamicChlStateCM OBJECT-TYPE
    SYNTAX      INTEGER
        {
            off(0),
            on(1)
        }
    MAX-ACCESS  read-write
    STATUS      current
    DESCRIPTION
        "Enable/Disable dynamic channel selection."
    ::= { ibDot11RadioConfigEntry 15 }

ibDot11RCRadioStatusCM OBJECT-TYPE
    SYNTAX      INTEGER
        {
            up(1),
            down(2),
            testing(3)
        }
    MAX-ACCESS  read-write
    STATUS      current
    DESCRIPTION
        "Represents the radio admin status whether is enabled
        or disabled."
    ::= { ibDot11RadioConfigEntry 16 }

ibDot11RCRadioRateCM OBJECT-TYPE
    SYNTAX      OCTET STRING(SIZE(0..255))
    MAX-ACCESS  read-write
    STATUS      current
    DESCRIPTION
        "Set data transmit rates for the radio, in the format of 1,2,5.5...
        For 802.11n radios, the format of each value can be MCS X.  The data transmit
        rates between AP and client should be one of the configured rates.
        (Note: For 802.11n radios, the first value is mandatory rate, and the second
        value is supported rate.  If more than two rate values are configured, the
        configuration will not take effect.  If only one rate value is configured,
        the mandatory rate will be set to the default value.)"
    ::= { ibDot11RadioConfigEntry 17 }

ibDot11RCDynamicPowerStateCM OBJECT-TYPE
    SYNTAX      IbDot11TruthValueCM
    MAX-ACCESS  read-write
    STATUS      current
    DESCRIPTION
        "Enable/disable dynamic power selection for the band."
    ::= { ibDot11RadioConfigEntry 18 }

ibDot11RCRssiThresholdCM OBJECT-TYPE
    SYNTAX      Integer32
    UNITS       "dBm"
    MAX-ACCESS  read-write
    STATUS      current
    DESCRIPTION
        "Represents the minimum value of the RSSI.
        The clients with RSSI below this value will be refused to associate."
    DEFVAL { 1 }
    ::= { ibDot11RadioConfigEntry 19 }

ibDot11RCDynamicChlStateSelfDecisiveCM OBJECT-TYPE
    SYNTAX      IbDot11TruthValueCM
    MAX-ACCESS  read-write
    STATUS      current
    DESCRIPTION
        "Enable/disable dynamic channel selection self decisive for the band."
    ::= { ibDot11RadioConfigEntry 20 }

ibDot11RCDynamicPowerStateSelfDecisiveCM OBJECT-TYPE
    SYNTAX      IbDot11TruthValueCM
    MAX-ACCESS  read-write
    STATUS      current
    DESCRIPTION
        "Enable/disable dynamic power selection self decisive for the band."
    ::= { ibDot11RadioConfigEntry 21 }

-- *****************************************************************************
-- * End of ibDot11RadioConfigTable Definition
-- *****************************************************************************

ibDot11RadioSSIDCfgTable OBJECT-TYPE
    SYNTAX      SEQUENCE OF IbDot11RadioSSIDCfgEntry
    MAX-ACCESS  not-accessible
    STATUS      current
    DESCRIPTION
        "For each radio, it could configure multiple service policies.
        The table describes the relationship between radio and
        service policies."
    ::= { ibDot11APConfigGroup 9 }

ibDot11RadioSSIDCfgEntry OBJECT-TYPE
    SYNTAX      IbDot11RadioSSIDCfgEntry
    MAX-ACCESS  not-accessible
    STATUS      current
    DESCRIPTION
        "Each entry contains SSID configuration information for each radio."
    INDEX
        {
            ibDot11RadioSSIDSerialID,
            ibDot11RadioSSIDRadioID,
            ibDot11RadioSSIDWLANID
        }
    ::= { ibDot11RadioSSIDCfgTable 1 }

IbDot11RadioSSIDCfgEntry ::= SEQUENCE
    {
        ibDot11RadioSSIDSerialID    IbDot11ObjectIDType,
        ibDot11RadioSSIDRadioID     IbDot11RadioScopeType,
        ibDot11RadioSSIDWLANID      Integer32,
        ibDot11RadioSSIDIndex       IbDot11ServicePolicyIDType,
        ibDot11RadioBSSID           MacAddress,
        ibDot11RadioSSIDRowStatus   RowStatus
    }

ibDot11RadioSSIDSerialID OBJECT-TYPE
    SYNTAX      IbDot11ObjectIDType
    MAX-ACCESS  not-accessible
    STATUS      current
    DESCRIPTION
        "This object represents the serial ID of AP."
    ::= { ibDot11RadioSSIDCfgEntry 1 }

ibDot11RadioSSIDRadioID OBJECT-TYPE
    SYNTAX      IbDot11RadioScopeType
    MAX-ACCESS  not-accessible
    STATUS      current
    DESCRIPTION
        "This object represents each radio."
    ::= { ibDot11RadioSSIDCfgEntry 2 }

ibDot11RadioSSIDWLANID OBJECT-TYPE
    SYNTAX      Integer32
    MAX-ACCESS  not-accessible
    STATUS      current
    DESCRIPTION
        "This object represents the WLAN ID of the BSSID."
    ::= { ibDot11RadioSSIDCfgEntry 3 }

ibDot11RadioSSIDIndex OBJECT-TYPE
    SYNTAX      IbDot11ServicePolicyIDType
    MAX-ACCESS  read-create
    STATUS      current
    DESCRIPTION
        "This object represents the ID of each service policy used by the
         radio."
    ::= { ibDot11RadioSSIDCfgEntry 4 }

ibDot11RadioBSSID OBJECT-TYPE
    SYNTAX      MacAddress
    MAX-ACCESS  read-only
    STATUS      current
    DESCRIPTION
        "As MAC address format, it is used to identify BSS."
    ::= { ibDot11RadioSSIDCfgEntry 5 }

ibDot11RadioSSIDRowStatus OBJECT-TYPE
    SYNTAX      RowStatus
    MAX-ACCESS  read-create
    STATUS      current
    DESCRIPTION
        "RowStatus."
    ::= { ibDot11RadioSSIDCfgEntry 6 }

-- *****************************************************************************
-- *  ibDot11APSerialIDTable Definition
-- *****************************************************************************

ibDot11APSerialIDTable OBJECT-TYPE
    SYNTAX      SEQUENCE OF IbDot11APSerialIDEntry
    MAX-ACCESS  not-accessible
    STATUS      current
    DESCRIPTION
        "The table will provide the general information about APs."
    ::= { ibDot11APConfigGroup 10 }

ibDot11APSerialIDEntry OBJECT-TYPE
    SYNTAX      IbDot11APSerialIDEntry
    MAX-ACCESS  not-accessible
    STATUS      current
    DESCRIPTION
        "Each entry contains the general information of an AP."
    INDEX
        {
            ibDot11SIDAPSerialID
        }
    ::= { ibDot11APSerialIDTable 1 }

IbDot11APSerialIDEntry ::= SEQUENCE
    {
        ibDot11SIDAPSerialID               OCTET STRING,
        ibDot11SIDAPWorkMode               INTEGER,
        ibDot11SIDAPGetIPMethod            INTEGER,
        ibDot11SIDAPTemplateName           OCTET STRING,
        ibDot11SIDModelAlias               OCTET STRING,
        ibDot11SIDAPDescription            OCTET STRING,
        ibDot11SIDRowStatus                RowStatus,
        ibDot11SIDAPName                   OCTET STRING,
        ibDot11SIDStatisInterv             Integer32,
        ibDot11SIDAPBroadcastProbeReply    TruthValue,
        ibDot11SIDAPStaIdleTimerInterv     Integer32,
        ibDot11SIDStaKeepAliveTimerInterv  Integer32,
        ibDot11SIDAPCir                    Integer32,
        ibDot11SIDAPCbs                    Integer32,
        ibDot11SIDAPPriorityLevel          Integer32,
        ibDot11SIDAPElementID              Integer32,
        ibDot11SIDAPDevDetectEnable        TruthValue,
        ibDot11SIDAPStatisIntervMode       INTEGER,
        ibDot11SIDAPWorkModeCM             INTEGER,
        ibDot11SIDEchoInterval             Integer32
    }

ibDot11SIDAPSerialID OBJECT-TYPE
    SYNTAX      OCTET STRING
    MAX-ACCESS  not-accessible
    STATUS      current
    DESCRIPTION
        "Represents AP serial id."
    ::= { ibDot11APSerialIDEntry 1 }

ibDot11SIDAPWorkMode OBJECT-TYPE
    SYNTAX      INTEGER
        {
            normal(1),
            monitor(2),
            hybrid(3)
        }
    MAX-ACCESS  read-create
    STATUS      current
    DESCRIPTION
        "Represents what work mode for AP.
        The following values are supported:
        normal   - AP will supply WLAN service.
        monitor  - AP will be a monitor to find attack.
        hybrid   - AP will supply WLAN service and Device detection is
        enabled."
    DEFVAL      { normal }
    ::= { ibDot11APSerialIDEntry 2 }

ibDot11SIDAPGetIPMethod OBJECT-TYPE
    SYNTAX      INTEGER
    {
        dhcpAlloc(1),
        static(2)
    }
    MAX-ACCESS  read-create
    STATUS      current
    DESCRIPTION
        "This object represents the method how AP gets IP address."
    DEFVAL      { dhcpAlloc }
    ::= { ibDot11APSerialIDEntry 3 }
ibDot11SIDAPTemplateName OBJECT-TYPE
    SYNTAX      OCTET STRING
    MAX-ACCESS  read-create
    STATUS      current
    DESCRIPTION
        "Represents the name of AP template."
    ::= { ibDot11APSerialIDEntry 4 }
ibDot11SIDModelAlias OBJECT-TYPE
    SYNTAX      OCTET STRING
    MAX-ACCESS  read-create
    STATUS      current
    DESCRIPTION
        "Represents the alias of AP model name."
    ::= { ibDot11APSerialIDEntry 5 }

ibDot11SIDAPDescription OBJECT-TYPE
    SYNTAX      OCTET STRING
    MAX-ACCESS  read-create
    STATUS      current
    DESCRIPTION
        "This attribute will give more information about AP.
        Administrator could suggest the location, owner or
        other information for each AP.
        If the value is set to NULL, the description will be removed."
    ::= { ibDot11APSerialIDEntry 6 }

ibDot11SIDRowStatus OBJECT-TYPE
    SYNTAX      RowStatus
    MAX-ACCESS  read-create
    STATUS      current
    DESCRIPTION
        "The status of this table entry."
    ::= { ibDot11APSerialIDEntry 7 }

ibDot11SIDAPName OBJECT-TYPE
    SYNTAX      OCTET STRING
    MAX-ACCESS  read-create
    STATUS      current
    DESCRIPTION
        "Represents the AP name."
    ::= { ibDot11APSerialIDEntry 8 }

ibDot11SIDStatisInterv OBJECT-TYPE
    SYNTAX      Integer32
    UNITS       "second"
    MAX-ACCESS  read-create
    STATUS      current
    DESCRIPTION
        "Represents the interval of radio statistic."
    ::= { ibDot11APSerialIDEntry 9 }

ibDot11SIDAPBroadcastProbeReply OBJECT-TYPE
    SYNTAX      TruthValue
    MAX-ACCESS  read-create
    STATUS      current
    DESCRIPTION
        "Represents enable the AP to reply broadcast probe or not.
        'true' : The AP to reply broadcast probe is enabled.
        'false': The AP to reply broadcast probe is disabled"
    DEFVAL      { true }
    ::= { ibDot11APSerialIDEntry 10 }

ibDot11SIDAPStaIdleTimerInterv OBJECT-TYPE
    SYNTAX      Integer32
    UNITS       "second"
    MAX-ACCESS  read-create
    STATUS      current
    DESCRIPTION
        "Represents the interval for which the link between AP and STA
        ( power-save or awake ) can be idle."
    ::= { ibDot11APSerialIDEntry 11 }

ibDot11SIDStaKeepAliveTimerInterv OBJECT-TYPE
    SYNTAX      Integer32
    UNITS       "second"
    MAX-ACCESS  read-create
    STATUS      current
    DESCRIPTION
        "Represents the interval of the keep alive requests sent between
        AP and STA."
    ::= { ibDot11APSerialIDEntry 12 }

ibDot11SIDAPCir OBJECT-TYPE
    SYNTAX      Integer32
    UNITS       "Kbps"
    MAX-ACCESS  read-create
    STATUS      current
    DESCRIPTION
        "Represents the committed information rate between AP and AC."
    ::= { ibDot11APSerialIDEntry 13 }

ibDot11SIDAPCbs OBJECT-TYPE
    SYNTAX      Integer32
    UNITS       "Bytes"
    MAX-ACCESS  read-create
    STATUS      current
    DESCRIPTION
        "Represents the committed burst size between AP and AC."
    ::= { ibDot11APSerialIDEntry 14 }

ibDot11SIDAPPriorityLevel OBJECT-TYPE
    SYNTAX      Integer32 (0..7)
    MAX-ACCESS  read-create
    STATUS      current
    DESCRIPTION
        "This object represents the connection priority for the AP.
        If the connection priority is 7, the AC is considered as the
        primary AC for the AP."
    DEFVAL      { 4 }
    ::= { ibDot11APSerialIDEntry 15 }

ibDot11SIDAPElementID OBJECT-TYPE
    SYNTAX      Integer32
    MAX-ACCESS  read-only
    STATUS      current
    DESCRIPTION
        "This object represents the AP element ID."
    ::= { ibDot11APSerialIDEntry 16 }

ibDot11SIDAPDevDetectEnable OBJECT-TYPE
    SYNTAX      TruthValue
    MAX-ACCESS  read-create
    STATUS      current
    DESCRIPTION
        "Represents whether device detection is enabled or not.
         'true' : Device detection is enabled.
         'false': Device detection is disabled.
         If device detection is enabled, the AP will provide both device
         detection and WLAN data services.
         By default, the AP only provides WLAN data services.  When an AP works
         in monitor mode, that is, the value of object ibDot11APWorkMode is
         monitor, device detection can not be enabled with object
         ibDot11SIDAPDevDetectEnable."
    DEFVAL      { false }
    ::= { ibDot11APSerialIDEntry 17 }

ibDot11SIDAPStatisIntervMode OBJECT-TYPE
    SYNTAX      INTEGER
    {
        normal(1),
        realtime(2)
    }
    MAX-ACCESS  read-create
    STATUS      current
    DESCRIPTION
        "This object represents the mode of statics interval.
         normal    - statics interval value between 10s to 240s
         realtime  - statics interval value between 0s to 5s"
    DEFVAL      { normal }
    ::= { ibDot11APSerialIDEntry 18 }

ibDot11SIDAPWorkModeCM OBJECT-TYPE
    SYNTAX      INTEGER
        {
            normal(0),
            monitor(1),
            semimonitor(2)
        }
    MAX-ACCESS  read-create
    STATUS      current
    DESCRIPTION
        "Represents what work mode for AP.
        The following values are supported:
        normal   - AP will supply WLAN service.
        monitor  - AP will be a monitor to find attack.
        SemiMonitor   - AP will supply WLAN service and Device detection is
        enabled."
    DEFVAL      { normal }
    ::= { ibDot11APSerialIDEntry 19 }

ibDot11SIDEchoInterval OBJECT-TYPE
    SYNTAX      Integer32
    UNITS       "second"
    MAX-ACCESS  read-write
    STATUS      current
    DESCRIPTION
        "Represents the interval for send echo requests."
    ::= { ibDot11APSerialIDEntry 20 }

-- *****************************************************************************
-- *  ibDot11RadioIntfConfigTable Definition
-- *****************************************************************************
ibDot11RadioIntfConfigTable OBJECT-TYPE
    SYNTAX      SEQUENCE OF IbDot11RadioIntfConfigEntry
    MAX-ACCESS  not-accessible
    STATUS      current
    DESCRIPTION
        "The table defines the parameters for radio in AP, as per
        radio."
    ::= { ibDot11RadioIntfConfigGroup 1 }

ibDot11RadioIntfConfigEntry OBJECT-TYPE
    SYNTAX      IbDot11RadioIntfConfigEntry
    MAX-ACCESS  not-accessible
    STATUS      current
    DESCRIPTION
        "Each entry contains information of each radio in AP."
    INDEX
        {
            ibDot11RadioIfIdx
        }
    ::= { ibDot11RadioIntfConfigTable 1 }

IbDot11RadioIntfConfigEntry ::= SEQUENCE
    {
        ibDot11RadioIfIdx               Integer32,
        ibDot11RadioCfgBeaconIntvl      Integer32,
        ibDot11RadioCfgDtimIntvl        Integer32,
        ibDot11RadioCfgRtsThreshold     Integer32,
        ibDot11RadioCfgFragThreshold    Integer32,
        ibDot11RadioCfgShtRetryThld     Integer32,
        ibDot11RadioCfglongRtrThld      Integer32,
        ibDot11RadioCfgMaxRxLifetime    Unsigned32,
        ibDot11RadioCfgType             IbDot11RadioType,
        ibDot11RadioCfgChannel          IbDot11ChannelScopeType,
        ibDot11RadioCfgMaxTxPwrLvl      IbDot11TxPwrLevelScopeType,
        ibDot11RadioCfgPreambleLen      IbDot11PreambleType,
        ibDot11RadioCfgWorkMode         IbDot11WorkMode,
        ibDot11RadioCfgOnly11gEnable    TruthValue,
        ibDot11RadioCfgType2            IbDot11RadioType2,
        ibDot11RadioCfgRssithresholdCM  Integer32
    }

ibDot11RadioIfIdx OBJECT-TYPE
    SYNTAX      Integer32
    MAX-ACCESS  not-accessible
    STATUS      current
    DESCRIPTION
        "Represents the Radio IfIndex of radio in AP."
    ::= { ibDot11RadioIntfConfigEntry 1 }

ibDot11RadioCfgBeaconIntvl OBJECT-TYPE
    SYNTAX      Integer32
    UNITS       "TU"
    MAX-ACCESS  read-write
    STATUS      current
    DESCRIPTION
        "Represents the interval for Beacon management frame."
    DEFVAL { 100 }
    ::= { ibDot11RadioIntfConfigEntry 2 }

ibDot11RadioCfgDtimIntvl OBJECT-TYPE
    SYNTAX      Integer32
    MAX-ACCESS  read-write
    STATUS      current
    DESCRIPTION
        "Represents the number of beacon intervals that shall elapse
        between transmission of Beacons frames containing a Traffic
        Indication Map (TIM) element whose DTIM Count field is 0.
        This value is transmitted in the Delivery TIM (DTIM) Period
        field of Beacon frames."
    DEFVAL { 1 }
    ::= { ibDot11RadioIntfConfigEntry 3 }

ibDot11RadioCfgRtsThreshold OBJECT-TYPE
    SYNTAX      Integer32
    UNITS       "Byte"
    MAX-ACCESS  read-write
    STATUS      current
    DESCRIPTION
        "Represents the current minimum size,in octets,of the MAC
        protocol data unit (MPDU), below which a Request to send/Clear
        to send (RTS/CTS) handshake shall not be performed."
    DEFVAL { 2346 }
    ::= { ibDot11RadioIntfConfigEntry 4 }

ibDot11RadioCfgFragThreshold OBJECT-TYPE
    SYNTAX      Integer32
    UNITS       "Byte"
    MAX-ACCESS  read-write
    STATUS      current
    DESCRIPTION
        "Represents the current maximum size, in octets, of the MPDU that
        may be delivered to the PHY.  A MSDU shall be broken into
        fragments if its size exceeds the value of this attribute after
        adding MAC headers and trailers."
    DEFVAL { 2346 }
    ::= { ibDot11RadioIntfConfigEntry 5 }

ibDot11RadioCfgShtRetryThld OBJECT-TYPE
    SYNTAX      Integer32
    MAX-ACCESS  read-write
    STATUS      current
    DESCRIPTION
        "Represents the maximum number of transmission attempts of a
        frame, the length of which is less than or equal to
        ibDot11RadioRTSThreshold, that shall be made before a failure
        condition is indicated."
    DEFVAL { 5 }
    ::= { ibDot11RadioIntfConfigEntry 6 }

ibDot11RadioCfglongRtrThld OBJECT-TYPE
    SYNTAX      Integer32
    MAX-ACCESS  read-write
    STATUS      current
    DESCRIPTION
        "Represents the maximum number of transmission attempts of a
        frame, the length of which is longer than
        ibDot11RadioRTSThreshold, that shall be made before a
        failure condition is indicated."
    DEFVAL { 5 }
    ::= { ibDot11RadioIntfConfigEntry 7 }

ibDot11RadioCfgMaxRxLifetime OBJECT-TYPE
    SYNTAX      Unsigned32
    UNITS       "millisecond"
    MAX-ACCESS  read-write
    STATUS      current
    DESCRIPTION
        "Represents the elapsed time.  After the time specified by
        ibDot11RadioCfgMaxRxLifetime, the further attempts to reassemble
        the MSDU shall be terminated."
    DEFVAL { 2000 }
    ::= { ibDot11RadioIntfConfigEntry 8 }

ibDot11RadioCfgType OBJECT-TYPE
    SYNTAX      IbDot11RadioType
    MAX-ACCESS  read-write
    STATUS      current
    DESCRIPTION
        "Represents the radio will work with which 802.11 radio type."
    ::= { ibDot11RadioIntfConfigEntry 9 }

ibDot11RadioCfgChannel OBJECT-TYPE
    SYNTAX      IbDot11ChannelScopeType
    MAX-ACCESS  read-write
    STATUS      current
    DESCRIPTION
        "Represents the channel allocation of radio."
    DEFVAL { 1 }
    ::= { ibDot11RadioIntfConfigEntry 10 }

ibDot11RadioCfgMaxTxPwrLvl OBJECT-TYPE
    SYNTAX      IbDot11TxPwrLevelScopeType
    UNITS       "dbm"
    MAX-ACCESS  read-write
    STATUS      current
    DESCRIPTION
        "Represents the maximal transmit power scope for AP."
    ::= { ibDot11RadioIntfConfigEntry 11 }

ibDot11RadioCfgPreambleLen OBJECT-TYPE
    SYNTAX      IbDot11PreambleType
    MAX-ACCESS  read-write
    STATUS      current
    DESCRIPTION
        "Represents whether use long or short preamble for 802.11 MAC
        frame."
    DEFVAL { short }
    ::= { ibDot11RadioIntfConfigEntry 12 }

ibDot11RadioCfgWorkMode OBJECT-TYPE
    SYNTAX      IbDot11WorkMode
    MAX-ACCESS  read-write
    STATUS      current
    DESCRIPTION
        "Represents work mode of the radio."
    ::= { ibDot11RadioIntfConfigEntry 13 }

ibDot11RadioCfgOnly11gEnable OBJECT-TYPE
    SYNTAX      TruthValue
    MAX-ACCESS  read-write
    STATUS      current
    DESCRIPTION
        "Represents whether enable only 802.11g radio mode or not.
        'true' : Only 802.11g radio mode is enabled.
        'false': Only 802.11g radio mode is disabled."
    DEFVAL { false }
    ::= { ibDot11RadioIntfConfigEntry 14 }

ibDot11RadioCfgType2 OBJECT-TYPE
    SYNTAX      IbDot11RadioType2
    MAX-ACCESS  read-write
    STATUS      current
    DESCRIPTION
        "Represents the radio will work with which 802.11 radio type."
    ::= { ibDot11RadioIntfConfigEntry 15 }

ibDot11RadioCfgRssithresholdCM OBJECT-TYPE
    SYNTAX      Integer32
    UNITS       "dBm"
    MAX-ACCESS  read-write
    STATUS      current
    DESCRIPTION
        "Represents the minimum value of the RSSI.
        The clients with RSSI below this value will be refused to associate."
    DEFVAL { 1 }
    ::= { ibDot11RadioIntfConfigEntry 16 }

-- *****************************************************************************
-- *  End of ibDot11RadioIntfConfigTable Definition
-- *****************************************************************************

-- *****************************************************************************
-- *  ibDot11RadioIntfBindTable Definition
-- *****************************************************************************
ibDot11RadioIntfBindTable OBJECT-TYPE
    SYNTAX      SEQUENCE OF IbDot11RadioIntfBindEntry
    MAX-ACCESS  not-accessible
    STATUS      current
    DESCRIPTION
        "The table defines the binding information for each radio in AP.
        "
    ::= { ibDot11RadioIntfConfigGroup 2 }

ibDot11RadioIntfBindEntry OBJECT-TYPE
    SYNTAX      IbDot11RadioIntfBindEntry
    MAX-ACCESS  not-accessible
    STATUS      current
    DESCRIPTION
        "Each entry contains the radio interface binding information
        in AP."
    INDEX
        {
            ibDot11RadioIfIdx,
            ibDot11RadioIntfBindSvcPlcyID
        }
    ::= { ibDot11RadioIntfBindTable 1 }

IbDot11RadioIntfBindEntry ::= SEQUENCE
    {
        ibDot11RadioIntfBindSvcPlcyID    IbDot11ServicePolicyIDType,
        ibDot11RadioIntfBindIfIdx        Unsigned32,
        ibDot11RadioIntfBindRowStatus    RowStatus
    }

ibDot11RadioIntfBindSvcPlcyID OBJECT-TYPE
    SYNTAX      IbDot11ServicePolicyIDType
    MAX-ACCESS  not-accessible
    STATUS      current
    DESCRIPTION
        "Represents the ID of each service policy."
    ::= { ibDot11RadioIntfBindEntry 1 }

ibDot11RadioIntfBindIfIdx OBJECT-TYPE
    SYNTAX      Unsigned32
    MAX-ACCESS  read-create
    STATUS      current
    DESCRIPTION
        "Represents the Ifindex of interface which is binded to
        the radio."
    ::= { ibDot11RadioIntfBindEntry 2 }

ibDot11RadioIntfBindRowStatus OBJECT-TYPE
    SYNTAX      RowStatus
    MAX-ACCESS  read-create
    STATUS      current
    DESCRIPTION
        "The status of this table entry."
    ::= { ibDot11RadioIntfBindEntry 3 }
-- *****************************************************************************
-- *  End of ibDot11RadioIntfBindTable Definition
-- *****************************************************************************

-- *****************************************************************************
-- *  ibDot11DataRateConfigTable Definition
-- *****************************************************************************
ibDot11DataRateConfigTable OBJECT-TYPE
    SYNTAX      SEQUENCE OF IbDot11DataRateConfigEntry
    MAX-ACCESS  not-accessible
    STATUS      current
    DESCRIPTION
        "Table will provide data rate configuration for a specific radio type."
    ::= { ibDot11DataRateConfigGroup 1 }

ibDot11DataRateConfigEntry OBJECT-TYPE
    SYNTAX      IbDot11DataRateConfigEntry
    MAX-ACCESS  not-accessible
    STATUS      current
    DESCRIPTION
        "Each entry of the table will provide data rate configuration for a
        specific radio type."
    INDEX
        {
            ibDot11RadioTypeID
        }
    ::= { ibDot11DataRateConfigTable 1 }

IbDot11DataRateConfigEntry ::= SEQUENCE
    {
        ibDot11RadioTypeID         IbDot11RadioType,
        ibDot11SupportedRateSet    OCTET STRING,
        ibDot11MandatoryRateSet    OCTET STRING,
        ibDot11DisabledRateSet     OCTET STRING,
        ibDot11SmartRateSet        OCTET STRING
    }

ibDot11RadioTypeID OBJECT-TYPE
    SYNTAX      IbDot11RadioType
    MAX-ACCESS  not-accessible
    STATUS      current
    DESCRIPTION
        "Represents the radio type."
    ::= { ibDot11DataRateConfigEntry 1 }

ibDot11SupportedRateSet OBJECT-TYPE
    SYNTAX      OCTET STRING(SIZE(0..255))
    MAX-ACCESS  read-write
    STATUS      current
    DESCRIPTION
        "Represents the supported rate set of a particular radio type."
    ::= { ibDot11DataRateConfigEntry 2 }

ibDot11MandatoryRateSet OBJECT-TYPE
    SYNTAX      OCTET STRING(SIZE(0..255))
    MAX-ACCESS  read-write
    STATUS      current
    DESCRIPTION
        "Represents the mandatory rate set of a particular radio type."
    ::= { ibDot11DataRateConfigEntry 3 }

ibDot11DisabledRateSet OBJECT-TYPE
    SYNTAX      OCTET STRING(SIZE(0..255))
    MAX-ACCESS  read-write
    STATUS      current
    DESCRIPTION
        "Represents the disabled rate set of a particular radio type."
    ::= { ibDot11DataRateConfigEntry 4 }

ibDot11SmartRateSet OBJECT-TYPE
    SYNTAX      OCTET STRING(SIZE(0..255))
    MAX-ACCESS  read-write
    STATUS      current
    DESCRIPTION
        "Represents the rate set of a particular radio type."
    ::= { ibDot11DataRateConfigEntry 5 }
-- *****************************************************************************
-- *  End of ibDot11DataRateConfigTable Definition
-- *****************************************************************************

-- *****************************************************************************
-- *  ibDot11WlanEssIfTable Definition
-- *************************************************************************

ibDot11WlanEssIfTable OBJECT-TYPE
    SYNTAX      SEQUENCE OF IbDot11WlanEssIfEntry
    MAX-ACCESS  not-accessible
    STATUS      current
    DESCRIPTION
        "This table is used to configure WLAN ESS interface."
    ::= { ibDot11InterfaceConfigGroup 1 }

ibDot11WlanEssIfEntry OBJECT-TYPE
    SYNTAX      IbDot11WlanEssIfEntry
    MAX-ACCESS  not-accessible
    STATUS      current
    DESCRIPTION
        "Each entry contains the WLAN ESS interface configuration."
    INDEX
        {
            ibDot11WlanEssIfNumber
        }
    ::= { ibDot11WlanEssIfTable 1 }

IbDot11WlanEssIfEntry ::= SEQUENCE
    {
        ibDot11WlanEssIfNumber      Integer32,
        ibDot11WlanEssIfIndex       Integer32,
        ibDot11WlanEssRowStatus     RowStatus
    }

ibDot11WlanEssIfNumber OBJECT-TYPE
    SYNTAX      Integer32
    MAX-ACCESS  not-accessible
    STATUS      current
    DESCRIPTION
        "This node represents the WLAN ESS interface number."
    ::= { ibDot11WlanEssIfEntry 1 }

ibDot11WlanEssIfIndex OBJECT-TYPE
    SYNTAX      Integer32
    MAX-ACCESS  read-only
    STATUS      current
    DESCRIPTION
        "This node represents the ifIndex of WLAN-ESS interface."
    ::= { ibDot11WlanEssIfEntry 2 }

ibDot11WlanEssRowStatus OBJECT-TYPE
    SYNTAX      RowStatus
    MAX-ACCESS  read-create
    STATUS      current
    DESCRIPTION
        "This node represents the WLAN ESS interface row status."
    ::= { ibDot11WlanEssIfEntry 3 }

-- *****************************************************************************
-- *  End of ibDot11WlanEssIfTable  Definition
-- *****************************************************************************
-- *****************************************************************************
-- *  ibDot11WlanBssIfTable Definition
-- *************************************************************************

ibDot11WlanBssIfTable OBJECT-TYPE
    SYNTAX      SEQUENCE OF IbDot11WlanBssIfEntry
    MAX-ACCESS  not-accessible
    STATUS      current
    DESCRIPTION
        "This table is used to configure WLAN BSS interface."
    ::= { ibDot11InterfaceConfigGroup 2 }

ibDot11WlanBssIfEntry OBJECT-TYPE
    SYNTAX      IbDot11WlanBssIfEntry
    MAX-ACCESS  not-accessible
    STATUS      current
    DESCRIPTION
        "Each entry contains the WLAN BSS interface configuration."
    INDEX
        {
            ibDot11WlanBssIfNumber
        }
    ::= { ibDot11WlanBssIfTable 1 }

IbDot11WlanBssIfEntry ::= SEQUENCE
    {
        ibDot11WlanBssIfNumber     Integer32,
        ibDot11WlanBssIfIndex      Integer32,
        ibDot11WlanBssRowStatus    RowStatus
    }

ibDot11WlanBssIfNumber OBJECT-TYPE
    SYNTAX      Integer32
    MAX-ACCESS  not-accessible
    STATUS      current
    DESCRIPTION
        "This node represents the WLAN BSS interface number."
    ::= { ibDot11WlanBssIfEntry 1 }

ibDot11WlanBssIfIndex OBJECT-TYPE
    SYNTAX      Integer32
    MAX-ACCESS  read-only
    STATUS      current
    DESCRIPTION
        "This node represents the ifIndex of WLAN-BSS interface."
    ::= { ibDot11WlanBssIfEntry 2 }

ibDot11WlanBssRowStatus OBJECT-TYPE
    SYNTAX      RowStatus
    MAX-ACCESS  read-create
    STATUS      current
    DESCRIPTION
        "This node represents the WLAN BSS interface row status."
    ::= { ibDot11WlanBssIfEntry 3 }

-- *****************************************************************************
-- *  End of ibDot11WlanBssIfTable Definition
-- *****************************************************************************
-- *****************************************************************************
-- *  ibDot11WLANEthernetIfTable Definition
-- *************************************************************************

ibDot11WLANEthernetIfTable OBJECT-TYPE
    SYNTAX      SEQUENCE OF IbDot11WLANEthernetIfEntry
    MAX-ACCESS  not-accessible
    STATUS      current
    DESCRIPTION
        "This table is used to configure WLAN Ethernet interface."
    ::= { ibDot11InterfaceConfigGroup 3 }

ibDot11WLANEthernetIfEntry OBJECT-TYPE
    SYNTAX      IbDot11WLANEthernetIfEntry
    MAX-ACCESS  not-accessible
    STATUS      current
    DESCRIPTION
        "Each entry contains the WLAN Ethernet interface configuration."
    INDEX
        {
            ibDot11WlanEthernetIfNumber
        }
    ::= { ibDot11WLANEthernetIfTable 1 }

IbDot11WLANEthernetIfEntry ::= SEQUENCE
    {
        ibDot11WlanEthernetIfNumber     Integer32,
        ibDot11WLANEthernetIfIndex      Integer32,
        ibDot11WlanEthernetRowStatus    RowStatus
    }

ibDot11WlanEthernetIfNumber OBJECT-TYPE
    SYNTAX      Integer32
    MAX-ACCESS  not-accessible
    STATUS      current
    DESCRIPTION
        "This node represents the WLAN Ethernet interface number."
    ::= { ibDot11WLANEthernetIfEntry 1 }

ibDot11WLANEthernetIfIndex OBJECT-TYPE
    SYNTAX      Integer32
    MAX-ACCESS  read-only
    STATUS      current
    DESCRIPTION
        "This node represents the ifIndex of WLAN-Ethernet interface."
    ::= { ibDot11WLANEthernetIfEntry 2 }

ibDot11WlanEthernetRowStatus OBJECT-TYPE
    SYNTAX      RowStatus
    MAX-ACCESS  read-create
    STATUS      current
    DESCRIPTION
        "This node represents the Wlan Ethernet interface row status."
    ::= { ibDot11WLANEthernetIfEntry 3 }

-- *****************************************************************************
-- *  End of ibDot11DataRateConfigTable Definition
-- *****************************************************************************
-- *****************************************************************************
-- *  ibDot11PortSecurityTable Definition
-- *****************************************************************************
ibDot11PortSecurityTable OBJECT-TYPE
    SYNTAX      SEQUENCE OF IbDot11PortSecurityEntry
    MAX-ACCESS  not-accessible
    STATUS      current
    DESCRIPTION
        "This table defines the WLAN security status for ESS, BSS, mesh and
        WLAN-Ethernet interface which binding the crypto service-template.
        Otherwise, when binding the clear service-template,
        ibPortSecurityTables should be used to configure port security."
    ::= { ibDot11InterfaceConfigGroup 4 }

ibDot11PortSecurityEntry OBJECT-TYPE
    SYNTAX      IbDot11PortSecurityEntry
    MAX-ACCESS  not-accessible
    STATUS      current
    DESCRIPTION
        "There is a row in this table for each ESS, BSS and WLAN-Ethernet
        interface.It is indexed using the object ifIndex in RFC1213-MIB."
    INDEX
        {
            ifIndex
        }
    ::= { ibDot11PortSecurityTable 1 }

IbDot11PortSecurityEntry ::= SEQUENCE
    {
        ibDot11PortSecurityMode                 INTEGER,
        ibDot11SecurityUserLoginTxKeyType       INTEGER,
        ibDot11SecurityPskKeyMode               INTEGER,
        ibDot11SecurityPskKeyString             DisplayString
    }

ibDot11PortSecurityMode OBJECT-TYPE
    SYNTAX      INTEGER
        {
            noRestrictions(1),
            userLoginSecureExt(2),
            psk(3),
            macAddressAndPsk(4),
            userLoginSecureExtOrPsk(5),
            ext(6)
        }
    MAX-ACCESS  read-write
    STATUS      current
    DESCRIPTION
        "Determines the security modes of the WLAN port.

        noRestrictions  - The default value,no any security mode is set.

        userLoginSecureExt  - Access to the port is denied until the port
        client is authorized (by 802.1X).

        psk  - Access to the port is denied until the port client is
        authorized (by 802.1X key negotiation).

        macAddressAndPsk  - The MAC address is first authenticated and only if
        this succeeds does the psk then attempt user authentication.

        userLoginSecureExtOrPsk  - This selects both the userLoginSecureExt and
        psk modes together such that either is allowed to authorized access.
        Which mode works for client depends on the client's choice.

        ext  - Access to the port is denied until the port client is
        authenticated (by ext).
        "
    ::= { ibDot11PortSecurityEntry 1 }

ibDot11SecurityUserLoginTxKeyType OBJECT-TYPE
    SYNTAX      INTEGER
        {
            userLoginTxKeyTypeNone(1),
            userLoginTxKeyTypeDot11Key(2),
            userLoginTxKeyTypeRsaRC4Key(3)
        }
    MAX-ACCESS  read-write
    STATUS      current
    DESCRIPTION
        "This indicates the key type in the 802.1X EAPOL_Key packet.

        userLoginTxKeyTypeNone  - This means the key type is not set yet.

        userLoginTxKeyTypeDot11Key  - This selects the 802.11 key type.

        userLoginTxKeyTypeRsaRC4Key  - This selects the RC4 key for RSA RC4
        session encryption."
    ::= { ibDot11PortSecurityEntry 2 }

ibDot11SecurityPskKeyMode OBJECT-TYPE
    SYNTAX      INTEGER
        {
            pskKeyModeNone(1),
            pskKeyModePassPhrase(2),
            pskKeyModeRawKey(3)
        }
    MAX-ACCESS  read-write
    STATUS      current
    DESCRIPTION
        "This is the password input mode.  When input as pskKeyModePassPhrase,
        ibDot11SecurePskKeyString must be 8 to 63 characters; when input as
        pskKeyModeRawKey, ibDot11SecurePskKeyString must be 64 characters and
        each character must be '0'-'9', 'a'-'f' and 'A'-'F'."
    ::= { ibDot11PortSecurityEntry 3 }

ibDot11SecurityPskKeyString OBJECT-TYPE
    SYNTAX      DisplayString
    MAX-ACCESS  read-write
    STATUS      current
    DESCRIPTION
        "This is the password string used for psk authentication."
    ::= { ibDot11PortSecurityEntry 4 }

-- *****************************************************************************
-- *  End of ibDot11PortSecurityTable Definition
-- *****************************************************************************
-- *****************************************************************************
-- *  ibDot11WlanMeshIfTable Definition
-- *************************************************************************

ibDot11WlanMeshIfTable OBJECT-TYPE
    SYNTAX      SEQUENCE OF IbDot11WlanMeshIfEntry
    MAX-ACCESS  not-accessible
    STATUS      current
    DESCRIPTION
        "This table is used to configure WLAN mesh interface."
    ::= { ibDot11InterfaceConfigGroup 5 }

ibDot11WlanMeshIfEntry OBJECT-TYPE
    SYNTAX      IbDot11WlanMeshIfEntry
    MAX-ACCESS  not-accessible
    STATUS      current
    DESCRIPTION
        "Each entry contains the WLAN mesh interface configuration."
    INDEX
        {
            ibDot11WlanMeshIfNumber
        }
    ::= { ibDot11WlanMeshIfTable 1 }

IbDot11WlanMeshIfEntry ::= SEQUENCE
    {
        ibDot11WlanMeshIfNumber    Integer32,
        ibDot11WlanMeshIfIndex     Integer32,
        ibDot11WlanMeshRowStatus   RowStatus
    }

ibDot11WlanMeshIfNumber OBJECT-TYPE
    SYNTAX      Integer32
    MAX-ACCESS  not-accessible
    STATUS      current
    DESCRIPTION
        "This node represents the WLAN mesh interface number."
    ::= { ibDot11WlanMeshIfEntry 1 }

ibDot11WlanMeshIfIndex OBJECT-TYPE
    SYNTAX      Integer32
    MAX-ACCESS  read-only
    STATUS      current
    DESCRIPTION
        "This node represents the index of WLAN mesh interface."
    ::= { ibDot11WlanMeshIfEntry 2 }

ibDot11WlanMeshRowStatus OBJECT-TYPE
    SYNTAX      RowStatus
    MAX-ACCESS  read-create
    STATUS      current
    DESCRIPTION
        "This node represents the WLAN mesh interface row status."
    ::= { ibDot11WlanMeshIfEntry 3 }

-- *****************************************************************************
-- *  End of ibDot11WlanMeshIfTable Definition
-- *****************************************************************************

-- *****************************************************************************
-- *  ibDot11ACBackupGroup Definition
-- *****************************************************************************
ibDot11BackupACAdrssIP OBJECT-TYPE
    SYNTAX      InetAddress
    MAX-ACCESS  read-write
    STATUS      current
    DESCRIPTION
        "This object represents the backup AC IP address.
        If the backup AC IP address is not configured,
        the object value is 0.0.0.0."
    ::= { ibDot11ACBackupGroup 1 }

ibDot11BackupACAdrssIPv6 OBJECT-TYPE
    SYNTAX      InetAddress
    MAX-ACCESS  read-write
    STATUS      current
    DESCRIPTION
        "This object represents the backup AC IPv6 address.
         If the backup AC IPv6 address is not configured,
         the object value is 0::0."
    ::= { ibDot11ACBackupGroup 2 }

-- *****************************************************************************
-- *  End of ibDot11ACBackupGroup Definition
-- *****************************************************************************

-- *****************************************************************************
-- *  ibDot11RadioElementConfigGroup Definition
-- *****************************************************************************

ibDot11nRadioCfgTable OBJECT-TYPE
    SYNTAX SEQUENCE OF IbDot11nRadioCfgEntry
    MAX-ACCESS not-accessible
    STATUS current
    DESCRIPTION
        "This table is used to configure dot11n on the radio."
    ::= { ibDot11RadioElementConfigGroup 1 }

ibDot11nRadioCfgEntry OBJECT-TYPE
    SYNTAX IbDot11nRadioCfgEntry
    MAX-ACCESS not-accessible
    STATUS current
    DESCRIPTION
        "This entry contains the dot11n configuration on the radio."
    INDEX { ibDot11nRadioCfgIndex }
    ::= { ibDot11nRadioCfgTable 1 }

IbDot11nRadioCfgEntry ::= SEQUENCE
    {
        ibDot11nRadioCfgIndex       IbDot11RadioElementIndex,
        ibDot11nAMpduEnable         TruthValue,
        ibDot11nAMsduEnable         TruthValue,
        ibDot11nClientDot11nOnly    TruthValue,
        ibDot11nChanelBand          INTEGER,
        ibDot11nShortGiEnable       TruthValue,
        ibDot11nClientDot11acOnly   TruthValue,
        ibDot11nSupportMaxMcs       Integer32,
        ibDot11nMandatoryMaxMcs     Integer32
    }

ibDot11nRadioCfgIndex OBJECT-TYPE
    SYNTAX IbDot11RadioElementIndex
    MAX-ACCESS not-accessible
    STATUS current
    DESCRIPTION
        "Represents index of the radio."
    ::= { ibDot11nRadioCfgEntry 1 }

ibDot11nAMpduEnable OBJECT-TYPE
    SYNTAX TruthValue
    MAX-ACCESS read-write
    STATUS current
    DESCRIPTION
        "Enable the function of A-MPDU."
        DEFVAL { true }
    ::= { ibDot11nRadioCfgEntry 2 }

ibDot11nAMsduEnable OBJECT-TYPE
    SYNTAX TruthValue
    MAX-ACCESS read-write
    STATUS current
    DESCRIPTION
        "Enable the function of A-MSDU."
    DEFVAL { true }
    ::= { ibDot11nRadioCfgEntry 3 }

ibDot11nClientDot11nOnly OBJECT-TYPE
    SYNTAX TruthValue
    MAX-ACCESS read-write
    STATUS current
    DESCRIPTION
        "If radio type is 802.11an or 802.11gn, only permit clients of 11n mode.
         If radio type is 802.11ac, permit clients of 11n and 11ac mode."
    DEFVAL { false }
    ::= { ibDot11nRadioCfgEntry 4 }

ibDot11nChanelBand OBJECT-TYPE
    SYNTAX INTEGER
        {
        mode20(1),
        mode40(2),
        mode80(3),
        mode160(4),
        mode80and80(5),
        mode320(9)
        }
    MAX-ACCESS read-write
    STATUS current
    DESCRIPTION
        "Specify the bandwidth mode."
    DEFVAL { mode40 }
    ::= { ibDot11nRadioCfgEntry 5 }

ibDot11nShortGiEnable OBJECT-TYPE
    SYNTAX TruthValue
    MAX-ACCESS read-write
    STATUS current
    DESCRIPTION
        "The function of Short GI."
    DEFVAL { true }
    ::= { ibDot11nRadioCfgEntry 6 }

ibDot11nClientDot11acOnly OBJECT-TYPE
    SYNTAX TruthValue
    MAX-ACCESS read-write
    STATUS current
    DESCRIPTION
        "Only permit clients of 11ac mode."
    DEFVAL { false }
    ::= { ibDot11nRadioCfgEntry 7 }

ibDot11nSupportMaxMcs OBJECT-TYPE
    SYNTAX Integer32 (0..76)
    MAX-ACCESS read-write
    STATUS current
    DESCRIPTION
        "Specify the maximum Modulation and Coding Scheme (MCS) index for
        802.11n supported rates.
        The specified maximum MCS index for 802.11n supported rates must be no
        less than the specified maximum MCS index for 802.11n mandatory rates."
    DEFVAL { 76 }
    ::= { ibDot11nRadioCfgEntry 8 }

ibDot11nMandatoryMaxMcs OBJECT-TYPE
    SYNTAX Integer32 (0..76 | 255)
    MAX-ACCESS read-write
    STATUS current
    DESCRIPTION
        "Specify the maximum modulation and coding scheme (MCS) index for
        802.11n mandatory rates.
        The value 255 indicates that no maximum MCS index
        is specified.  No maximum MCS index is specified for 802.11n
        mandatory rates by default.
        Besides 255, the specified maximum MCS index for 802.11n supported
        rates must be no less than the specified maximum MCS index for 802.11n
        mandatory rates."
    DEFVAL { 255 }
    ::= { ibDot11nRadioCfgEntry 9 }

-- *****************************************************************************
-- *  End of ibDot11RadioElementConfigGroup Definition
-- *****************************************************************************

-- *****************************************************************************
-- *  ibDot11RadioWDSTable Definition
-- *****************************************************************************

ibDot11RadioWDSTable OBJECT-TYPE
    SYNTAX      SEQUENCE OF IbDot11RadioWDSEntry
    MAX-ACCESS  not-accessible
    STATUS      current
    DESCRIPTION
        "This table is used to configure WDS on the radio."
    ::= { ibDot11RadioElementConfigGroup 2 }

ibDot11RadioWDSEntry OBJECT-TYPE
    SYNTAX      IbDot11RadioWDSEntry
    MAX-ACCESS  not-accessible
    STATUS      current
    DESCRIPTION
        "Each entry contains the WDS configuration on the radio."
    INDEX
        {
            ibDot11RadioWDSIndex
        }
    ::= { ibDot11RadioWDSTable 1 }

IbDot11RadioWDSEntry ::= SEQUENCE
    {
        ibDot11RadioWDSIndex            IbDot11RadioElementIndex,
        ibDot11RadioWDSMode             INTEGER,
        ibDot11RadioWDSNetWorkID        OCTET STRING,
        ibDot11WDSSecPskKeyMode         INTEGER,
        ibDot11WDSSecPskKeyString       DisplayString
    }

ibDot11RadioWDSIndex OBJECT-TYPE
    SYNTAX      IbDot11RadioElementIndex
    MAX-ACCESS  not-accessible
    STATUS      current
    DESCRIPTION
        "Represents the element index of radio."
    ::= { ibDot11RadioWDSEntry 1 }

ibDot11RadioWDSMode OBJECT-TYPE
    SYNTAX      INTEGER
        {
            nowds(1),
            wds(2)
        }
    MAX-ACCESS  read-write
    STATUS      current
    DESCRIPTION
        "Represents enable the WDS mode or not.
        nowds: The WDS mode is disabled.
        wds  : The WDS mode is enabled"
    DEFVAL      { nowds }
    ::= { ibDot11RadioWDSEntry 2 }

ibDot11RadioWDSNetWorkID OBJECT-TYPE
    SYNTAX      OCTET STRING(SIZE(0..32))
    MAX-ACCESS  read-write
    STATUS      current
    DESCRIPTION
        "Represents the mesh ID of WDS."
    DEFVAL      { "" }
    ::= { ibDot11RadioWDSEntry 3 }

ibDot11WDSSecPskKeyMode OBJECT-TYPE
    SYNTAX      INTEGER
        {
          pskKeyModeNone(1),
          pskKeyModePassPhrase(2),
          pskKeyModeRawKey(3)
        }
    MAX-ACCESS  read-write
    STATUS      current
    DESCRIPTION
        "Represents the PSK mode of WDS."
    DEFVAL      { pskKeyModeNone }
    ::= { ibDot11RadioWDSEntry 4 }

ibDot11WDSSecPskKeyString OBJECT-TYPE
    SYNTAX      DisplayString
    MAX-ACCESS  read-write
    STATUS      current
    DESCRIPTION
        "Represents the PSK value of WDS."
    DEFVAL      { "" }
    ::= { ibDot11RadioWDSEntry 5 }

-- *****************************************************************************
-- *  End of ibDot11RadioWDSTable  Definition
-- *****************************************************************************

-- *****************************************************************************
-- *  ibDot11nRadioCfg2Table Definition
-- *****************************************************************************

ibDot11nRadioCfg2Table OBJECT-TYPE
    SYNTAX SEQUENCE OF IbDot11nRadioCfg2Entry
    MAX-ACCESS not-accessible
    STATUS current
    DESCRIPTION
        "This table is used to configure dot11n on the radio."
    ::= { ibDot11RadioElementConfigGroup 3 }

ibDot11nRadioCfg2Entry OBJECT-TYPE
    SYNTAX IbDot11nRadioCfg2Entry
    MAX-ACCESS not-accessible
    STATUS current
    DESCRIPTION
        "This entry contains the dot11n configuration on the radio."
    INDEX {
              ibDot11nRadioCfg2APIDIndex,
              ibDot11nRadioCfg2RadioIDIndex
          }
    ::= { ibDot11nRadioCfg2Table 1 }

IbDot11nRadioCfg2Entry ::= SEQUENCE
    {
        ibDot11nRadioCfg2APIDIndex           IbDot11ObjectIDType,
        ibDot11nRadioCfg2RadioIDIndex        IbDot11RadioScopeType,
        ibDot11nRadioCfg2AMpduEnable         TruthValue,
        ibDot11nRadioCfg2AMsduEnable         TruthValue,
        ibDot11nRadioCfg2ClientDot11nOnly    TruthValue,
        ibDot11nRadioCfg2ChannelBand          INTEGER,
        ibDot11nRadioCfg2ShortGiEnable       TruthValue,
        ibDot11nRadioCfg2AMpduEnableCM        INTEGER,
        ibDot11nRadioCfg2ChannelBandCM        INTEGER,
        ibDot11nRadioCfg2ShortGiEnableCM      INTEGER,
        ibDot11nRadioCfg2ClientDot11acOnly   TruthValue,
        ibDot11nRadioCfg2ClientDot11nOnlyCM   IbDot11TruthValueCM,
        ibDot11nRadioCfg2SupportMaxMcs       Integer32,
        ibDot11nRadioCfg2MandatoryMaxMcs     Integer32
    }

ibDot11nRadioCfg2APIDIndex OBJECT-TYPE
    SYNTAX IbDot11ObjectIDType
    MAX-ACCESS not-accessible
    STATUS current
    DESCRIPTION
        "Represents index of the AP."
    ::= { ibDot11nRadioCfg2Entry 1 }

ibDot11nRadioCfg2RadioIDIndex OBJECT-TYPE
    SYNTAX IbDot11RadioScopeType
    MAX-ACCESS not-accessible
    STATUS current
    DESCRIPTION
        "Represents index of the radio."
    ::= { ibDot11nRadioCfg2Entry 2 }

ibDot11nRadioCfg2AMpduEnable OBJECT-TYPE
    SYNTAX TruthValue
    MAX-ACCESS read-write
    STATUS current
    DESCRIPTION
        "Enable the function of A-MPDU."
        DEFVAL { true }
    ::= { ibDot11nRadioCfg2Entry 3 }

ibDot11nRadioCfg2AMsduEnable OBJECT-TYPE
    SYNTAX TruthValue
    MAX-ACCESS read-write
    STATUS current
    DESCRIPTION
        "Enable the function of A-MSDU."
    DEFVAL { true }
    ::= { ibDot11nRadioCfg2Entry 4 }

ibDot11nRadioCfg2ClientDot11nOnly OBJECT-TYPE
    SYNTAX TruthValue
    MAX-ACCESS read-write
    STATUS current
    DESCRIPTION
        "If radio type is 802.11an or 802.11gn, only permit clients of 11n mode.
         If radio type is 802.11ac, permit clients of 11n and 11ac mode."
    DEFVAL { false }
    ::= { ibDot11nRadioCfg2Entry 5 }

ibDot11nRadioCfg2ChannelBand OBJECT-TYPE
    SYNTAX INTEGER
        {
            mode20(1),
            mode40(2),
            mode80(3),
            mode160(4),
            mode80and80(5),
            mode320(9)
        }
    MAX-ACCESS read-write
    STATUS current
    DESCRIPTION
        "Specify the bandwidth mode."
    ::= { ibDot11nRadioCfg2Entry 6 }

ibDot11nRadioCfg2ShortGiEnable OBJECT-TYPE
    SYNTAX TruthValue
    MAX-ACCESS read-write
    STATUS current
    DESCRIPTION
        "Enable the function of Short GI."
    DEFVAL { true }
    ::= { ibDot11nRadioCfg2Entry 7 }

ibDot11nRadioCfg2AMpduEnableCM OBJECT-TYPE
    SYNTAX   INTEGER
        {
            off(0),
            on(1)
        }
    MAX-ACCESS read-write
    STATUS current
    DESCRIPTION
        "Enable the function of A-MPDU."
        DEFVAL { on }
    ::= { ibDot11nRadioCfg2Entry 8 }

ibDot11nRadioCfg2ChannelBandCM OBJECT-TYPE
    SYNTAX      INTEGER
        {
            mode40(1),
            mode20(2),
            mode80(3),
            mode160(4),
            mode80and80(5),
            mode320(9)
        }
    MAX-ACCESS read-write
    STATUS current
    DESCRIPTION
        "Specify the bandwidth mode."
    ::= { ibDot11nRadioCfg2Entry 9 }

ibDot11nRadioCfg2ShortGiEnableCM OBJECT-TYPE
    SYNTAX    INTEGER
        {
            off(0),
            on(1)
        }
    MAX-ACCESS read-write
    STATUS current
    DESCRIPTION
        "Enable the function of Short GI."
    DEFVAL { on }
    ::= { ibDot11nRadioCfg2Entry 10 }

ibDot11nRadioCfg2ClientDot11acOnly OBJECT-TYPE
    SYNTAX TruthValue
    MAX-ACCESS read-write
    STATUS current
    DESCRIPTION
        "Only permit clients of 11ac mode."
    DEFVAL { false }
    ::= { ibDot11nRadioCfg2Entry 11 }

ibDot11nRadioCfg2ClientDot11nOnlyCM OBJECT-TYPE
    SYNTAX IbDot11TruthValueCM
    MAX-ACCESS read-write
    STATUS current
    DESCRIPTION
        "If radio type is 802.11an or 802.11gn, permit only clients of 11n mode.
        If radio type is 802.11ac, permit clients of both 11n and 11ac mode."
    DEFVAL { dot11false }
    ::= { ibDot11nRadioCfg2Entry 12 }

ibDot11nRadioCfg2SupportMaxMcs OBJECT-TYPE
    SYNTAX Integer32 (0..76)
    MAX-ACCESS read-write
    STATUS current
    DESCRIPTION
        "Specify the maximum Modulation and Coding Scheme (MCS) index for
        802.11n supported rates.
        The specified maximum MCS index for 802.11n supported rates must be no
        less than the specified maximum MCS index for 802.11n mandatory rates."
    DEFVAL { 76 }
    ::= { ibDot11nRadioCfg2Entry 13 }

ibDot11nRadioCfg2MandatoryMaxMcs OBJECT-TYPE
    SYNTAX Integer32 (0..76 | 255)
    MAX-ACCESS read-write
    STATUS current
    DESCRIPTION
        "Specify the maximum modulation and coding scheme (MCS) index for
        802.11n mandatory rates.
        The value 255 indicates that no maximum MCS index
        is specified.  No maximum MCS index is specified for 802.11n
        mandatory rates by default.
        Besides 255, the specified maximum MCS index for 802.11n supported
        rates must be no less than the specified maximum MCS index for 802.11n
        mandatory rates."
    DEFVAL { 255 }
    ::= { ibDot11nRadioCfg2Entry 14 }

-- *****************************************************************************
-- *  End of ibDot11nRadioCfg2Table Definition
-- *****************************************************************************

-- *****************************************************************************
-- *  ibDot11CfgNotifyGroup Definition
-- *****************************************************************************
ibDot11CfgNotifications OBJECT IDENTIFIER ::= { ibDot11CfgNotifyGroup 0 }

ibDot11CfgCipherChange NOTIFICATION-TYPE
    OBJECTS
    {
        ibDot11SSIDName,
        ibDot11SecurityCiphers
    }
    STATUS      current
    DESCRIPTION
        "This notification is sent when cipher type of corresponding service
        template is changed."
    ::= { ibDot11CfgNotifications 1 }

ibDot11CfgPSKChange NOTIFICATION-TYPE
    OBJECTS
    {
        ibDot11SSIDName
    }
    STATUS      current
    DESCRIPTION
        "This notification is sent when pre-shared key of corresponding
        service template is changed."
    ::= { ibDot11CfgNotifications 2 }

ibDot11SSIDWepIDConflictTrap NOTIFICATION-TYPE
    OBJECTS
    {
        ibDot11PreConflictTemplateNum,
        ibDot11CurrConflictTemplateNum,
        ibDot11ConflictCipherIdx,
        ibDot11ConfigureAPID,
        ibDot11ConfigureRadioID,
        ibDot11ConfigureAPMacAddress,
        ibDot11PreConflictTemplateSSID,
        ibDot11CurrConflictTemplateSSID
    }
    STATUS      current
    DESCRIPTION
        "This notification will be sent when the same wep ID is configured
         on two service policies."
    ::= { ibDot11CfgNotifications 3 }

-- CFG Notification variable object

ibDot11CfgTrapVarObjects OBJECT IDENTIFIER
    ::= { ibDot11CfgNotifyGroup 1 }

ibDot11PreConflictTemplateNum OBJECT-TYPE
    SYNTAX      Integer32 (1..1024)
    MAX-ACCESS  accessible-for-notify
    STATUS      current
    DESCRIPTION
        "Represents previous service policy ID when radio bind service policy
         and current service policy conflict with previous service policy
         in cipher configuration."
    ::= { ibDot11CfgTrapVarObjects 1 }

ibDot11CurrConflictTemplateNum OBJECT-TYPE
    SYNTAX      Integer32 (1..1024)
    MAX-ACCESS  accessible-for-notify
    STATUS      current
    DESCRIPTION
        "Represents current service policy ID when radio bind service policy
         and current service policy conflict with previous service policy
         in cipher configuration."
    ::= { ibDot11CfgTrapVarObjects 2 }

ibDot11ConflictCipherIdx OBJECT-TYPE
    SYNTAX      Integer32 (1..4)
    MAX-ACCESS  accessible-for-notify
    STATUS      current
    DESCRIPTION
        "Represents wep ID that conflicted with."
    ::= { ibDot11CfgTrapVarObjects 3 }

ibDot11ConfigureAPID OBJECT-TYPE
    SYNTAX      IbDot11ObjectIDType
    MAX-ACCESS  accessible-for-notify
    STATUS      current
    DESCRIPTION
        "Represents which AP is configured."
    ::= { ibDot11CfgTrapVarObjects 4 }

ibDot11ConfigureRadioID OBJECT-TYPE
    SYNTAX      IbDot11RadioScopeType
    MAX-ACCESS  accessible-for-notify
    STATUS      current
    DESCRIPTION
        "Represents which radio in AP is configured."
    ::= { ibDot11CfgTrapVarObjects 5 }

ibDot11ConfigureAPMacAddress OBJECT-TYPE
    SYNTAX      MacAddress
    MAX-ACCESS  accessible-for-notify
    STATUS      current
    DESCRIPTION
        "Represents MAC Address of AP."
    ::= { ibDot11CfgTrapVarObjects 6 }

ibDot11PreConflictTemplateSSID OBJECT-TYPE
    SYNTAX      IbDot11SSIDStringType
    MAX-ACCESS  accessible-for-notify
    STATUS      current
    DESCRIPTION
        "Represents the previous SSID of the AP."
    ::= { ibDot11CfgTrapVarObjects 7 }

ibDot11CurrConflictTemplateSSID OBJECT-TYPE
    SYNTAX      IbDot11SSIDStringType
    MAX-ACCESS  accessible-for-notify
    STATUS      current
    DESCRIPTION
        "Represents the current SSID of the AP."
    ::= { ibDot11CfgTrapVarObjects 8 }

-- *****************************************************************************
-- *  End of ibDot11CfgNotifyGroup Definition
-- *****************************************************************************

-- *****************************************************************************
-- *  ibDot11LocalACTemplateTable Definition
-- *****************************************************************************
ibDot11LocalACTemplateTable OBJECT-TYPE
    SYNTAX      SEQUENCE OF IbDot11LocalACTemplateEntry
    MAX-ACCESS  not-accessible
    STATUS      current
    DESCRIPTION
        "By local AC template CLI, administrator will configure the parameters of LocalAC
        by convenience.
        Before local AC boot up and connect to AC by CAPWAP tunnel, administrator
        will create local AC template for each local AC. When local AC connect to AC,
        AC will assign configuration to local AC by ibDot11LocalACSerialID
        information in local AC template."
    ::= { ibDot11LocalACConfigGroup 1 }

ibDot11LocalACTemplateEntry OBJECT-TYPE
    SYNTAX      IbDot11LocalACTemplateEntry
    MAX-ACCESS  not-accessible
    STATUS      current
    DESCRIPTION
        "Each entry contains configuration information for each LocalAC."
    INDEX
        {
            ibDot11LocalACTemplateName
        }
    ::= { ibDot11LocalACTemplateTable 1 }

IbDot11LocalACTemplateEntry ::= SEQUENCE
    {
        ibDot11LocalACTemplateName             OCTET STRING,
        ibDot11LocalACName                     OCTET STRING,
        ibDot11LocalACSerialID                 OCTET STRING,
        ibDot11TemLocalACModelAlias            OCTET STRING,
        ibDot11LocalACTempRowStatus            RowStatus,
        ibDot11LocalACStatus                   INTEGER,
        ibDot11LocalACIPAddress                IpAddress,
        ibDot11LocalACIPv6Address              OCTET STRING,
        ibDot11EchoInterval                    Integer32,
        ibDot11RetransInterval                 Integer32,
        ibDot11RetransCount                    Integer32,
        ibDot11FirmwareUpgrade                 INTEGER
    }

ibDot11LocalACTemplateName OBJECT-TYPE
    SYNTAX      OCTET STRING(SIZE(0..127))
    MAX-ACCESS  not-accessible
    STATUS      current
    DESCRIPTION
        "Represents the name of LocalAC template."
    ::= { ibDot11LocalACTemplateEntry 1 }

ibDot11LocalACName OBJECT-TYPE
    SYNTAX      OCTET STRING
    MAX-ACCESS  read-create
    STATUS      current
    DESCRIPTION
        "Represents the LocalAC name."
    ::= { ibDot11LocalACTemplateEntry 2 }

ibDot11LocalACSerialID OBJECT-TYPE
    SYNTAX      OCTET STRING
    MAX-ACCESS  read-create
    STATUS      current
    DESCRIPTION
        "Represents LocalAC serial id."
    ::= { ibDot11LocalACTemplateEntry 3 }

ibDot11TemLocalACModelAlias OBJECT-TYPE
    SYNTAX      OCTET STRING
    MAX-ACCESS  read-create
    STATUS      current
    DESCRIPTION
        "Represents the alias of LocalAC model name."
    ::= { ibDot11LocalACTemplateEntry 4 }

ibDot11LocalACTempRowStatus OBJECT-TYPE
    SYNTAX      RowStatus
    MAX-ACCESS  read-create
    STATUS      current
    DESCRIPTION
        "The status of this table entry."
    ::= { ibDot11LocalACTemplateEntry 5 }

ibDot11LocalACStatus OBJECT-TYPE
    SYNTAX      INTEGER
        {
            join(1),
            joinConfirm(2),
            download(3),
            config(4),
            run(5),
            idle(6)
        }
    MAX-ACCESS  read-only
    STATUS      current
    DESCRIPTION
        "Represents the capwap status of local AC.
        The following values are supported:
        join         - local AC is joining to cnetral AC.
        joinConfirm  - cnetral AC confirm whether permit local AC to
        - join.
        download     - local AC is downloading software from cnetral
        - AC.
        config       - local AC and cnetral AC exchange configuration
        - before local AC provide WLAN service.
        run          - The local AC is run.
        idle         - The local AC is idle."
    ::= { ibDot11LocalACTemplateEntry 6 }

ibDot11LocalACIPAddress OBJECT-TYPE
    SYNTAX      IpAddress
    MAX-ACCESS  read-only
    STATUS      current
    DESCRIPTION
        "Represents the IP address of an LocalAC."
    ::= { ibDot11LocalACTemplateEntry 7 }

ibDot11LocalACIPv6Address OBJECT-TYPE
    SYNTAX      OCTET STRING
    MAX-ACCESS  read-only
    STATUS      current
    DESCRIPTION
        "Represents the IPv6 address of LocalAC."
    ::= { ibDot11LocalACTemplateEntry 8 }

ibDot11EchoInterval OBJECT-TYPE
    SYNTAX      Integer32(0 | 5..255)
    UNITS       "second"
    MAX-ACCESS  read-create
    STATUS      current
    DESCRIPTION
        "Represents the interval of echo."
    DEFVAL      { 10 }
    ::= { ibDot11LocalACTemplateEntry 9 }

ibDot11RetransInterval OBJECT-TYPE
    SYNTAX      Integer32(3..8)
    UNITS       "second"
    MAX-ACCESS  read-create
    STATUS      current
    DESCRIPTION
        "Represents the interval of retransmit."
    DEFVAL      { 5 }
    ::= { ibDot11LocalACTemplateEntry 10 }

ibDot11RetransCount OBJECT-TYPE
    SYNTAX      Integer32(2..5)
    UNITS       "second"
    MAX-ACCESS  read-create
    STATUS      current
    DESCRIPTION
        "Represents the maximum of retransmit."
    DEFVAL      { 3 }
    ::= { ibDot11LocalACTemplateEntry 11 }

ibDot11FirmwareUpgrade OBJECT-TYPE
    SYNTAX      INTEGER
        {
            enable(1),
            disable(2)
        }
    MAX-ACCESS  read-create
    STATUS      current
    DESCRIPTION
        "Represents the status of firmware upgrade for an local AC.
        The following values are supported:
        enable      - local AC firmware upgrade will be enabled.
        disable     - local AC firmware upgrade will be disabled."
        DEFVAL      { enable }
    ::= { ibDot11LocalACTemplateEntry 12 }

-- *****************************************************************************
-- *  End of  ibDot11LocalACTemplateTable Definition
-- *****************************************************************************

-- *****************************************************************************
-- *  ibDot11RemoteCfgApTable Definition
-- *****************************************************************************
ibDot11RemoteCfgApTable OBJECT-TYPE
    SYNTAX      SEQUENCE OF IbDot11RemoteCfgApEntry
    MAX-ACCESS  not-accessible
    STATUS      current
    DESCRIPTION
        "Remote configuration for an AP."
    ::= { ibDot11RemoteConfigGroup  1 }

ibDot11RemoteCfgApEntry OBJECT-TYPE
    SYNTAX      IbDot11RemoteCfgApEntry
    MAX-ACCESS  not-accessible
    STATUS      current
    DESCRIPTION
        "Each entry contains configuration information for each AP."
    INDEX
        {
            ibDot11RmtApName
        }
    ::= { ibDot11RemoteCfgApTable 1 }

IbDot11RemoteCfgApEntry ::= SEQUENCE
    {
        ibDot11RmtApName                 OCTET STRING,
        ibDot11RmtVlanList               OCTET STRING,
        ibDot11RmtCfgEnable              TruthValue
    }

ibDot11RmtApName OBJECT-TYPE
    SYNTAX      OCTET STRING(SIZE(1..127))
    MAX-ACCESS  not-accessible
    STATUS      current
    DESCRIPTION
        "Represents the name of an AP."
    ::= { ibDot11RemoteCfgApEntry 1 }

ibDot11RmtVlanList OBJECT-TYPE
    SYNTAX      OCTET STRING
    MAX-ACCESS  read-write
    STATUS      current
    DESCRIPTION
        "Represents the VLAN list on an AP."
    ::= { ibDot11RemoteCfgApEntry 2 }

ibDot11RmtCfgEnable OBJECT-TYPE
    SYNTAX TruthValue
    MAX-ACCESS read-write
    STATUS current
    DESCRIPTION
        "Enables remote configuration synchronization."
    DEFVAL { false }
    ::= { ibDot11RemoteCfgApEntry 3 }
-- *****************************************************************************
-- *  End of  ibDot11RemoteCfgApTable Definition
-- *****************************************************************************

-- *****************************************************************************
-- *  ibDot11RemoteCfgIFTable Definition
-- *****************************************************************************
ibDot11RemoteCfgIFTable OBJECT-TYPE
    SYNTAX      SEQUENCE OF IbDot11RemoteCfgIFEntry
    MAX-ACCESS  not-accessible
    STATUS      current
    DESCRIPTION
        "Remote configuration for interface on an AP."
    ::= { ibDot11RemoteConfigGroup  2 }

ibDot11RemoteCfgIFEntry OBJECT-TYPE
    SYNTAX      IbDot11RemoteCfgIFEntry
    MAX-ACCESS  not-accessible
    STATUS      current
    DESCRIPTION
        "Each entry contains configuration information for each interface on an AP."
    INDEX
        {
            ibDot11RmtIfApName,
            ibDot11RmtIfType,
            ibDot11RmtIfNum
        }
    ::= { ibDot11RemoteCfgIFTable 1 }

IbDot11RemoteCfgIFEntry ::= SEQUENCE
    {
        ibDot11RmtIfApName                OCTET STRING,
        ibDot11RmtIfType                  Integer32,
        ibDot11RmtIfNum                   Integer32,
        ibDot11RmtIfName                  OCTET STRING,
        ibDot11RmtIfLinkType              INTEGER,
        ibDot11RmtIfAccessVlan            Integer32,
        ibDot11RmtIfTrunkPvidVlan         Integer32,
        ibDot11RmtIfTrunkVlanlist         OCTET STRING,
        ibDot11RmtIfHybridPvidVlan        Integer32,
        ibDot11RmtIfHybVlanListTag        OCTET STRING,
        ibDot11RmtIfHybVlanListUnTag      OCTET STRING,
        ibDot11RmtIfIsolate               TruthValue,
        ibDot11RmtIfLinkAggGroupId        Integer32,
        ibDot11RmtIfManagement            TruthValue
    }

ibDot11RmtIfApName OBJECT-TYPE
    SYNTAX      OCTET STRING(SIZE(1..127))
    MAX-ACCESS  not-accessible
    STATUS      current
    DESCRIPTION
        "Represents the name of an AP."
    ::= { ibDot11RemoteCfgIFEntry 1 }

ibDot11RmtIfType OBJECT-TYPE
    SYNTAX      Integer32
    MAX-ACCESS  not-accessible
    STATUS      current
    DESCRIPTION
        "Represents the type of the interface.
         ethernet (1),
         gigabitethernet (2),
         ten-gigabitethernet (3),
         smartrate-ethernet(4)."
    ::= { ibDot11RemoteCfgIFEntry 2 }

ibDot11RmtIfNum OBJECT-TYPE
    SYNTAX      Integer32
    MAX-ACCESS  not-accessible
    STATUS      current
    DESCRIPTION
        "Represents the ID of the interface."
    ::= { ibDot11RemoteCfgIFEntry 3 }

ibDot11RmtIfName OBJECT-TYPE
    SYNTAX      OCTET STRING
    MAX-ACCESS  read-only
    STATUS      current
    DESCRIPTION
        "Represents the name of the interface."
    ::= { ibDot11RemoteCfgIFEntry 4 }

ibDot11RmtIfLinkType OBJECT-TYPE
    SYNTAX      INTEGER
        {
            access (1),
            trunk (2),
            hybrid (3)
        }
    MAX-ACCESS  read-write
    STATUS      current
    DESCRIPTION
        "Set the link type to access, hybrid or trunk.
         Setting recommend one and setup more related nodes."
    ::= { ibDot11RemoteCfgIFEntry 5 }

ibDot11RmtIfAccessVlan OBJECT-TYPE
    SYNTAX      Integer32
    MAX-ACCESS  read-write
    STATUS      current
    DESCRIPTION
        "Specify the access VLAN for a port."
    ::= { ibDot11RemoteCfgIFEntry 6 }

ibDot11RmtIfTrunkPvidVlan OBJECT-TYPE
    SYNTAX      Integer32
    MAX-ACCESS  read-write
    STATUS      current
    DESCRIPTION
        "Specify the default VLAN for a port."
    ::= { ibDot11RemoteCfgIFEntry 7 }

ibDot11RmtIfTrunkVlanlist OBJECT-TYPE
    SYNTAX      OCTET STRING
    MAX-ACCESS  read-write
    STATUS      current
    DESCRIPTION
        "Specify the permitted VLAN list for a port."
    ::= { ibDot11RemoteCfgIFEntry 8 }

ibDot11RmtIfHybridPvidVlan OBJECT-TYPE
    SYNTAX      Integer32
    MAX-ACCESS  read-write
    STATUS      current
    DESCRIPTION
        "Specify the default VLAN for the hybrid port."
    ::= { ibDot11RemoteCfgIFEntry 9 }

ibDot11RmtIfHybVlanListTag OBJECT-TYPE
    SYNTAX      OCTET STRING
    MAX-ACCESS  read-write
    STATUS      current
    DESCRIPTION
        "Assign the hybrid port to tagged VLANs."
    ::= { ibDot11RemoteCfgIFEntry 10 }

ibDot11RmtIfHybVlanListUnTag OBJECT-TYPE
    SYNTAX      OCTET STRING
    MAX-ACCESS  read-write
    STATUS      current
    DESCRIPTION
        "Assign the hybrid port to untagged VLANs."
    ::= { ibDot11RemoteCfgIFEntry 11 }

ibDot11RmtIfIsolate OBJECT-TYPE
    SYNTAX TruthValue
    MAX-ACCESS read-write
    STATUS current
    DESCRIPTION
        "Enable or disable port isolation."
    DEFVAL { true }
    ::= { ibDot11RemoteCfgIFEntry 12 }

ibDot11RmtIfLinkAggGroupId OBJECT-TYPE
    SYNTAX      Integer32
    MAX-ACCESS  read-write
    STATUS      current
    DESCRIPTION
        "Specify link aggregation group number for the port."
    ::= { ibDot11RemoteCfgIFEntry 13 }

ibDot11RmtIfManagement OBJECT-TYPE
    SYNTAX      TruthValue
    MAX-ACCESS  read-write
    STATUS      current
    DESCRIPTION
        "Interface management of the port."
    DEFVAL { true }
    ::= { ibDot11RemoteCfgIFEntry 14 }
-- *****************************************************************************
-- *  End of  ibDot11RemoteCfgIFTable Definition
-- *****************************************************************************

END
