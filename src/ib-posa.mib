-- =================================================================
-- Copyright (C) 2023 Intelbras S.A. All rights reserved.
--
-- Description: This MIB is to provide the definition of the POSA
--              (Point Of Sale Access) system.
-- Reference:
-- Version: V1.9
-- History:
-- V1.0 2008-03-12 Initial version, created by Lei Hao, Yang Xu
-- V1.1 2008-09-22 updated by yangxu
--      Modified the limitation(SIZE (4..7)) of ibPosaMapDestCode
--      Modified the default value of ibPosaFcmAnswerTimeout
--      Modified the limitation(0..65535) of ibPosaAppHostPort
--      Modified the limitation(0..65535) of ibPosaTerminalListenPort
--      Added new node ibPosaTerminalTransAppID in ibPosaTerminalTable
--      Renamed ibPosaAppDiscardedPkts to ibPosaAppInDiscardedPkts
--      Added new node ibPosaAppOutDiscardedPkts in ibPosaAppStatTable
--      Renamed ibPosaTerminalDiscardedPkts to ibPosaTerminalInDiscardedPkts
--      Added new node ibPosaTerminalOutDiscardedPkts in ibPosaTerminalStatTable
--      Modified the description of object ibPosaAppHostPort,
--      ibPosaFcmStatTimeoutCnts, ibPosaFcmStatConnectFailCnts,
--      ibPosaAppRecvPkts, ibPosaAppSendPkts, ibPosaAppErrPkts,
--      ibPosaAppDistributeErrCnts, ibPosaAppInDiscardedPkts,
--      ibPosaTerminalRecvPkts, ibPosaTerminalSendPkts,
--      ibPosaTerminalErrPkts, ibPosaTerminalMapErrCnts,
--      ibPosaTerminalInDiscardedPkts.
-- V1.2 2010-04-08 updated by Cai Zibin, Tong Wei
--      Added ibPosaFcmConfTable
--      Added ibPosaTcpTermStatTable
--      Added ibPosaBatchTerminalTable
--      Added ibPosaCallerStatTable
--      Added new node ibPosaTerminalHangUp, ibPosaFcmLinkNegoFailed,
--      ibPosaFcmPhyNegoFailed in ibPosaTrapPrex
--      Added new node ibPosaSrvStateChangeTrapEnable,
--      ibPosaAppStateChangeTrapEnable, ibPosaTerminalHangUpTrapEnable,
--      ibPosaFcmLnkNegoFailTrapEnable, ibPosaFcmPhyNegoFailTrapEnable,
--      in ibPosaControl
--      ibPosaAppName, ibPosaCallerIDTransEnable, ibPosaTpduChangeStrategy
--      in ibPosaAppTable
--      ibPosaTerminalName and ibPosaTerminalCfgIfIndex in ibPosaTerminalTable
--      ibPosaMapSrcCode in ibPosaMapTable
-- V1.3 2011-09-01 updated by he changfu,du pengfei
--      Added new node ibPosaBackupAppID,ibPosaQuietTimeOut
--      in ibPosaAppTable
--      Added a new value for IbPeerState.
--      2011-12-12 updated by lei hao,yang xu
--      Added new node, ibPosaFcmStatTransCnts, ibPosaFcmStatTransSuccessCnts
--      and ibPosaFcmStatTransCntsClear in ibPosaFcmStatTable
--      2012-2-28 updated by zhangxianyi
--      Added new node ibPosaAppHello, ibPosaAppHelloInterval
--      ibPosaAppRouterPort
--      in ibPosaAppTable
-- V1.4 2012-8-22 updated by dupengfei
--      Added value of "error(9)" for IbPeerState
-- V1.5 2013-08-30 updated by q04356
--      Modified the range of ibPosaAppID and ibPosaBackupAppID in ibPosaAppTable
--      Modified the range of ibPosaTerminalTransAppID in ibPosaTerminalTable
--      Modified the range of ibPosaMapAppID in ibPosaMapTable
--      2013-09-03 updated by q04356
--      Added new nodes ibPosaTcpConnectionNumber, ibPosaFcmConnectionNumber
--      ibPosaTcpConnectionThreshold, ibPosaFcmConnectionThreshold,
--      ibPosaTcpConnectionTrapEnable and
--      ibPosaFcmConnectionTrapEnable in ibPosaControl
--      Added new nodes ibPosaTcpConnectionExceed and
--      ibPosaFcmConnectionExceed in ibPosaTrapPrex
-- V1.6 2013-10-18 updated by zhangxinhua
--      Modified the MAX-ACCESS of ibPosaTerminalID to be accessible-for-notify
--      Deleted the range description of ibPosaTcpConnectionThreshold and
--      ibPosaFcmConnectionThreshold
--      Added new nodes ibPosaTcpTradeLimit, ibPosaTcpTradeTrapEnable,
--      ibPosaTcpTradeTimeout in ibPosaControl
--      Added new nodes ibPosaTcpTradeExceed in ibPosaTrapPrex
--      2013-12-14 updated by q04356
--      Modified the default of ibPosaFcmIdleTimeout in ibPosaControl
-- V1.7 2014-05-29 updated by liubo
--      Modified the range for ibPosaAppID and ibPosaBackupAppID in ibPosaAppTable
--      Modified the range for ibPosaTerminalTransAppID in ibPosaTerminalTable
--      Modified the range for ibPosaMapAppID in ibPosaMapTable
-- V1.8 2014-11-14 updated by liubo
--      Modified the range for ibPosaTerminalID in ibPosaTerminalTable
--      Modified the range for ibPosaBatchTerminalFirstID in ibPosaBatchTerminalTable
--      Modified the default value for ibPosaFcmConnectionThreshold
-- V1.9 2015-8-26 updated by limeng
--      Added ibPosaNiiStatTable
--      Added ibPosaE1StatTable
--      Added new nodes ibPosaTradeSuccessFallingTrapEnable, ibPosaTradeSuccessFallingThreshold,
--      ibPosaE1DialFallingTrapEnable, ibPosaE1DialFallingThreshold
--      and ibPosaFcmTradeAbnormalTrapEnable in ibPosaControl
--      Added new node ibPosaTermianlTcpConnectionNumber in ibPosaTerminalStatTable
--      Added new nodes ibPosaTradeSuccessFalling, ibPosaE1DialFalling
--      and ibPosaFcmTradeAbnormal in ibPosaTrapPrex
--      Added new object ibPosaCallerStatCallerID to ibPosaTerminalHangUp
--      Added new object ibPosaCallerStatCallerID to ibPosaFcmLinkNegoFailed
--      Added new object ibPosaCallerStatCallerID to ibPosaFcmPhyNegoFailed
--      Modified the MAX-ACCESS of ibPosaCallerStatCallerID to be accessible-for-notify
-- =================================================================
IB-POSA-MIB DEFINITIONS ::= BEGIN

IMPORTS
    ibCommon
        FROM IB-OID-MIB
    Integer32, Counter32, OBJECT-TYPE, MODULE-IDENTITY, NOTIFICATION-TYPE,
    Counter64, Gauge32
        FROM SNMPv2-SMI
    RowStatus, TruthValue, TEXTUAL-CONVENTION
        FROM SNMPv2-TC
    InetAddress, InetAddressType
        FROM INET-ADDRESS-MIB
    ifIndex, ifDescr
        FROM IF-MIB;

ibPosa MODULE-IDENTITY
    LAST-UPDATED "201508260000Z"
    ORGANIZATION
        "Intelbras S.A. Industria de Telecomunicacao Eletronica Brasileria."
    CONTACT-INFO
        ""
    DESCRIPTION
        "This MIB is to provide the definition of the POSA
        (Point Of Sale Access) system."
    REVISION "201508260000Z"
    DESCRIPTION
        "Added ibPosaNiiStatTable.
        Added ibPosaE1StatTable.
        Added new nodes ibPosaTradeSuccessFallingTrapEnable, ibPosaTradeSuccessFallingThreshold,
        ibPosaE1DialFallingTrapEnable, ibPosaE1DialFallingThreshold
        and ibPosaFcmTradeAbnormalTrapEnable in ibPosaContro.
        Added new node ibPosaTermianlTcpConnectionNumber in ibPosaTerminalStatTable.
        Added new nodes ibPosaTradeSuccessFalling, ibPosaE1DialFalling
        and ibPosaFcmTradeAbnormal in ibPosaTrapPrex.
        Added new object ibPosaCallerStatCallerID to ibPosaTerminalHangUp.
        Added new object ibPosaCallerStatCallerID to ibPosaFcmLinkNegoFailed.
        Added new object ibPosaCallerStatCallerID to ibPosaFcmPhyNegoFailed.
        Modified the MAX-ACCESS of ibPosaCallerStatCallerID to be accessible-for-notify."
    REVISION "201411140000Z"
    DESCRIPTION
        "Modified the range for ibPosaTerminalID in ibPosaTerminalTable.
        Modified the range for ibPosaBatchTerminalFirstID in ibPosaBatchTerminalTable.
        Modified the default value for ibPosaFcmConnectionThreshold"
    REVISION "200803120933Z"
    DESCRIPTION
        "The initial revision of this MIB module."
    ::= { ibCommon 92 }


-- definition of textual conventions

IbAppServiceType ::= TEXTUAL-CONVENTION
    STATUS       current
    DESCRIPTION
        "The service type of a POS application.  It means the way
        in which the router connects with the application server.
        At present, it supports two service types, tcp(1) and flow(2).
        If the router connects with the server through SEARIAL/ASYNC
        interface, the service type is flow(1).  If through TCP/IP,
        the service type is tcp(1)."
    SYNTAX INTEGER
        {
        tcp(1),
        flow(2)
        }

IbAppMode ::= TEXTUAL-CONVENTION
    STATUS       current
    DESCRIPTION
        "The work mode of a POS application.  It has two value normal(1)
        and temporary(2).  This attribute is valid only when the service type
        is tcp(1).  If it works in temporary(2) mode, the TCP connection
        between router and application server is established
        when a POS trade begins and disconnected when a POS trade finishes.
        In normal(1) mode, the TCP connection is established
        when POS function is enabled and exists all along."
    SYNTAX INTEGER
        {
        normal(1),
        temporary(2)
        }

IbPeerState ::= TEXTUAL-CONVENTION
    STATUS       current
    DESCRIPTION
        "The current running state of the peer (application server or POS terminal)
        of the router.
        notset(1)     The peer is not configured correctly.
        down(2)       The interface connecting with the peer is down.
        up(3)         The interface connecting with the peer is up.
        kept(4)       The connection between router and the peer is
                      not established.
        linking(5)    The connection between router and the peer is
                      establishing.
        linked(6)     The connection between router and the peer is
                      established.
        multilink(7)  There are multiple connections between router and the peer.
        blocked(8)    The connection between router and the peer is
                      unreachable.
        error(9)      Enable failed.

        The status of down(2) and up(3) appear only when the router and the peer
        are connected with interface.
        The status about TCP connections appear when the router and the peer are
        connected with TCP/IP.
        "
    SYNTAX INTEGER
        {
        notset(1),
        down(2),
        up(3),
        kept(4),
        linking(5),
        linked(6),
        multilink(7),
        blocked(8),
        error(9)
        }

IbTerminalAccessType ::= TEXTUAL-CONVENTION
    STATUS       current
    DESCRIPTION
        "The access type of a POS terminal.  Now it supports 3 types.
        fcm(1)  The POS terminal connects with router through FCM interface.
        flow(2) The POS terminal connects with router through SERIAL, ASYNC,
                AM (Analog Modem) or AUX interface.
        tcp(3)  The POS terminal connects with router through TCP/IP protocol.
                The default access type is fcm(2)."
    SYNTAX INTEGER
        {
        fcm(1),
        flow(2),
        tcp(3)
        }

IbTpduChangeStrategy ::= TEXTUAL-CONVENTION
    STATUS       current
    DESCRIPTION
        "The strategy to modify the address of the packet from terminals before
        delivering it to application server.  Now it supports 2 types.
        ChangeTpduSrc(1)  Replace the source address of the packet with POSID.
        ChangeTpduDest(2) Replace the destination address of the packet with
                          POSID."
    SYNTAX INTEGER
        {
        changeTpduSrc(1),
        changeTpduDest(2)
        }

--
-- nodes defined
--

ibPosaControl OBJECT IDENTIFIER ::= { ibPosa 1 }

ibPosaServerEnable OBJECT-TYPE
    SYNTAX INTEGER
        {
        disabled(1),
        enabled(2)
        }
    MAX-ACCESS read-write
    STATUS current
    DESCRIPTION
        "This attribute controls the starting or stoppage of POS access function.
        The defalut value is disabled(1)."
    DEFVAL { disabled }
    ::= { ibPosaControl 1 }

ibPosaFcmAnswerTimeout OBJECT-TYPE
    SYNTAX Integer32 (500..2000)
    UNITS "milliseconds"
    MAX-ACCESS read-write
    STATUS current
    DESCRIPTION
        "The maximum answer time of a POS connection through a FCM (Fast
        Connection Modem) interface.
        The answer time is the interval from the POS terminal sending request
        to the Router giving its reply, in units of milliseconds."
    DEFVAL { 2000 }
    ::= { ibPosaControl 2 }

ibPosaFcmTradeTimeout OBJECT-TYPE
    SYNTAX Integer32 (30000..12000000)
    UNITS "milliseconds"
    MAX-ACCESS read-write
    STATUS current
    DESCRIPTION
        "The maximum time of a POS trade through a FCM interface,
        in units of milliseconds."
    DEFVAL { 12000000 }
    ::= { ibPosaControl 3 }

ibPosaFcmIdleTimeout OBJECT-TYPE
    SYNTAX Integer32 (1..12000)
    UNITS "seconds"
    MAX-ACCESS read-write
    STATUS current
    DESCRIPTION
        "The maximum idle time of a POS connection through the FCM interface,
        in units of seconds."
    DEFVAL { 180 }
    ::= { ibPosaControl 4 }

ibPosaSrvStateChangeTrapEnable OBJECT-TYPE
    SYNTAX TruthValue
    MAX-ACCESS read-write
    STATUS current
    DESCRIPTION
        "This attribute controls whether the ibPosaServerStatusChange trap will
        be sent or not."
    DEFVAL { true }
    ::= { ibPosaControl 5 }

ibPosaAppStateChangeTrapEnable OBJECT-TYPE
    SYNTAX TruthValue
    MAX-ACCESS read-write
    STATUS current
    DESCRIPTION
        "This attribute controls whether the ibPosaAppStateChange trap will
        be sent or not."
    DEFVAL { true }
    ::= { ibPosaControl 6 }

ibPosaTerminalHangUpTrapEnable OBJECT-TYPE
    SYNTAX TruthValue
    MAX-ACCESS read-write
    STATUS current
    DESCRIPTION
        "This attribute controls whether the ibPosaTerminalHangUp trap will
        be sent or not."
    DEFVAL { true }
    ::= { ibPosaControl 7 }

ibPosaFcmLnkNegoFailTrapEnable OBJECT-TYPE
    SYNTAX TruthValue
    MAX-ACCESS read-write
    STATUS current
    DESCRIPTION
        "This attribute controls whether the ibPosaFcmLinkNegoFailed trap will
        be sent or not."
    DEFVAL { true }
    ::= { ibPosaControl 8 }

ibPosaFcmPhyNegoFailTrapEnable OBJECT-TYPE
    SYNTAX TruthValue
    MAX-ACCESS read-write
    STATUS current
    DESCRIPTION
        "This attribute controls whether the ibPosaFcmPhyNegoFailed trap will
        be sent or not."
    DEFVAL { true }
    ::= { ibPosaControl 9 }

ibPosaTcpConnectionNumber OBJECT-TYPE
    SYNTAX Integer32
    MAX-ACCESS read-only
    STATUS current
    DESCRIPTION
        "The current number of TCP connections."
    ::= { ibPosaControl 10 }

ibPosaFcmConnectionNumber OBJECT-TYPE
    SYNTAX Integer32
    MAX-ACCESS read-only
    STATUS current
    DESCRIPTION
        "The current number of FCM connections."
    ::= { ibPosaControl 11 }

ibPosaTcpConnectionThreshold OBJECT-TYPE
    SYNTAX Integer32
    MAX-ACCESS read-write
    STATUS current
    DESCRIPTION
        "The threshold of TCP connections."
    DEFVAL {4096}
    ::= { ibPosaControl 12 }

ibPosaFcmConnectionThreshold OBJECT-TYPE
    SYNTAX Integer32
    MAX-ACCESS read-write
    STATUS current
    DESCRIPTION
        "The threshold of FCM connections."
    DEFVAL {1024}
    ::= { ibPosaControl 13 }

ibPosaTcpConnectionTrapEnable OBJECT-TYPE
    SYNTAX TruthValue
    MAX-ACCESS read-write
    STATUS current
    DESCRIPTION
        "This attribute specifies the threshold that must be exceeded to
        send the ibPosaTcpConnectionExceed trap."
    DEFVAL { true }
    ::= { ibPosaControl 14 }

ibPosaFcmConnectionTrapEnable OBJECT-TYPE
    SYNTAX TruthValue
    MAX-ACCESS read-write
    STATUS current
    DESCRIPTION
        "This attribute specifies the threshold that must be exceeded to
        send the ibPosaFcmConnectionExceed trap."
    DEFVAL { true }
    ::= { ibPosaControl 15 }

ibPosaTcpTradeLimit OBJECT-TYPE
    SYNTAX Integer32
    MAX-ACCESS read-write
    STATUS current
    DESCRIPTION
        "The limit of concurrent trades in one TCP connection.  The value 0
        means unlimited."
    DEFVAL {0}
    ::= { ibPosaControl 16 }

ibPosaTcpTradeTrapEnable OBJECT-TYPE
    SYNTAX TruthValue
    MAX-ACCESS read-write
    STATUS current
    DESCRIPTION
        "This attribute specifies the limit that must be exceeded to
        send the ibPosaTcpTradeExceed trap."
    DEFVAL { true }
    ::= { ibPosaControl 17 }

ibPosaTcpTradeTimeout OBJECT-TYPE
    SYNTAX Integer32
    MAX-ACCESS read-write
    STATUS current
    DESCRIPTION
        "The maximum interval to wait for the reply from sending the trade
        packet to the application server.  The value 0 means wait forever."
    DEFVAL {240}
    ::= { ibPosaControl 18 }

ibPosaTradeSuccessFallingTrapEnable OBJECT-TYPE
    SYNTAX TruthValue
    MAX-ACCESS read-write
    STATUS current
    DESCRIPTION
        "This attribute controls whether the ibPosaTradeSuccessFalling trap will
        be sent or not."
    DEFVAL { true }
    ::= { ibPosaControl 19 }

ibPosaTradeSuccessFallingThreshold OBJECT-TYPE
    SYNTAX Integer32
    MAX-ACCESS read-write
    STATUS current
    DESCRIPTION
        "The threshold of transaction success rate ."
    DEFVAL {90}
    ::= { ibPosaControl 20 }

ibPosaE1DialFallingTrapEnable OBJECT-TYPE
    SYNTAX TruthValue
    MAX-ACCESS read-write
    STATUS current
    DESCRIPTION
        "This attribute controls whether the ibPosaE1DialFalling trap will
        be sent or not."
    DEFVAL { true }
    ::= { ibPosaControl 21 }

ibPosaE1DialFallingThreshold OBJECT-TYPE
    SYNTAX Integer32
    MAX-ACCESS read-write
    STATUS current
    DESCRIPTION
        "The threshold of dialing success rate ."
    DEFVAL {90}
    ::= { ibPosaControl 22 }

ibPosaFcmTradeAbnormalTrapEnable OBJECT-TYPE
    SYNTAX TruthValue
    MAX-ACCESS read-write
    STATUS current
    DESCRIPTION
        "This attribute controls whether the ibPosaFcmTradeAbnormal trap will
        be sent or not."
    DEFVAL { true }
    ::= { ibPosaControl 23 }

ibPosaTables OBJECT IDENTIFIER ::= { ibPosa 2 }

--
-- definition of ibPosaAppTable
--

ibPosaAppTable OBJECT-TYPE
    SYNTAX SEQUENCE OF IbPosaAppEntry
    MAX-ACCESS not-accessible
    STATUS current
    DESCRIPTION
        "This table shows the configuration information and
        running status of POS application."
    ::= { ibPosaTables 1 }

ibPosaAppEntry OBJECT-TYPE
    SYNTAX IbPosaAppEntry
    MAX-ACCESS not-accessible
    STATUS current
    DESCRIPTION
        "This table shows the configuration information and
        running status of POS application."
    INDEX { ibPosaAppID }
    ::= { ibPosaAppTable 1 }

IbPosaAppEntry ::=
    SEQUENCE {
        ibPosaAppID
            Integer32,
        ibPosaAppServiceType
            IbAppServiceType,
        ibPosaAppIfIndex
            Integer32,
        ibPosaAppMode
            IbAppMode,
        ibPosaAppHostIPType
            InetAddressType,
        ibPosaAppHostIP
            InetAddress,
        ibPosaAppHostPort
            Integer32,
        ibPosaAppRouterIPType
            InetAddressType,
        ibPosaAppRouterIP
            InetAddress,
        ibPosaAppKeepAliveInterval
            Integer32,
        ibPosaAppKeepAliveCount
            Integer32,
        ibPosaAppConnectTimeout
            Integer32,
        ibPosaAppState
            IbPeerState,
        ibPosaAppRowStatus
            RowStatus,
        ibPosaAppName
            OCTET STRING,
        ibPosaCallerIDTransEnable
            TruthValue,
        ibPosaTpduChangeStrategy
            IbTpduChangeStrategy,
        ibPosaBackupAppID
            Integer32,
        ibPosaQuietTimeOut
            Integer32,
        ibPosaAppHello
            TruthValue,
        ibPosaAppHelloInterval
            Integer32,
        ibPosaAppRouterPort
            Integer32
     }

ibPosaAppID OBJECT-TYPE
    SYNTAX Integer32 (1..1024)
    MAX-ACCESS accessible-for-notify
    STATUS current
    DESCRIPTION
        "The identification of a POS application."
    ::= { ibPosaAppEntry 1 }

ibPosaAppServiceType OBJECT-TYPE
    SYNTAX IbAppServiceType
    MAX-ACCESS read-create
    STATUS current
    DESCRIPTION
        "The service type of a POS application.  It means the way
        in which the router connects with the application server."
    DEFVAL { tcp }
    ::= { ibPosaAppEntry 2 }

ibPosaAppIfIndex OBJECT-TYPE
    SYNTAX Integer32
    MAX-ACCESS read-create
    STATUS current
    DESCRIPTION
        "This attribute is the ifindex through which the router connecting with
        the application server, if the service type of POS application is flow(2).
        It is invalid if the service type is tcp(1).
        At preasent, it supports 5 types of interface: FCM, SERIAL, ASYNC,
        AM (Analog Modem) and AUX."
    REFERENCE
        "ifindex"
    ::= { ibPosaAppEntry 3 }

ibPosaAppMode OBJECT-TYPE
    SYNTAX IbAppMode
    MAX-ACCESS read-create
    STATUS current
    DESCRIPTION
        "The work mode of a POS application."
    DEFVAL { normal }
    ::= { ibPosaAppEntry 4 }

ibPosaAppHostIPType OBJECT-TYPE
    SYNTAX InetAddressType
    MAX-ACCESS read-create
    STATUS current
    DESCRIPTION
        "The IP address type of the application server.  And now it must be IPV4.
        It is invalid if the service type is flow(2)."
    ::= { ibPosaAppEntry 5 }

ibPosaAppHostIP OBJECT-TYPE
    SYNTAX InetAddress
    MAX-ACCESS read-create
    STATUS current
    DESCRIPTION
        "The IP address of the application server.  And now it only supports IPV4.
        It is invalid if the service type is flow(2)."
    ::= { ibPosaAppEntry 6 }

ibPosaAppHostPort OBJECT-TYPE
    SYNTAX Integer32 (0..65535)
    MAX-ACCESS read-create
    STATUS current
    DESCRIPTION
        "The listening port of the application server.  If the information of
        the application server is not specified, this object will return the
        value 0.
        It is invalid if the service type is flow(2)."
    ::= { ibPosaAppEntry 7 }

ibPosaAppRouterIPType OBJECT-TYPE
    SYNTAX InetAddressType
    MAX-ACCESS read-create
    STATUS current
    DESCRIPTION
        "The source IP address type of the access router.  Now it must be ipv4.
        It is invalid if the service type is flow(2)."
    ::= { ibPosaAppEntry 8 }

ibPosaAppRouterIP OBJECT-TYPE
    SYNTAX InetAddress
    MAX-ACCESS read-create
    STATUS current
    DESCRIPTION
        "The source IP address of access router used in connecting with
        application server.  Now it only supports ipv4.
        It is invalid if the service type is flow(2)."
    ::= { ibPosaAppEntry 9 }

ibPosaAppKeepAliveInterval OBJECT-TYPE
    SYNTAX Integer32 (1..7200)
    UNITS "seconds"
    MAX-ACCESS read-create
    STATUS current
    DESCRIPTION
        "The TCP keep alive interval of the connection between the router and
        the application server.  In unit of seconds.
        The default value is 2 seconds.
        It is valid only when the service type is tcp(1)."
    DEFVAL { 2 }
    ::= { ibPosaAppEntry 10 }

ibPosaAppKeepAliveCount OBJECT-TYPE
    SYNTAX Integer32 (2..100)
    MAX-ACCESS read-create
    STATUS current
    DESCRIPTION
        "The maximum number of sending TCP keep alive packets.
        It is valid only when the service type is tcp(1)."
    DEFVAL { 3 }
    ::= { ibPosaAppEntry 11 }

ibPosaAppConnectTimeout OBJECT-TYPE
    SYNTAX Integer32 (1..20)
    UNITS "seconds"
    MAX-ACCESS read-create
    STATUS current
    DESCRIPTION
        "The maximum interval that the router waits for the reply from
        application server after sending the request for establishing a TCP
        connection.  It is invalid if the service type is flow(2)."
    DEFVAL { 20 }
    ::= { ibPosaAppEntry 12 }

ibPosaAppState OBJECT-TYPE
    SYNTAX IbPeerState
    MAX-ACCESS read-only
    STATUS current
    DESCRIPTION
        "The current running state of application server."
    ::= { ibPosaAppEntry 13 }

ibPosaAppRowStatus OBJECT-TYPE
    SYNTAX RowStatus
    MAX-ACCESS read-create
    STATUS current
    DESCRIPTION
        "Operation status."
    ::= { ibPosaAppEntry 14 }

ibPosaAppName OBJECT-TYPE
    SYNTAX OCTET STRING (SIZE (0..32))
    MAX-ACCESS read-create
    STATUS current
    DESCRIPTION
        "The description of a POS application."
    ::= { ibPosaAppEntry 15 }

ibPosaCallerIDTransEnable OBJECT-TYPE
    SYNTAX TruthValue
    MAX-ACCESS read-create
    STATUS current
    DESCRIPTION
        "Enable or disable the caller-id transmission function."
    DEFVAL { false }
    ::= { ibPosaAppEntry 16 }

ibPosaTpduChangeStrategy OBJECT-TYPE
    SYNTAX IbTpduChangeStrategy
    MAX-ACCESS read-create
    STATUS current
    DESCRIPTION
        "Set the strategy to modify the address of the packet from terminals
        before delivering it to application server."
    DEFVAL { changeTpduSrc }
    ::= { ibPosaAppEntry 17 }

ibPosaBackupAppID OBJECT-TYPE
    SYNTAX Integer32 (0..1024)
    MAX-ACCESS read-create
    STATUS current
    DESCRIPTION
        "Specify the backup application ID, 0 indicates not using backup application.
        It is invalid if the service type is flow(2)."
    ::= { ibPosaAppEntry 18 }

ibPosaQuietTimeOut OBJECT-TYPE
    SYNTAX Integer32 (10..600)
    MAX-ACCESS read-create
    STATUS current
    DESCRIPTION
        "Specify the wait time for re-activating application server.
        It is invalid if the service type is flow(2)."
    ::= { ibPosaAppEntry 19 }

ibPosaAppHello OBJECT-TYPE
    SYNTAX TruthValue
    MAX-ACCESS read-create
    STATUS current
    DESCRIPTION
        "Specify the switch of hello packet for the application server."
    DEFVAL { false }
    ::= { ibPosaAppEntry 20 }

ibPosaAppHelloInterval OBJECT-TYPE
    SYNTAX Integer32 (1..600)
    MAX-ACCESS read-create
    STATUS current
    DESCRIPTION
        "Specify the interval time in minute(s) of hello packet."
    DEFVAL { 1 }
    ::= { ibPosaAppEntry 21 }

ibPosaAppRouterPort OBJECT-TYPE
    SYNTAX Integer32 (0..4999)
    MAX-ACCESS read-create
    STATUS current
    DESCRIPTION
        "The source port of access router used in connecting with
        application server.  0 indicates not to specify the source port.
        It is valid only if the service type is tcp(1) and mode is normal(1)."
    ::= { ibPosaAppEntry 22 }

--
-- definition of ibPosaTerminalTable
--

ibPosaTerminalTable OBJECT-TYPE
    SYNTAX SEQUENCE OF IbPosaTerminalEntry
    MAX-ACCESS not-accessible
    STATUS current
    DESCRIPTION
        "This table shows the configuration information and
        running status of POS terminal."
    ::= { ibPosaTables 2 }

ibPosaTerminalEntry OBJECT-TYPE
    SYNTAX IbPosaTerminalEntry
    MAX-ACCESS not-accessible
    STATUS current
    DESCRIPTION
        "This table shows the configuration information and
        running status of POS terminal."
    INDEX { ibPosaTerminalID }
    ::= { ibPosaTerminalTable 1 }

IbPosaTerminalEntry ::=
    SEQUENCE {
        ibPosaTerminalID
            Integer32,
        ibPosaTerminalAccessType
            IbTerminalAccessType,
        ibPosaTerminalIfIndex
            Integer32,
        ibPosaTerminalTransAppID
            Integer32,
        ibPosaTerminalListenPort
            Integer32,
        ibPosaTerminalState
            IbPeerState,
        ibPosaTerminalRowStatus
            RowStatus,
        ibPosaTerminalName
            OCTET STRING,
        ibPosaTerminalCfgIfIndex
            Integer32
     }

ibPosaTerminalID OBJECT-TYPE
    SYNTAX Integer32 (1..1024)
    MAX-ACCESS accessible-for-notify
    STATUS current
    DESCRIPTION
        "The identification of a POS terminal."
    ::= { ibPosaTerminalEntry 1 }

ibPosaTerminalAccessType OBJECT-TYPE
    SYNTAX IbTerminalAccessType
    MAX-ACCESS read-create
    STATUS current
    DESCRIPTION
        "The access type of a POS terminal."
    DEFVAL { fcm }
    ::= { ibPosaTerminalEntry 2 }

ibPosaTerminalIfIndex OBJECT-TYPE
    SYNTAX Integer32
    MAX-ACCESS read-create
    STATUS current
    DESCRIPTION
        "The ifindex of the interface through which connects the POS terminal
        and the router.  It is invalid if the access type is TCP."
    REFERENCE
        "ifindex"
    ::= { ibPosaTerminalEntry 3 }

ibPosaTerminalTransAppID OBJECT-TYPE
    SYNTAX Integer32 (0..1024)
    MAX-ACCESS read-create
    STATUS current
    DESCRIPTION
        "The identification of the application server to which all the packets
        from this POS terminal will be sent.
        If this object is set to 0, the destination application server to which
        a packet from this POS terminal will be sent is determined by its TPDU
        (Transport Protocol Data Unit) destination address.
        It is invalid if the access type is TCP."
    DEFVAL { 0 }
    ::= { ibPosaTerminalEntry 4 }

ibPosaTerminalListenPort OBJECT-TYPE
    SYNTAX Integer32 (0..65535)
    MAX-ACCESS read-create
    STATUS current
    DESCRIPTION
        "The listening port accepting the connection from POS terminals.
        It is valid only when the access type is TCP."
    ::= { ibPosaTerminalEntry 5 }

ibPosaTerminalState OBJECT-TYPE
    SYNTAX IbPeerState
    MAX-ACCESS read-only
    STATUS current
    DESCRIPTION
        "The current running status of a POS terminal."
    ::= { ibPosaTerminalEntry 6 }

ibPosaTerminalRowStatus OBJECT-TYPE
    SYNTAX RowStatus
    MAX-ACCESS read-create
    STATUS current
    DESCRIPTION
        "Operation status."
    ::= { ibPosaTerminalEntry 7 }

ibPosaTerminalName OBJECT-TYPE
    SYNTAX OCTET STRING (SIZE (0..32))
    MAX-ACCESS read-create
    STATUS current
    DESCRIPTION
        "The description of a POS terminal."
    ::= { ibPosaTerminalEntry 8 }

ibPosaTerminalCfgIfIndex OBJECT-TYPE
    SYNTAX Integer32
    MAX-ACCESS read-only
    STATUS current
    DESCRIPTION
        "The ifindex of the interface on which the terminal configuration is.
        If it is a physical interface, its value is equal to that of
        ibPosaTerminalIfIndex."
    REFERENCE
        "ifindex"
    ::= { ibPosaTerminalEntry 9 }

--
-- definition of ibPosaMapTable
--

ibPosaMapTable OBJECT-TYPE
    SYNTAX SEQUENCE OF IbPosaMapEntry
    MAX-ACCESS not-accessible
    STATUS current
    DESCRIPTION
        "This table describe the application-mapping information."
    ::= { ibPosaTables 3 }

ibPosaMapEntry OBJECT-TYPE
    SYNTAX IbPosaMapEntry
    MAX-ACCESS not-accessible
    STATUS current
    DESCRIPTION
        "This table describe the application-mapping information."
    INDEX { ibPosaMapSrcCode, ibPosaMapDestCode }
    ::= { ibPosaMapTable 1 }

IbPosaMapEntry ::=
    SEQUENCE {
        ibPosaMapDestCode
            OCTET STRING,
        ibPosaMapAppID
            Integer32,
        ibPosaMapRowStatus
            RowStatus,
        ibPosaMapSrcCode
            OCTET STRING
     }

ibPosaMapDestCode OBJECT-TYPE
    SYNTAX OCTET STRING (SIZE (4..7))
    MAX-ACCESS not-accessible
    STATUS current
    DESCRIPTION
        "The destination code of the mapping item.  Generally, the destination
        code is a 4-character-string.  If the destination address in POS packet
        matches the code, the packet will be deliveried to the corresponding
        application server.  If any code can not be matched, the packet will be
        deliveried to the default server.  A special destination code, 'default',
        is for default mapping item."
    ::= { ibPosaMapEntry 1 }

ibPosaMapAppID OBJECT-TYPE
    SYNTAX Integer32 (1..1024)
    MAX-ACCESS read-create
    STATUS current
    DESCRIPTION
        "The identifier of POS application.  It is the index of ibPosaAppTable."
    ::= { ibPosaMapEntry 2 }

ibPosaMapRowStatus OBJECT-TYPE
    SYNTAX RowStatus
    MAX-ACCESS read-create
    STATUS current
    DESCRIPTION
        "Operation status."
    ::= { ibPosaMapEntry 3 }

ibPosaMapSrcCode OBJECT-TYPE
    SYNTAX OCTET STRING (SIZE (4..7))
    MAX-ACCESS not-accessible
    STATUS current
    DESCRIPTION
        "The source code of the mapping item.  Generally, the source code is a
        4-character-string.  If the source address in POS packet matches the
        code, the packet will be deliveried to the corresponding application
        server.  If any code can not be matched, the packet will be deliveried
        to the default server.  A special source code, 'default', is for
        default mapping item."
    ::= { ibPosaMapEntry 4 }

--
-- definition of ibPosaFcmStatTable
--

ibPosaFcmStatTable OBJECT-TYPE
    SYNTAX SEQUENCE OF IbPosaFcmStatEntry
    MAX-ACCESS not-accessible
    STATUS current
    DESCRIPTION
        "This table shows the statistics information of FCM interface."
    ::= { ibPosaTables 4 }

ibPosaFcmStatEntry OBJECT-TYPE
    SYNTAX IbPosaFcmStatEntry
    MAX-ACCESS not-accessible
    STATUS current
    DESCRIPTION
        "This table shows the statistics information of FCM interface."
    INDEX { ibPosaFcmStatIfIndex }
    ::= { ibPosaFcmStatTable 1 }

IbPosaFcmStatEntry ::=
    SEQUENCE {
        ibPosaFcmStatIfIndex
            Integer32,
        ibPosaFcmStatTimeoutCnts
            Counter32,
        ibPosaFcmStatConnectFailCnts
            Counter32,
        ibPosaFcmStatTransCnts
            Gauge32,
        ibPosaFcmStatTransSuccessCnts
            Gauge32,
        ibPosaFcmStatTransCntsClear
            TruthValue
     }

ibPosaFcmStatIfIndex OBJECT-TYPE
    SYNTAX Integer32 (0..2147483647)
    MAX-ACCESS not-accessible
    STATUS current
    DESCRIPTION
        "The index of FCM interface."
    ::= { ibPosaFcmStatEntry 1 }

ibPosaFcmStatTimeoutCnts OBJECT-TYPE
    SYNTAX Counter32
    MAX-ACCESS read-only
    STATUS current
    DESCRIPTION
        "The number of disconnections because of trade timeouts."
    ::= { ibPosaFcmStatEntry 2 }

ibPosaFcmStatConnectFailCnts OBJECT-TYPE
    SYNTAX Counter32
    MAX-ACCESS read-only
    STATUS current
    DESCRIPTION
        "The number of connection failures because of unsuccessful negotiations."
    ::= { ibPosaFcmStatEntry 3 }
ibPosaFcmStatTransCnts OBJECT-TYPE
    SYNTAX Gauge32
    MAX-ACCESS read-only
    STATUS current
    DESCRIPTION
        "The number of all transactions made through the interface."
    ::= { ibPosaFcmStatEntry 4 }

ibPosaFcmStatTransSuccessCnts OBJECT-TYPE
    SYNTAX Gauge32
    MAX-ACCESS read-only
    STATUS current
    DESCRIPTION
        "The number of successful transactions made through the interface."
    ::= { ibPosaFcmStatEntry 5 }

ibPosaFcmStatTransCntsClear OBJECT-TYPE
    SYNTAX TruthValue
    MAX-ACCESS read-write
    STATUS current
    DESCRIPTION
        "Clear the number of successful transactions and all transactions."
    DEFVAL { false }
    ::= { ibPosaFcmStatEntry 6 }

--
-- definition of ibPosaAppStatTable
--

ibPosaAppStatTable OBJECT-TYPE
    SYNTAX SEQUENCE OF IbPosaAppStatEntry
    MAX-ACCESS not-accessible
    STATUS current
    DESCRIPTION
        "This table shows the statistics information of application."
    ::= { ibPosaTables 5 }

ibPosaAppStatEntry OBJECT-TYPE
    SYNTAX IbPosaAppStatEntry
    MAX-ACCESS not-accessible
    STATUS current
    DESCRIPTION
        "This table shows the statistics information of application."
    INDEX { ibPosaAppID }
    ::= { ibPosaAppStatTable 1 }

IbPosaAppStatEntry ::=
    SEQUENCE {
        ibPosaAppRecvPkts
            Counter32,
        ibPosaAppSendPkts
            Counter32,
        ibPosaAppErrPkts
            Counter32,
        ibPosaAppDistributeErrCnts
            Counter32,
        ibPosaAppInDiscardedPkts
            Counter32,
        ibPosaAppOutDiscardedPkts
            Counter32
     }

ibPosaAppRecvPkts OBJECT-TYPE
    SYNTAX Counter32
    MAX-ACCESS read-only
    STATUS current
    DESCRIPTION
        "The number of packets recieved from the application server."
    ::= { ibPosaAppStatEntry 1 }

ibPosaAppSendPkts OBJECT-TYPE
    SYNTAX Counter32
    MAX-ACCESS read-only
    STATUS current
    DESCRIPTION
        "The number of packets sent to the application server."
    ::= { ibPosaAppStatEntry 2 }

ibPosaAppErrPkts OBJECT-TYPE
    SYNTAX Counter32
    MAX-ACCESS read-only
    STATUS current
    DESCRIPTION
        "The number of inbound packets that contained errors."
    ::= { ibPosaAppStatEntry 3 }

ibPosaAppDistributeErrCnts OBJECT-TYPE
    SYNTAX Counter32
    MAX-ACCESS read-only
    STATUS current
    DESCRIPTION
        "The number of packets that are discarded when no corresponding POS
        terminal can be found."
    ::= { ibPosaAppStatEntry 4 }

ibPosaAppInDiscardedPkts OBJECT-TYPE
    SYNTAX Counter32
    MAX-ACCESS read-only
    STATUS current
    DESCRIPTION
        "The number of inbound packets that are discarded when the incoming
        buffer is full."
    ::= { ibPosaAppStatEntry 5 }

ibPosaAppOutDiscardedPkts OBJECT-TYPE
    SYNTAX Counter32
    MAX-ACCESS read-only
    STATUS current
    DESCRIPTION
        "The number of outbound packets that are discarded because of link
        errors between the router and the application server."
    ::= { ibPosaAppStatEntry 6 }

--
-- definition of ibPosaTerminalStatTable
--

ibPosaTerminalStatTable OBJECT-TYPE
    SYNTAX SEQUENCE OF IbPosaTerminalStatEntry
    MAX-ACCESS not-accessible
    STATUS current
    DESCRIPTION
        "This table shows the statistics information of application."
    ::= { ibPosaTables 6 }

ibPosaTerminalStatEntry OBJECT-TYPE
    SYNTAX IbPosaTerminalStatEntry
    MAX-ACCESS not-accessible
    STATUS current
    DESCRIPTION
        "This table shows the statistics information of application."
    INDEX { ibPosaTerminalID }
    ::= { ibPosaTerminalStatTable 1 }

IbPosaTerminalStatEntry ::=
    SEQUENCE {
        ibPosaTerminalRecvPkts
            Counter32,
        ibPosaTerminalSendPkts
            Counter32,
        ibPosaTerminalErrPkts
            Counter32,
        ibPosaTerminalMapErrCnts
            Counter32,
        ibPosaTerminalInDiscardedPkts
            Counter32,
        ibPosaTerminalOutDiscardedPkts
            Counter32,
        ibPosaTermianlTcpConnectionNumber
            Integer32
     }

ibPosaTerminalRecvPkts OBJECT-TYPE
    SYNTAX Counter32
    MAX-ACCESS read-only
    STATUS current
    DESCRIPTION
        "The number of packets recieved from the POS terminal."
    ::= { ibPosaTerminalStatEntry 1 }

ibPosaTerminalSendPkts OBJECT-TYPE
    SYNTAX Counter32
    MAX-ACCESS read-only
    STATUS current
    DESCRIPTION
        "The number of packets sent to the POS terminal."
    ::= { ibPosaTerminalStatEntry 2 }

ibPosaTerminalErrPkts OBJECT-TYPE
    SYNTAX Counter32
    MAX-ACCESS read-only
    STATUS current
    DESCRIPTION
        "The number of inbound packets that contained errors."
    ::= { ibPosaTerminalStatEntry 3 }

ibPosaTerminalMapErrCnts OBJECT-TYPE
    SYNTAX Counter32
    MAX-ACCESS read-only
    STATUS current
    DESCRIPTION
        "The number of packets that are discarded because of mapping errors."
    ::= { ibPosaTerminalStatEntry 4 }

ibPosaTerminalInDiscardedPkts OBJECT-TYPE
    SYNTAX Counter32
    MAX-ACCESS read-only
    STATUS current
    DESCRIPTION
        "The number of inbound packets that are discarded when the incoming
        buffer is full."
    ::= { ibPosaTerminalStatEntry 5 }

ibPosaTerminalOutDiscardedPkts OBJECT-TYPE
    SYNTAX Counter32
    MAX-ACCESS read-only
    STATUS current
    DESCRIPTION
        "The number of outbound packets that are discarded because of link
        errors between the router and the POS terminal."
    ::= { ibPosaTerminalStatEntry 6 }

ibPosaTermianlTcpConnectionNumber OBJECT-TYPE
    SYNTAX Integer32
    MAX-ACCESS read-only
    STATUS current
    DESCRIPTION
        "The number of TCP connections between the router and the POS terminal."
    ::= { ibPosaTerminalStatEntry 7 }

--
-- definition of ibPosaBatchTerminalTable
--

ibPosaBatchTerminalTable OBJECT-TYPE
    SYNTAX SEQUENCE OF IbPosaBatchTerminalEntry
    MAX-ACCESS not-accessible
    STATUS current
    DESCRIPTION
        "The table of the configuration information relevant to
        a batch of POS terminals."
    ::= { ibPosaTables 7 }

ibPosaBatchTerminalEntry OBJECT-TYPE
    SYNTAX IbPosaBatchTerminalEntry
    MAX-ACCESS not-accessible
    STATUS current
    DESCRIPTION
        "The configuration information relevant to a batch of
        POS terminals."
    INDEX { ifIndex }
    ::= { ibPosaBatchTerminalTable 1 }

IbPosaBatchTerminalEntry ::=
    SEQUENCE {
        ibPosaBatchTerminalFirstID
            Integer32,
        ibPosaBatchTerminalRowStatus
            RowStatus
     }

ibPosaBatchTerminalFirstID OBJECT-TYPE
    SYNTAX Integer32 (1..1024)
    MAX-ACCESS read-create
    STATUS current
    DESCRIPTION
        "The first ID of the batch of POS terminals."
    ::= { ibPosaBatchTerminalEntry 1 }

ibPosaBatchTerminalRowStatus OBJECT-TYPE
    SYNTAX RowStatus
    MAX-ACCESS read-create
    STATUS current
    DESCRIPTION
        "Operation status."
    ::= { ibPosaBatchTerminalEntry 2 }

--
-- definition of ibPosaTcpTermStatTable
--

ibPosaTcpTermStatTable OBJECT-TYPE
    SYNTAX SEQUENCE OF IbPosaTcpTermStatEntry
    MAX-ACCESS not-accessible
    STATUS current
    DESCRIPTION
        "This table shows the statistics information of terminal whose
        access type is tcp."
    ::= { ibPosaTables 8 }

ibPosaTcpTermStatEntry OBJECT-TYPE
    SYNTAX IbPosaTcpTermStatEntry
    MAX-ACCESS not-accessible
    STATUS current
    DESCRIPTION
        "This table shows the statistics information of terminal whose
        access type is tcp."
    INDEX { ibPosaTcpTermStatIndex }
    ::= { ibPosaTcpTermStatTable 1 }

IbPosaTcpTermStatEntry ::=
    SEQUENCE {
        ibPosaTcpTermStatIndex
            Integer32,
        ibPosaTcpTermStatIPType
            InetAddressType,
        ibPosaTcpTermStatIP
            InetAddress,
        ibPosaTcpTermStatIPMask
            InetAddress,
        ibPosaTcpTermRecvPkts
            Counter64,
        ibPosaTcpTermSendPkts
            Counter64,
        ibPosaTcpTermErrPkts
            Counter64,
        ibPosaTcpTermMapErrCnts
            Counter64,
        ibPosaTcpTermInDiscardedPkts
            Counter64,
        ibPosaTcpTermOutDiscardedPkts
            Counter64,
        ibPosaTcpTermStatRowStatus
            RowStatus
     }

ibPosaTcpTermStatIndex OBJECT-TYPE
    SYNTAX Integer32 (1..64)
    MAX-ACCESS not-accessible
    STATUS current
    DESCRIPTION
        "The index of entity."
    ::= { ibPosaTcpTermStatEntry 1 }

ibPosaTcpTermStatIPType OBJECT-TYPE
    SYNTAX InetAddressType
    MAX-ACCESS read-create
    STATUS current
    DESCRIPTION
        "The type of Internet address.  And now it must be ipv4."
    ::= { ibPosaTcpTermStatEntry 2 }

ibPosaTcpTermStatIP OBJECT-TYPE
    SYNTAX InetAddress
    MAX-ACCESS read-create
    STATUS current
    DESCRIPTION
        "The IP address or the subnet of the statistics terminal(s).
        When the vlaue is a subnet, the statistics of all the
        terminals in the subnet will be added up.  And now it only
        supports ipv4."
    ::= { ibPosaTcpTermStatEntry 3 }

ibPosaTcpTermStatIPMask OBJECT-TYPE
    SYNTAX InetAddress
    MAX-ACCESS read-create
    STATUS current
    DESCRIPTION
        "The mask associated with the IP address or the subnet.  And
        now it only supports ipv4."
    ::= { ibPosaTcpTermStatEntry 4 }

ibPosaTcpTermRecvPkts OBJECT-TYPE
    SYNTAX Counter64
    MAX-ACCESS read-only
    STATUS current
    DESCRIPTION
        "The number of packets recieved from the POS terminal(s)."
    ::= { ibPosaTcpTermStatEntry 5 }

ibPosaTcpTermSendPkts OBJECT-TYPE
    SYNTAX Counter64
    MAX-ACCESS read-only
    STATUS current
    DESCRIPTION
        "The number of packets sent to the POS terminal(s)."
    ::= { ibPosaTcpTermStatEntry 6 }

ibPosaTcpTermErrPkts OBJECT-TYPE
    SYNTAX Counter64
    MAX-ACCESS read-only
    STATUS current
    DESCRIPTION
        "The number of inbound packets that contained errors."
    ::= { ibPosaTcpTermStatEntry 7 }

ibPosaTcpTermMapErrCnts OBJECT-TYPE
    SYNTAX Counter64
    MAX-ACCESS read-only
    STATUS current
    DESCRIPTION
        "The number of packets that are discarded because of mapping errors."
    ::= { ibPosaTcpTermStatEntry 8 }

ibPosaTcpTermInDiscardedPkts OBJECT-TYPE
    SYNTAX Counter64
    MAX-ACCESS read-only
    STATUS current
    DESCRIPTION
        "The number of inbound packets that are discarded when the incoming
        buffer is full."
    ::= { ibPosaTcpTermStatEntry 9 }

ibPosaTcpTermOutDiscardedPkts OBJECT-TYPE
    SYNTAX Counter64
    MAX-ACCESS read-only
    STATUS current
    DESCRIPTION
        "The number of outbound packets that are discarded because of link
        errors between the router and the POS terminal(s)."
    ::= { ibPosaTcpTermStatEntry 10 }

ibPosaTcpTermStatRowStatus OBJECT-TYPE
    SYNTAX RowStatus
    MAX-ACCESS read-create
    STATUS current
    DESCRIPTION
        "Operation status."
    ::= { ibPosaTcpTermStatEntry 11 }

ibPosaFcmConfTable OBJECT-TYPE
    SYNTAX      SEQUENCE OF IbPosaFcmConfEntry
    MAX-ACCESS   not-accessible
    STATUS       current
    DESCRIPTION
        "This table shows the configuration information of FCM (Fast Connection
        Modem) interfaces."
    ::= { ibPosaTables 9 }

ibPosaFcmConfEntry OBJECT-TYPE
    SYNTAX         IbPosaFcmConfEntry
    MAX-ACCESS     not-accessible
    STATUS         current
    DESCRIPTION
        "This entry shows the configuration information of FCM (Fast Connection
        Modem) interfaces."
    INDEX { ifIndex }
    ::= { ibPosaFcmConfTable 1 }

IbPosaFcmConfEntry ::= SEQUENCE  {
        ibPosaFcmNegoHookOff         Integer32,
        ibPosaFcmNegoSilence         Integer32,
        ibPosaFcmNegoScrmbBinary1    Integer32,
        ibPosaFcmNegoUnscrmbBinary1  Integer32,
        ibPosaFcmThresholdRlsdOff    Integer32,
        ibPosaFcmThresholdRlsdOn     Integer32,
        ibPosaFcmThresholdTxPower    Integer32,
        ibPosaFcmThresholdAnswerTone Integer32
        }

ibPosaFcmNegoHookOff     OBJECT-TYPE
    SYNTAX   Integer32 (100..6000)
    UNITS       "milliseconds"
    MAX-ACCESS      read-write
    STATUS          current
    DESCRIPTION
        "Delay time for hookoff."
    DEFVAL { 500 }
    ::= { ibPosaFcmConfEntry 1 }

ibPosaFcmNegoSilence     OBJECT-TYPE
    SYNTAX   Integer32 (0..3000)
    UNITS       "milliseconds"
    MAX-ACCESS      read-write
    STATUS          current
    DESCRIPTION
        "Silence time for modem negotiation."
    DEFVAL { 0 }
    ::= { ibPosaFcmConfEntry 2 }

ibPosaFcmNegoScrmbBinary1 OBJECT-TYPE
    SYNTAX   Integer32 (100..1500)
    UNITS       "milliseconds"
    MAX-ACCESS      read-write
    STATUS          current
    DESCRIPTION
        "Scramble-binary1 time for modem negotiation."
    DEFVAL { 250 }
    ::= { ibPosaFcmConfEntry 3 }

ibPosaFcmNegoUnscrmbBinary1 OBJECT-TYPE
    SYNTAX   Integer32 (300..1500)
    UNITS       "milliseconds"
    MAX-ACCESS      read-write
    STATUS          current
    DESCRIPTION
        "Unscramble-binary1 time for modem negotiation."
    DEFVAL { 400 }
    ::= { ibPosaFcmConfEntry 4 }

ibPosaFcmThresholdRlsdOff  OBJECT-TYPE
    SYNTAX   Integer32 (0..75)
    UNITS       "-dBm"
    MAX-ACCESS      read-write
    STATUS          current
    DESCRIPTION
        "RLSD (Received Line Signal Detect) off threshold for modem."
    DEFVAL { 48 }
    ::= { ibPosaFcmConfEntry 5 }

ibPosaFcmThresholdRlsdOn  OBJECT-TYPE
    SYNTAX   Integer32 (0..75)
    UNITS       "-dBm"
    MAX-ACCESS      read-write
    STATUS          current
    DESCRIPTION
        "RLSD (Received Line Signal Detect) on threshold for modem."
    DEFVAL { 43 }
    ::= { ibPosaFcmConfEntry 6 }

ibPosaFcmThresholdTxPower OBJECT-TYPE
    SYNTAX   Integer32 (1..42)
    UNITS       "-dBm"
    MAX-ACCESS      read-write
    STATUS          current
    DESCRIPTION
        "TX power for modem."
    DEFVAL { 10 }
    ::= { ibPosaFcmConfEntry 7 }

ibPosaFcmThresholdAnswerTone OBJECT-TYPE
    SYNTAX   Integer32 (1..42)
    UNITS       "-dBm"
    MAX-ACCESS      read-write
    STATUS          current
    DESCRIPTION
        "Answer tone level for modem."
    DEFVAL { 9 }
    ::= { ibPosaFcmConfEntry 8 }

ibPosaCallerStatTable OBJECT-TYPE
    SYNTAX      SEQUENCE OF IbPosaCallerStatEntry
    MAX-ACCESS   not-accessible
    STATUS       current
    DESCRIPTION
        "This table shows the statistics information of terminal according the
        caller-ID."
    ::= { ibPosaTables 10 }

ibPosaCallerStatEntry OBJECT-TYPE
    SYNTAX         IbPosaCallerStatEntry
    MAX-ACCESS     not-accessible
    STATUS         current
    DESCRIPTION
        "This table shows the statistics information of terminal according the
        caller-ID."
    INDEX { ibPosaCallerStatCallerID }
    ::= { ibPosaCallerStatTable 1 }

IbPosaCallerStatEntry ::= SEQUENCE  {
        ibPosaCallerStatCallerID
            OCTET STRING,
        ibPosaCallerRecvPkts
            Counter64,
        ibPosaCallerSendPkts
            Counter64,
        ibPosaCallerErrPkts
            Counter64,
        ibPosaCallerMapErrCnts
            Counter64,
        ibPosaCallerInDiscardedPkts
            Counter64,
        ibPosaCallerOutDiscardedPkts
            Counter64,
        ibPosaCallerStatRowStatus
            RowStatus
        }

ibPosaCallerStatCallerID OBJECT-TYPE
    SYNTAX OCTET STRING (SIZE (0..64))
    MAX-ACCESS accessible-for-notify
    STATUS current
    DESCRIPTION
        "The caller number."
    ::= { ibPosaCallerStatEntry 1 }

ibPosaCallerRecvPkts OBJECT-TYPE
    SYNTAX Counter64
    MAX-ACCESS read-only
    STATUS current
    DESCRIPTION
        "The number of packets recieved from the POS terminal(s)."
    ::= { ibPosaCallerStatEntry 2 }

ibPosaCallerSendPkts OBJECT-TYPE
    SYNTAX Counter64
    MAX-ACCESS read-only
    STATUS current
    DESCRIPTION
        "The number of packets sent to the POS terminal(s)."
    ::= { ibPosaCallerStatEntry 3 }

ibPosaCallerErrPkts OBJECT-TYPE
    SYNTAX Counter64
    MAX-ACCESS read-only
    STATUS current
    DESCRIPTION
        "The number of inbound packets that contained errors."
    ::= { ibPosaCallerStatEntry 4 }

ibPosaCallerMapErrCnts OBJECT-TYPE
    SYNTAX Counter64
    MAX-ACCESS read-only
    STATUS current
    DESCRIPTION
        "The number of packets that are discarded because of mapping errors."
    ::= { ibPosaCallerStatEntry 5 }

ibPosaCallerInDiscardedPkts OBJECT-TYPE
    SYNTAX Counter64
    MAX-ACCESS read-only
    STATUS current
    DESCRIPTION
        "The number of inbound packets that are discarded when the incoming
        buffer is full."
    ::= { ibPosaCallerStatEntry 6 }

ibPosaCallerOutDiscardedPkts OBJECT-TYPE
    SYNTAX Counter64
    MAX-ACCESS read-only
    STATUS current
    DESCRIPTION
        "The number of outbound packets that are discarded because of link
        errors between the router and the POS terminal(s)."
    ::= { ibPosaCallerStatEntry 7 }

ibPosaCallerStatRowStatus OBJECT-TYPE
    SYNTAX RowStatus
    MAX-ACCESS read-create
    STATUS current
    DESCRIPTION
        "Operation status."
    ::= { ibPosaCallerStatEntry 8 }

--
-- definition of ibPosaNiiStatTable
--

ibPosaNiiStatTable OBJECT-TYPE
    SYNTAX SEQUENCE OF IbPosaNiiStatEntry
    MAX-ACCESS not-accessible
    STATUS current
    DESCRIPTION
        "This table shows statistics on the Network International Identifier."
    ::= { ibPosaTables 11 }

ibPosaNiiStatEntry OBJECT-TYPE
    SYNTAX IbPosaNiiStatEntry
    MAX-ACCESS not-accessible
    STATUS current
    DESCRIPTION
        "This table shows statistics on the Network International Identifier."
    INDEX { ibPosaNiiStatIndex }
    ::= { ibPosaNiiStatTable 1 }

IbPosaNiiStatEntry ::=
    SEQUENCE {
        ibPosaNiiStatIndex
            OCTET STRING,
        ibPosaNiiRecvPkts
            Counter32,
        ibPosaNiiSendPkts
            Counter32,
        ibPosaNiiSuccessTradeCnt
            Counter32,
        ibPosaNiiTradeCnt
            Counter32
     }

ibPosaNiiStatIndex OBJECT-TYPE
    SYNTAX OCTET STRING (SIZE (4))
    MAX-ACCESS accessible-for-notify
    STATUS current
    DESCRIPTION
        "The index of entity."
    ::= { ibPosaNiiStatEntry 1 }

ibPosaNiiRecvPkts OBJECT-TYPE
    SYNTAX Counter32
    MAX-ACCESS read-only
    STATUS current
    DESCRIPTION
        "The number of packets received from the POS terminals."
    ::= { ibPosaNiiStatEntry 2 }

ibPosaNiiSendPkts OBJECT-TYPE
    SYNTAX Counter32
    MAX-ACCESS read-only
    STATUS current
    DESCRIPTION
        "The number of packets sent to the POS terminals."
    ::= { ibPosaNiiStatEntry 3 }

ibPosaNiiSuccessTradeCnt OBJECT-TYPE
    SYNTAX Counter32
    MAX-ACCESS read-only
    STATUS current
    DESCRIPTION
        "The number of successful transactions of the Network International Identifier."
    ::= { ibPosaNiiStatEntry 4 }

ibPosaNiiTradeCnt OBJECT-TYPE
    SYNTAX Counter32
    MAX-ACCESS read-only
    STATUS current
    DESCRIPTION
        "The number of all transactions of the Network International Identifier."
    ::= { ibPosaNiiStatEntry 5 }

--
-- definition of ibPosaE1StatTable
--

ibPosaE1StatTable OBJECT-TYPE
    SYNTAX SEQUENCE OF IbPosaE1StatEntry
    MAX-ACCESS not-accessible
    STATUS current
    DESCRIPTION
        "This table shows statistics on E1-controller."
    ::= { ibPosaTables 12 }

ibPosaE1StatEntry OBJECT-TYPE
    SYNTAX IbPosaE1StatEntry
    MAX-ACCESS not-accessible
    STATUS current
    DESCRIPTION
        "This table shows statistics on E1-controller."
    INDEX { ibPosaE1StatIndex }
    ::= { ibPosaE1StatTable 1 }

IbPosaE1StatEntry ::=
    SEQUENCE {
        ibPosaE1StatIndex
            Integer32,
        ibPosaE1DialCnt
            Counter32,
        ibPosaE1DialSuccess
            Counter32,
        ibPosaE1RecvPkts
            Counter32,
        ibPosaE1SendPkts
            Counter32,
        ibPosaE1ErrPkts
            Counter32,
        ibPosaE1MapErrCnts
            Counter32,
        ibPosaE1InDiscardedPkts
            Counter32,
        ibPosaE1OutDiscardedPkts
            Counter32
     }

ibPosaE1StatIndex OBJECT-TYPE
    SYNTAX Integer32 (1..2147483647)
    MAX-ACCESS not-accessible
    STATUS current
    DESCRIPTION
        "The index of entity."
    ::= { ibPosaE1StatEntry 1 }

ibPosaE1DialCnt OBJECT-TYPE
    SYNTAX Counter32
    MAX-ACCESS read-only
    STATUS current
    DESCRIPTION
        "The number of dialing  from the E1-controller."
    ::= { ibPosaE1StatEntry 2 }

ibPosaE1DialSuccess OBJECT-TYPE
    SYNTAX Counter32
    MAX-ACCESS read-only
    STATUS current
    DESCRIPTION
        "The number of successful dialing  from the E1-controller."
    ::= { ibPosaE1StatEntry 3 }

ibPosaE1RecvPkts OBJECT-TYPE
    SYNTAX Counter32
    MAX-ACCESS read-only
    STATUS current
    DESCRIPTION
        "The number of packets received from the POS terminals."
    ::= { ibPosaE1StatEntry 4 }

ibPosaE1SendPkts OBJECT-TYPE
    SYNTAX Counter32
    MAX-ACCESS read-only
    STATUS current
    DESCRIPTION
        "The number of packets sent to the POS terminals."
    ::= { ibPosaE1StatEntry 5 }

ibPosaE1ErrPkts OBJECT-TYPE
    SYNTAX Counter32
    MAX-ACCESS read-only
    STATUS current
    DESCRIPTION
        "The number of inbound packets that contained errors."
    ::= { ibPosaE1StatEntry 6 }

ibPosaE1MapErrCnts OBJECT-TYPE
    SYNTAX Counter32
    MAX-ACCESS read-only
    STATUS current
    DESCRIPTION
        "The number of packets that are discarded because of mapping errors."
    ::= { ibPosaE1StatEntry 7 }

ibPosaE1InDiscardedPkts OBJECT-TYPE
    SYNTAX Counter32
    MAX-ACCESS read-only
    STATUS current
    DESCRIPTION
        "The number of inbound packets that are discarded when the incoming
        buffer is full."
    ::= { ibPosaE1StatEntry 8 }

ibPosaE1OutDiscardedPkts OBJECT-TYPE
    SYNTAX Counter32
    MAX-ACCESS read-only
    STATUS current
    DESCRIPTION
        "The number of outbound packets that are discarded because of link
        errors between the router and the POS terminal."
    ::= { ibPosaE1StatEntry 9 }

--
-- traps defined
--

ibPosaTrap OBJECT IDENTIFIER ::= { ibPosa 3 }

ibPosaTrapPrex OBJECT IDENTIFIER ::= { ibPosaTrap 0 }

ibPosaServerStatusChange NOTIFICATION-TYPE
    OBJECTS { ibPosaServerEnable }
    STATUS current
    DESCRIPTION
        "This trap is generated when the POS function is started or stopped."
    ::= { ibPosaTrapPrex 1 }

ibPosaAppStateChange NOTIFICATION-TYPE
    OBJECTS { ibPosaAppID, ibPosaAppStateChangeObject }
    STATUS current
    DESCRIPTION
        "This trap is generated whenever the availability of application server
        changes."
    ::= { ibPosaTrapPrex 2 }

ibPosaTerminalHangUp NOTIFICATION-TYPE
    OBJECTS { ifIndex, ifDescr, ibPosaCallerStatCallerID }
    STATUS current
    DESCRIPTION
        "This trap is generated whenever the POS connection through a FCM (Fast
        Connection Modem) interface is hanged up by POS terminal."
    ::= { ibPosaTrapPrex 3 }

ibPosaFcmLinkNegoFailed NOTIFICATION-TYPE
    OBJECTS { ifIndex, ifDescr , ibPosaCallerStatCallerID }
    STATUS current
    DESCRIPTION
        "This trap is generated whenever the link layer negotiation is failed
        between the POS terminal and router through a FCM (Fast Connection
        Modem) interface."
    ::= { ibPosaTrapPrex 4 }

ibPosaFcmPhyNegoFailed NOTIFICATION-TYPE
    OBJECTS { ifIndex, ifDescr , ibPosaCallerStatCallerID }
    STATUS current
    DESCRIPTION
        "This trap is generated whenever the physical layer negotiation is failed
        between the POS terminal and router through a FCM (Fast Connection
        Modem) interface."
    ::= { ibPosaTrapPrex 5 }

ibPosaTcpConnectionExceed NOTIFICATION-TYPE
    OBJECTS { ibPosaTcpConnectionThreshold }
    STATUS current
    DESCRIPTION
        "This trap is generated whenever the number of connections exceeds the threshold."
    ::= { ibPosaTrapPrex 6 }

ibPosaFcmConnectionExceed NOTIFICATION-TYPE
    OBJECTS { ibPosaFcmConnectionThreshold }
    STATUS current
    DESCRIPTION
        "This trap is generated whenever the number of connections exceeds the threshold."
    ::= { ibPosaTrapPrex 7 }

ibPosaTcpTradeExceed NOTIFICATION-TYPE
    OBJECTS { ibPosaTcpTradeLimit, ibPosaTerminalID }
    STATUS current
    DESCRIPTION
        "This trap is generated whenever the number of trades in any TCP connect exceeds
        the limit."
    ::= { ibPosaTrapPrex 8 }

ibPosaTradeSuccessFalling NOTIFICATION-TYPE
    OBJECTS { ibPosaNiiStatIndex, ibPosaTradeSuccessFallingThreshold }
    STATUS current
    DESCRIPTION
        "This trap is generated whenever the transaction success rate of bank server is smaller than or equal to the threshold."
    ::= { ibPosaTrapPrex 9 }

ibPosaE1DialFalling NOTIFICATION-TYPE
    OBJECTS { ifIndex, ifDescr, ibPosaE1DialFallingThreshold }
    STATUS current
    DESCRIPTION
        "This trap is generated whenever the dialing success rate of E1-controller is smaller than or equal to the threshold."
    ::= { ibPosaTrapPrex 10 }

ibPosaFcmTradeAbnormal NOTIFICATION-TYPE
    OBJECTS { ifIndex, ifDescr, ibPosaCallerStatCallerID }
    STATUS current
    DESCRIPTION
        "This trap is generated whenever the dialing link is abnormal."
    ::= { ibPosaTrapPrex 11 }

ibPosaTrapObjects OBJECT IDENTIFIER ::= { ibPosaTrap 1 }

ibPosaAppStateChangeObject OBJECT-TYPE
    SYNTAX INTEGER
        {
        available(1),
        unavailable(2)
        }
    MAX-ACCESS accessible-for-notify
    STATUS current
    DESCRIPTION
        "This is a dummy MIB object referenced by the ibPosaAppStateChange trap.
        This object shows the availability changing of corresponding application
        server."
    ::= { ibPosaTrapObjects 1 }

END
