-- ============================================================================
-- Copyright (C) 2023 Intelbras S.A. All rights reserved.
--
-- Description: The MIB is extracted from draft-ietf-bfd-base-04.txt.
-- This file defines a portion of the Management Information Base (MIB) for use
-- with network management protocols in the Internet community. It describes
-- managed objects to configure or monitor Bi-Directional Forwarding Detection
-- on devices supporting this feature.
-- Reference:
-- Version: V1.8
-- History:
-- V1.0  2006-05-15 created by Huang Lina and Xu Qigang
-- V1.1  2014-01-20 modified by Wang Xingying
-- V1.2  2014-12-23 modified by Wang Xingying
-- V1.3  2016-03-12 modified by Guo Bin
-- V1.4  2020-08-13 Updated ibBfdGlobalObjects by Xu Kele
-- V1.5  2021-03-18 Added ibBfdTrapBindObjects, and update ibBfdSessStateDown, ibBfdSessStateUp by Xu Kele
-- V1.6  2021-10-16 Updated ibBfdTrapBindObjects, ibBfdSessStateDown, ibBfdSessStateUp by Xu Kele
-- V1.7  2022-08-04 Updated ibBfdSessTable, ibBfdSessStateUp, ibBfdSessStateDown by Tang Aibo
-- V1.8  2022-10-06 Updated ibBfdTrapBindObjects, ibBfdSessStateDown, and ibBfdSessStateUp by Zhou Xianwei
-- ============================================================================
IB-BFD-STD-MIB DEFINITIONS ::= BEGIN
IMPORTS
    MODULE-IDENTITY, OBJECT-TYPE,
    Unsigned32, Counter32, Counter64,
    NOTIFICATION-TYPE
        FROM SNMPv2-SMI                        -- [RFC2578]

    TEXTUAL-CONVENTION, TruthValue,
    TimeStamp,DisplayString
        FROM SNMPv2-TC

    InterfaceIndex, InterfaceIndexOrZero
        FROM IF-MIB

    InetAddress, InetAddressType, InetPortNumber
        FROM INET-ADDRESS-MIB                 -- [RFC3291]

    ibCommon
        FROM IB-OID-MIB;

ibBfdMIB MODULE-IDENTITY
    LAST-UPDATED "202210061100Z"  -- 06 Oct 2022 11:00:00 Beijing time
    ORGANIZATION
        "Intelbras S.A. Industria de Telecomunicacao Eletronica Brasileria."
    CONTACT-INFO
        ""
    DESCRIPTION
        "Bidirectional Forwarding Management Information Base."

    -- Revision history.
    REVISION "202210061100Z"  -- 06 Oct 2022 11:00:00 Beijing time
    DESCRIPTION
        "Updated ibBfdTrapBindObjects, ibBfdSessStateDown, and ibBfdSessStateUp."

    REVISION "202208041100Z"  -- 04 Aug 2022 11:00:00 Beijing time
    DESCRIPTION
        "Updated ibBfdSessTable, ibBfdSessStateDown, ibBfdSessStateUp."

    REVISION "202110161100Z"  -- 16 Oct 2021 11:00:00 Beijing time
    DESCRIPTION
        "Updated ibBfdTrapBindObjects, ibBfdSessStateDown, ibBfdSessStateUp."

    REVISION "202103181100Z"  -- 18 Mar 2021 11:00:00 Beijing time
    DESCRIPTION
        "Added ibBfdTrapBindObjects, and modified the objects of ibBfdSessStateDown and ibBfdSessStateUp."

    REVISION "202008131100Z"  -- 13 Aug 2020 11:00:00 Beijing time
    DESCRIPTION
        "Modified the objects of ibBfdGlobalObjects."

    REVISION "201412131200Z"  -- 13 Dec 2014 12:00:00 Beijing time
    DESCRIPTION
        "Modified the objects of ibBfdSessEntry."

    REVISION "201401171200Z"  -- 17 Jan 2014 12:00:00 Beijing time
    DESCRIPTION
        "Modified for bfd trap."

    REVISION "200605161200Z"  -- 08 May 2006 12:00:00 Beijing time
    DESCRIPTION
         "The first version."

::= { ibCommon 72 }

-- Top level components of this MIB module.

ibBfdNotifications OBJECT IDENTIFIER ::= { ibBfdMIB 0 }
ibBfdObjects       OBJECT IDENTIFIER ::= { ibBfdMIB 1 }
ibBfdConformance   OBJECT IDENTIFIER ::= { ibBfdMIB 2 }
ibBfdGlobalObjects OBJECT IDENTIFIER ::= { ibBfdObjects 1 }
ibBfdTrapBindObjects   OBJECT IDENTIFIER ::= { ibBfdMIB 3 }

-- Textual Conventions

BfdSessIndexTC ::= TEXTUAL-CONVENTION
    DISPLAY-HINT  "d"
    STATUS        current
    DESCRIPTION
        "An index used to uniquely identify BFD sessions."
    SYNTAX Unsigned32 (0..4294967295)

BfdInterval ::=   TEXTUAL-CONVENTION
    DISPLAY-HINT  "d"
    STATUS        current
    DESCRIPTION
        "A time interval delay in microseconds, which is used by the BFD."
    SYNTAX        Unsigned32 (1..4294967295)

BfdDiag ::=       TEXTUAL-CONVENTION
    STATUS        current
    DESCRIPTION
        "The diagnostic code is used by the BFD specifying the local
         system's reason for the last session state change, and must
         be initialized to zero(No Diagnostic).

         The 'noDiagnostic' means the session keeps state up.
         The 'controlDetectionTimeExpired' indicates the reason the session
         enters state down from state up is that the control detection time
         expires.
         The 'echoFunctionFailed' indicates the reason the session
         enters state down from state up is that Echo Function fails.
         The 'neighborSignaledSessionDown' indicates the reason the session
         enters state down from state up is that neighbor signals session Down.
         The 'forwardingPlaneReset' indicates the reason the session
         enters state down from state up is that the Forwarding Plane resets.
         The 'pathDown' indicates the reason the session
         enters state down from state up is that the path state is down.
         The 'concatenatedPathDown' indicates the reason the session
         enters state down from state up is that the concatenated path state
         is down.
         The 'administrativelyDown' indicates the reason the session
         enters state down from state up is that the session is kept
         administratively down by entering the AdminDown state.
         The 'reverseConcatenatedPathDown' indicates the reason the session
         enters state down from state up is that reverse concatenated path
         state is down."

    SYNTAX INTEGER { noDiagnostic(1),
                     controlDetectionTimeExpired(2),
                     echoFunctionFailed(3),
                     neighborSignaledSessionDown(4),
                     forwardingPlaneReset(5),
                     pathDown(6),
                     concatenatedPathDown(7),
                     administrativelyDown(8),
                     reverseConcatenatedPathDown(9)
    }

IbBfdBindVpnInstanceName ::= TEXTUAL-CONVENTION
    DISPLAY-HINT "31a"
    STATUS        current
    DESCRIPTION
         "An identifier that is assigned to each MPLS/BGP VPN and
         is used to uniquely identify it.  This is assigned by the
         system operator or NMS and SHOULD be unique throughout
         the MPLS domain.  If this is the case, then this identifier
         can then be used at any LSR within a specific MPLS domain
         to identify this MPLS/BGP VPN.  It may also be possible to
         preserve the uniqueness of this identifier across MPLS
         domain boundaries, in which case this identifier can then
         be used to uniquely identify MPLS/BGP VPNs on a more global
         basis.  This object MAY be set to the VPN ID as defined in
         RFC 2685."
    REFERENCE
        "RFC 2685 Fox B., et al, 'Virtual Private
         Networks Identifier', September 1999."
   SYNTAX OCTET STRING (SIZE (0..31))

IbBfdSessionName ::= TEXTUAL-CONVENTION
    DISPLAY-HINT "64a"
    STATUS       current
    DESCRIPTION
        "A name used to uniquely identify BFD sessions."
    SYNTAX  OCTET STRING(SIZE (0..64))

--  BFD General Variables

--  These variables apply globally to the Router's BFD Process.
ibBfdVersionNumber OBJECT-TYPE
    SYNTAX      Unsigned32
    MAX-ACCESS  read-only
    STATUS      current
    DESCRIPTION
        "It indicates the BFD session's current version number."
    REFERENCE
        "BFD Version 1 (draft-ietf-bfd-base-04.txt)"
    DEFVAL { 1 }
    ::= { ibBfdGlobalObjects 1 }

ibBfdSysInitMode OBJECT-TYPE
    SYNTAX      INTEGER { active(1), passive(2)}
    MAX-ACCESS  read-write
    STATUS      current
    DESCRIPTION
        "A system may take either an active role or a passive role in
         session initialization. A system taking the active role must
         send BFD control packets for a particular session, regardless
         of whether it has received any BFD packets for that session.
         A system taking the passive role must not begin sending BFD
         packets for a particular session until it has received a BFD
         packet for that session, and thus has learned the remote system's
         discriminator value."
    DEFVAL { active }
    ::= { ibBfdGlobalObjects 2 }

ibBfdSessNotificationsEnable OBJECT-TYPE
    SYNTAX        TruthValue
    MAX-ACCESS    read-write
    STATUS        current
    DESCRIPTION
        "This variable enables the emission of ibBfdSessStateUp
         ibBfdSessStateDown and ibBfdSessReachLimit notifications
         if this variable is set to true(1); otherwise these notifications
         are not emitted."
    DEFVAL { false }
    ::= { ibBfdGlobalObjects 3 }

ibBfdSessNumberLimit OBJECT-TYPE
    SYNTAX        Unsigned32 (1..4294967295)
    MAX-ACCESS    read-only
    STATUS        current
    DESCRIPTION
        "This variable is the active session limit of this device."
    ::= { ibBfdGlobalObjects 4 }

ibBfdSessionsActive OBJECT-TYPE
    SYNTAX        Unsigned32
    MAX-ACCESS    read-only
    STATUS        current
    DESCRIPTION
        "This variable is the active session count of this device."
    ::= { ibBfdGlobalObjects 5 }


--  BFD Interface Table
--  The BFD Interface Table defines BFD interface specific information.

ibBfdIfTable OBJECT-TYPE
    SYNTAX      SEQUENCE OF IbBfdIfEntry
    MAX-ACCESS  not-accessible
    STATUS      current
    DESCRIPTION
        "This Table describes the BFD interface specific information."
    ::= { ibBfdObjects 2 }

ibBfdIfEntry OBJECT-TYPE
    SYNTAX      IbBfdIfEntry
    MAX-ACCESS  not-accessible
    STATUS      current
    DESCRIPTION
        "This Entry describes the BFD interface specific information."
    INDEX { ibBfdIfIndex }
    ::= { ibBfdIfTable 1 }

IbBfdIfEntry ::= SEQUENCE{
        ibBfdIfIndex                      InterfaceIndex,
        ibBfdIfDesiredMinTxInterval       BfdInterval,
        ibBfdIfDesiredMinRxInterval       BfdInterval,
        ibBfdIfDetectMult                 Unsigned32,
        ibBfdIfAuthType                   INTEGER
    }

ibBfdIfIndex OBJECT-TYPE
    SYNTAX        InterfaceIndex
    MAX-ACCESS    accessible-for-notify
    STATUS        current
    DESCRIPTION
        "This variable contains an index that represents a
         unique BFD interface on this device."
    ::= { ibBfdIfEntry 1 }

ibBfdIfDesiredMinTxInterval OBJECT-TYPE
    SYNTAX        BfdInterval
    MAX-ACCESS    read-write
    STATUS        current
    DESCRIPTION
        "This variable defines the minimum interval, in
         microseconds, that the interface would like to use when
         transmitting BFD Control packets."
    ::= { ibBfdIfEntry 2 }

ibBfdIfDesiredMinRxInterval OBJECT-TYPE
    SYNTAX        BfdInterval
    MAX-ACCESS    read-write
    STATUS        current
    DESCRIPTION
        "This variable defines the minimum interval, in,
         microseconds, between received  BFD Control packets the
         local system is capable of supporting."
    ::= { ibBfdIfEntry 3 }

ibBfdIfDetectMult OBJECT-TYPE
    SYNTAX        Unsigned32
    MAX-ACCESS    read-write
    STATUS        current
    DESCRIPTION
        "The desired detect time multiplier for BFD control packets.
         The negotiated control packet transmission interval, multiplied
         by this variable, will be the detection time for this session
         (as seen by the remote system.)  The variable must be a
         nonzero integer."
    ::= { ibBfdIfEntry 4 }

ibBfdIfAuthType OBJECT-TYPE
    SYNTAX        INTEGER {
                            none(1),
                            simple(2),
                            md5(3),
                            mmd5(4),
                            sha1(5),
                            msha1(6)
    }
    MAX-ACCESS    read-only
    STATUS        current
    DESCRIPTION
        "The Authentication Type used for this interface. This
         field is valid only when the Authentication Present bit is set.

         The 'none' indicates the session doesn't support
         authentication.
         The 'simple' indicates the session supports simple
         password authentication.
         The 'md5' indicates the session supports Keyed MD5
         authentication.
         The 'mmd5' indicates the session supports
         Meticulous Keyed MD5 authentication.
         The 'sha1' indicates the session supports Keyed SHA1
         authentication.
         The 'msha1' indicates the session supports
         Meticulous Keyed SHA1 authentication."
    DEFVAL { none }
    ::= { ibBfdIfEntry 5 }

--  BFD Session Table
--  The BFD Session Table defines BFD session specific information.

ibBfdSessTable OBJECT-TYPE
    SYNTAX        SEQUENCE OF IbBfdSessEntry
    MAX-ACCESS    not-accessible
    STATUS        current
    DESCRIPTION
        "This table describes the BFD sessions."
    REFERENCE
        "BFD Version 1 (draft-ietf-bfd-base-04.txt)"
    ::= { ibBfdObjects 3 }

ibBfdSessEntry OBJECT-TYPE
    SYNTAX        IbBfdSessEntry
    MAX-ACCESS    not-accessible
    STATUS        current
    DESCRIPTION
        "This Entry describes the BFD sessions."
    INDEX { ibBfdSessIndex }
    ::= { ibBfdSessTable 1 }

IbBfdSessEntry ::= SEQUENCE {
        ibBfdSessIndex                    BfdSessIndexTC,
        ibBfdSessIfIndex                  InterfaceIndexOrZero,
        ibBfdSessAppSupportId             BITS,
        ibBfdSessLocalDiscr               Unsigned32,
        ibBfdSessRemoteDiscr              Unsigned32,
        ibBfdSessDstPort                  InetPortNumber,
        ibBfdSessOperMode                 INTEGER,
        ibBfdSessAddrType                 InetAddressType,
        ibBfdSessLocalAddr                InetAddress,
        ibBfdSessRemoteAddr               InetAddress,
        ibBfdSessLocalDiag                BfdDiag,
        ibBfdSessState                    INTEGER,
        ibBfdSessControlPlanIndepFlag     TruthValue,
        ibBfdSessAuthFlag                 TruthValue,
        ibBfdSessDemandModeFlag           TruthValue
    }

ibBfdSessIndex OBJECT-TYPE
    SYNTAX        BfdSessIndexTC
    MAX-ACCESS    accessible-for-notify
    STATUS        current
    DESCRIPTION
        "This variable contains an index which represents a
         unique BFD session on this device."
    ::= { ibBfdSessEntry 1 }

ibBfdSessIfIndex  OBJECT-TYPE
    SYNTAX        InterfaceIndexOrZero
    MAX-ACCESS    read-only
    STATUS        current
    DESCRIPTION
        "This variable contains an interface's index under which the BFD
         session runs. If ibBfdSessIfIndex is equal to 0, it means that
         the BFD session does not specify an interface."
    ::= { ibBfdSessEntry 2 }

ibBfdSessAppSupportId OBJECT-TYPE
    SYNTAX        BITS {none(0), ospf(1), isis(2), bgp(3), mpls(4)}
    MAX-ACCESS    read-only
    STATUS        current
    DESCRIPTION
        "This variable contains an ID used to indicate
         a local application which owns or maintains this
         BFD session. Note, a BFD session can support several route
         protocols. This is a bit-map of possible conditions.
         The corresponding bit positions are:
         |0        |none        |
         |1        |ospf        |
         |2        |isis        |
         |3        |bgp         |
         |4        |mpls        |
        "
    ::= { ibBfdSessEntry 3 }

ibBfdSessLocalDiscr OBJECT-TYPE
    SYNTAX        Unsigned32 (1..4294967295)
    MAX-ACCESS    read-only
    STATUS        current
    DESCRIPTION
        "This variable defines the local discriminator for this BFD
         session, used to uniquely identify it."
    ::= { ibBfdSessEntry 4 }

ibBfdSessRemoteDiscr OBJECT-TYPE
    SYNTAX        Unsigned32 (1..4294967295)
    MAX-ACCESS    read-only
    STATUS        current
    DESCRIPTION
        "This variable defines the session discriminator chosen
         by the remote system for this BFD session."
    ::= { ibBfdSessEntry 5 }

ibBfdSessDstPort OBJECT-TYPE
    SYNTAX        InetPortNumber
    MAX-ACCESS    read-only
    STATUS        current
    DESCRIPTION
        "The UDP Port for BFD. The default value is the
         well-known value for this port."
    REFERENCE
        "BFD Version 1 (draft-ietf-bfd-base-04.txt)"
    DEFVAL { 3784 }
    ::= { ibBfdSessEntry 6 }

ibBfdSessOperMode OBJECT-TYPE
    SYNTAX   INTEGER{
                         asynchModeWOEchoFun(1),
                         demandModeWOEchoFunction(2),
                         asyncModeWEchoFun(3),
                         demandModeWEchoFunction(4)
    }
    MAX-ACCESS   read-only
    STATUS   current
    DESCRIPTION
        "This variable defines current operating mode that BFD
         session is running in.

         The primary mode which the BFD session runs in is known as
         Asynchronous mode.  In this mode, the systems periodically
         send BFD Control packets to one another, and if a number of
         those packets in a row are not received by the other system,
         the session is declared to be down.

         The second mode is known as Demand mode.  In this mode, it is
         assumed that each system has an independent way of verifying
         that it has connectivity to the other system.  Once a BFD
         session is established, the systems stop sending BFD Control
         packets, except when either system feels the need to verify
         connectivity explicitly, in which case a short sequence of BFD
         Control packets is sent, and then the protocol quiesces.

         An adjunct to both modes is the Echo function.  When the Echo
         function is active, a stream of BFD Echo packets is transmitted
         in such a way as to have the other system loop them back through
         its forwarding path. If a number of packets of the echoed data
         stream are not received, the session is declared to be down.
         The Echo function may be used with either Asynchronous or
         Demand modes.

         The 'asynchModeWOEchoFun' indicates this BFD session operates in
         the Asynchronous mode, and doesn't support the Echo Function.

         The 'demandModeWOEchoFunction' indicates this BFD session operates in
         the Demand mode, and doesn't support the Echo Function.

         The 'asyncModeWEchoFun' indicates this BFD session operates in
         the Asynchronous mode, and also supports the Echo Function.

         The 'demandModeWEchoFunction' indicates this BFD session operates in
         the Demand mode, and also supports the Echo Function."
    DEFVAL { asynchModeWOEchoFun }
    ::= { ibBfdSessEntry 7 }

ibBfdSessAddrType  OBJECT-TYPE
    SYNTAX        InetAddressType
    MAX-ACCESS    read-only
    STATUS        current
    DESCRIPTION
        "This object defines IP address type of the interface
         associated with this BFD session.

         Only values unknown(0), ipv4(1) or ipv6(2)
         have to be supported.

         A value of unknown(0) is allowed only when
         the outgoing interface is of type point-to-point, or
         when the BFD session is not associated with a specific
         interface.

         If any other unsupported values are attempted in a set
         operation, the agent must return an inconsistentValue
         error."
    ::= { ibBfdSessEntry 8 }

ibBfdSessLocalAddr OBJECT-TYPE
    SYNTAX        InetAddress
    MAX-ACCESS    read-only
    STATUS        current
    DESCRIPTION
        "This variable defines IP address of the local interface
         from which the BFD packets is transmitted.
         It can also be used to enabled BFD on a specific
         interface. The value is set to zero when BFD session is not
         associated with a specific interface."
    ::= { ibBfdSessEntry 9 }

ibBfdSessRemoteAddr OBJECT-TYPE
    SYNTAX        InetAddress
    MAX-ACCESS    read-only
    STATUS        current
    DESCRIPTION
        "This variable defines IP address of the remote interface
         from which the BFD packets is transmitted.
         It can also be used to enabled BFD on a specific
         interface. The value is set to zero when BFD session is not
         associated with a specific interface."
    ::= { ibBfdSessEntry 10 }

ibBfdSessLocalDiag OBJECT-TYPE
    SYNTAX        BfdDiag
    MAX-ACCESS    read-only
    STATUS        current
    DESCRIPTION
        "The BFD diagnostic code for the BFD session was down with the
         neighbor. If no such event happens this object contains a zero
         value."
    DEFVAL { noDiagnostic }
    ::= { ibBfdSessEntry 11 }

ibBfdSessState OBJECT-TYPE
    SYNTAX        INTEGER {
                           adminDown(0),
                           down(1),
                           init(2),
                           up(3)
    }
    MAX-ACCESS    read-only
    STATUS        current
    DESCRIPTION
        "The state of the running BFD session.

         There are three states through which a session normally
         proceeds, two for establishing a session (Init and Up)
         and one for tearing down a session (Down.)  This allows
         a three-way handshake for both session establishment and
         session teardown (assuring that both systems are aware of
         all session state changes.)  A fourth state (AdminDown)
         exists so that a session can be administratively put down
         indefinitely.

         The Down state means that the session is down (or has just been
         created.) A session remains in Down state until the remote
         system indicates that it agrees that the session is down by
         sending a BFD Control packet with the State field set to
         anything other than Up.  If that packet signals Down state,
         the session advances to Init state;  if that packet signals
         Init state, the session advances to Up state.

         Init state means that the remote system is 0communicating,
         and the local system desires to bring the session up, but
         the remote system does not yet realize it.  A session will
         remain in Init state until either a BFD Control Packet is
         received that is signaling Init or Up state (in which case
         the session advances to Up state) or until the detection time
         expires, meaning that communication with the remote system
         has been lost (in which case the session advances to Down
         state.)

         Up state means that the BFD session has successfully been
         established, and implies that connectivity between the systems
         is working.  The session will remain in the Up state until either
         connectivity fails, or the session is taken down administratively.
         If either the remote system signals Down state, or the detection
         time expires, the session advances to Down state.

         AdminDown state means that the session is being held
         administratively down.  This causes the remote system to enter
         Down state, and remain there until the local system exits
         AdminDown state."
    DEFVAL { down }
    ::= { ibBfdSessEntry 12 }

ibBfdSessControlPlanIndepFlag OBJECT-TYPE
    SYNTAX        TruthValue
    MAX-ACCESS    read-only
    STATUS        current
    DESCRIPTION
        "This variable indicates whether the local system
         can continue to work while the control plane is out
         of work. Specifically, it is set to true(1) if the
         local system is independent of the control plane. Otherwise,
         the value is set to false(2)"
    DEFVAL { true }
    ::= { ibBfdSessEntry 13 }

ibBfdSessAuthFlag OBJECT-TYPE
    SYNTAX        TruthValue
    MAX-ACCESS    read-only
    STATUS        current
    DESCRIPTION
        "This variable indicates that the local system wants
         to use Authentication. Specifically, it is set
         to true(1) if the local system wishes the session
         to be authenticated or false(2) if not."
    DEFVAL { false }
    ::= { ibBfdSessEntry 14 }

ibBfdSessDemandModeFlag OBJECT-TYPE
    SYNTAX        TruthValue
    MAX-ACCESS    read-only
    STATUS        current
    DESCRIPTION
        "This variable indicates that the local system wants
         to use Demand mode. Specifically, it is set
         to true(1) if the local system wishes to use
         Demand mode or false(2) if not"
    DEFVAL { false }
    ::= { ibBfdSessEntry 15 }

-- BFD Session State Table

ibBfdSessStatTable OBJECT-TYPE
    SYNTAX        SEQUENCE OF IbBfdSessStatEntry
    MAX-ACCESS    not-accessible
    STATUS        current
    DESCRIPTION
        "The table defines BFD session state."
    ::= { ibBfdObjects 4 }

ibBfdSessStatEntry OBJECT-TYPE
    SYNTAX        IbBfdSessStatEntry
    MAX-ACCESS    not-accessible
    STATUS        current
    DESCRIPTION
        "An entry in this table is created by a BFD-enabled node for
         every BFD Session. It defines BFD session statistics."
    AUGMENTS    { ibBfdSessEntry }
    ::= { ibBfdSessStatTable 1 }

IbBfdSessStatEntry ::= SEQUENCE {
        ibBfdSessStatPktInHC             Counter64,
        ibBfdSessStatPktOutHC            Counter64,
        ibBfdSessStatDownCount           Counter32,
        ibBfdSessStatPktDiscard          Counter64,
        ibBfdSessStatPktLost             Counter64
    }


ibBfdSessStatPktInHC OBJECT-TYPE
    SYNTAX        Counter64
    MAX-ACCESS    read-only
    STATUS        current
    DESCRIPTION
        "The total number of BFD messages received by this BFD
         session."
    ::= { ibBfdSessStatEntry 1 }

ibBfdSessStatPktOutHC OBJECT-TYPE
    SYNTAX        Counter64
    MAX-ACCESS    read-only
    STATUS        current
    DESCRIPTION
        "The total number of BFD messages sent by this BFD session."
    ::= { ibBfdSessStatEntry 2 }

ibBfdSessStatDownCount OBJECT-TYPE
    SYNTAX         Counter32
    MAX-ACCESS     read-only
    STATUS         current
    DESCRIPTION
        "The number of times this session has gone into the Down
         state since the router last rebooted."
    ::= { ibBfdSessStatEntry 3 }

ibBfdSessStatPktDiscard OBJECT-TYPE
    SYNTAX        Counter64
    MAX-ACCESS    read-only
    STATUS        current
    DESCRIPTION
        "The number of  packets the local system has discarded
         since the router last rebooted."
    ::= { ibBfdSessStatEntry 4 }

ibBfdSessStatPktLost OBJECT-TYPE
    SYNTAX        Counter64
    MAX-ACCESS    read-only
    STATUS        current
    DESCRIPTION
        "The number of packets the local system has failed to transmit
         since the router last rebooted."
    ::= { ibBfdSessStatEntry 5 }


-- BFD Session Performance Table

ibBfdSessPerfTable OBJECT-TYPE
    SYNTAX        SEQUENCE OF IbBfdSessPerfEntry
    MAX-ACCESS    not-accessible
    STATUS        current
    DESCRIPTION
        "The table defines BFD session performance."
    ::= { ibBfdObjects 5 }

ibBfdSessPerfEntry OBJECT-TYPE
    SYNTAX        IbBfdSessPerfEntry
    MAX-ACCESS    not-accessible
    STATUS        current
    DESCRIPTION
        "An entry in this table is created by a BFD-enabled node for
         every BFD session. It defines BFD Session performance."
    AUGMENTS    { ibBfdSessEntry }
    ::= { ibBfdSessPerfTable 1 }

IbBfdSessPerfEntry ::= SEQUENCE {
        ibBfdSessPerfCreatTime       TimeStamp,
        ibBfdSessPerfLastUpTime      TimeStamp,
        ibBfdSessPerfLastDownTime    TimeStamp
    }

ibBfdSessPerfCreatTime OBJECT-TYPE
    SYNTAX        TimeStamp
    MAX-ACCESS    read-only
    STATUS        current
    DESCRIPTION
        "The value of sysUpTime when the session was created. If no such
         create event exists this object contains a zero value."
    ::= { ibBfdSessPerfEntry 1 }

ibBfdSessPerfLastUpTime OBJECT-TYPE
    SYNTAX        TimeStamp
    MAX-ACCESS    read-only
    STATUS        current
    DESCRIPTION
        "The value of sysUpTime when the last time communication was lost.
         If no such up event exists this variable contains a zero value."
    ::= { ibBfdSessPerfEntry 2 }

ibBfdSessPerfLastDownTime OBJECT-TYPE
    SYNTAX        TimeStamp
    MAX-ACCESS    read-only
    STATUS        current
    DESCRIPTION
        "The value of sysUpTime when the last time communication was lost
         with the neighbor. If no such event exist this variable contains
         a zero value."
    ::= { ibBfdSessPerfEntry 3 }


-- Notification Configuration

ibBfdSessName OBJECT-TYPE
    SYNTAX        IbBfdSessionName
    MAX-ACCESS    accessible-for-notify
    STATUS        current
    DESCRIPTION
        "A name used to uniquely identify BFD sessions."
    ::= { ibBfdTrapBindObjects 1 }

ibBfdVpnInstanceName OBJECT-TYPE
    SYNTAX        IbBfdBindVpnInstanceName
    MAX-ACCESS    accessible-for-notify
    STATUS        current
    DESCRIPTION
        "The human-readable name of this VPN.  This MAY
         be equivalent to the [RFC2685] VPN-ID, but may
         also vary.  If it is set to the VPN ID, it MUST
         be equivalent to the value of mplsL3VpnVrfVpnId.
         It is strongly recommended that all sites supporting
         VRFs that are part of the same VPN use the same
         naming convention for VRFs as well as the same VPN
         ID."
    REFERENCE
        "[RFC2685]"
    ::= { ibBfdTrapBindObjects 2 }

ibBfdLocalAddr OBJECT-TYPE
    SYNTAX        DisplayString
    MAX-ACCESS    accessible-for-notify
    STATUS        current
    DESCRIPTION
        "This variable defines IP address of the local interface
         from which the BFD packets is transmitted.
         It can also be used to enabled BFD on a specific
         interface. The value is set to zero when BFD session is not
         associated with a specific interface."
    ::= { ibBfdTrapBindObjects 3 }

ibBfdRemoteAddr OBJECT-TYPE
    SYNTAX        DisplayString
    MAX-ACCESS    accessible-for-notify
    STATUS        current
    DESCRIPTION
        "This variable defines IP address of the local interface
         from which the BFD packets is transmitted.
         It can also be used to enabled BFD on a specific
         interface. The value is set to zero when BFD session is not
         associated with a specific interface."
    ::= { ibBfdTrapBindObjects 4 }

ibBfdIfName OBJECT-TYPE
    SYNTAX        DisplayString (SIZE (0..255))
    MAX-ACCESS    accessible-for-notify
    STATUS        current
    DESCRIPTION
        "It is the name of the binding interface in the BFD session."
    ::= { ibBfdTrapBindObjects 5 }

ibBfdSessType OBJECT-TYPE
    SYNTAX        INTEGER {
                            static(1),
                            dynamic(2)
    }
    MAX-ACCESS    accessible-for-notify
    STATUS        current
    DESCRIPTION
        "The type of the BFD session."
    ::= { ibBfdTrapBindObjects 6 }

ibBfdVrfIndex OBJECT-TYPE
    SYNTAX        Unsigned32 (0..4294967295)
    MAX-ACCESS    accessible-for-notify
    STATUS        current
    DESCRIPTION
        "The index of the VPN interface."
    ::= { ibBfdTrapBindObjects 7 }

ibBfdDiscrAuto OBJECT-TYPE
    SYNTAX        TruthValue
    MAX-ACCESS    accessible-for-notify
    STATUS        current
    DESCRIPTION
        "Describe whether the discriminator can be auto allocated.
         It is set to true(1) when enabled and false(2) when not enabled"
    DEFVAL { false }
    ::= { ibBfdTrapBindObjects 8 }

ibBfdSessVsiPeerAddr OBJECT-TYPE
    SYNTAX        DisplayString (SIZE (0..255))
    MAX-ACCESS    accessible-for-notify
    STATUS        current
    DESCRIPTION
        "It is the peer ip of VSI."
    ::= { ibBfdTrapBindObjects 9 }

ibBfdSessVsiName OBJECT-TYPE
    SYNTAX        DisplayString (SIZE (0..255))
    MAX-ACCESS    accessible-for-notify
    STATUS        current
    DESCRIPTION
        "It is the name of VSI."
    ::= { ibBfdTrapBindObjects 10 }

ibBfdSessDefaultIp OBJECT-TYPE
    SYNTAX        TruthValue
    MAX-ACCESS    accessible-for-notify
    STATUS        current
    DESCRIPTION
        "BFD session use default multicast IP as the detect peer ip.
        When set to true(1), the multicast address is not used as the peer
        IP address, and when set to false(2), the multicast address is used
        as the peer IP address"
    ::= { ibBfdTrapBindObjects 11 }

ibBfdSessNextHop OBJECT-TYPE
    SYNTAX        DisplayString (SIZE (0..255))
    MAX-ACCESS    accessible-for-notify
    STATUS        current
    DESCRIPTION
        "It is the next hop of the BFD session."
    ::= { ibBfdTrapBindObjects 12 }

ibBfdSessPWSecondaryFlag OBJECT-TYPE
    SYNTAX        INTEGER {
                            masterPW(1),
                            secondaryPW(2),
                            noPW(3)
    }
    MAX-ACCESS    accessible-for-notify
    STATUS        current
    DESCRIPTION
        "The role of the PW bound with BFD session."
    ::= { ibBfdTrapBindObjects 13 }

ibBfdSessVcId OBJECT-TYPE
    SYNTAX        Unsigned32 (0..4294967295)
    MAX-ACCESS    accessible-for-notify
    STATUS        current
    DESCRIPTION
        "It is the ID of VC."
    ::= { ibBfdTrapBindObjects 14 }

ibBfdLocalDiscr OBJECT-TYPE
    SYNTAX        Unsigned32 (1..4294967295)
    MAX-ACCESS    accessible-for-notify
    STATUS        current
    DESCRIPTION
        "This variable defines the local discriminator that uniquely identifies a BFD
         session."
    ::= { ibBfdTrapBindObjects 15 }

ibBfdSessStateChange NOTIFICATION-TYPE
    OBJECTS       { ibBfdSessIfIndex,
                    ibBfdSessIndex,
                    ibBfdSessState
    }
    STATUS        current
    DESCRIPTION
        "A notification sent when a session changes
         state, entering state up or entering state down.
         The session will enter state up finishing three times handshakes
         , and will enter state down when the communication path is out
         of work.

         When the ibBfdSessState's value is state up, the session enters
         state up, and the session enters state down when the
         ibBfdSessState's value is state down.

         The ibBfdSessIfIndex contains an interface's index under which
         the BFD session runs.

         The ibBfdSessIndex contains an index which represents a
         unique BFD session on this device.

         The ibBfdSessState is the state of the running BFD session.
         "
    ::= { ibBfdNotifications 1 }

ibBfdSessAuthFail NOTIFICATION-TYPE
    OBJECTS       { ibBfdIfIndex
    }
    STATUS        current
    DESCRIPTION
        "A notification sent when receiving a session
         with an authentication fail.

         The ibBfdIfIndex is an index which represents a unique BFD
         interface on this device.
         "
    ::= { ibBfdNotifications 2 }

ibBfdSessStateUp NOTIFICATION-TYPE
    OBJECTS       { ibBfdSessIfIndex,
                    ibBfdSessIndex,
                    ibBfdSessState,
                    ibBfdSessName,
                    ibBfdVpnInstanceName,
                    ibBfdLocalAddr,
                    ibBfdRemoteAddr,
                    ibBfdIfName,
                    ibBfdSessLocalDiag,
                    ibBfdSessType,
                    ibBfdVrfIndex,
                    ibBfdDiscrAuto,
                    ibBfdSessVsiPeerAddr,
                    ibBfdSessVsiName,
                    ibBfdSessDefaultIp,
                    ibBfdSessNextHop,
                    ibBfdSessPWSecondaryFlag,
                    ibBfdSessVcId,
                    ibBfdLocalDiscr
    }
    STATUS        current
    DESCRIPTION
        "A notification sent when a session changes state to up.

         The session will enter state up finishing three times handshakes.

         The ibBfdSessIfIndex contains an interface's index under which
         the BFD session runs.

         The ibBfdSessIndex contains an index which represents a
         unique BFD session on this device.

         The ibBfdSessState is the state of the running BFD session.

         The ibBfdSessName is the name of the running BFD session.

         The ibBfdVpnInstanceName contains a VPN's name under which
         the BFD session runs.

         The ibBfdLocalAddr contains an IP address of the local interface
         from which the BFD packets is transmitted.

         The ibBfdRemoteAddr contains an IP address of the remote interface
         from which the BFD packets is transmitted.

         The ibBfdIfName is the name of the binding interface in the BFD session.

         The ibBfdSessLocalDiag is the BFD diagnostic code for the BFD session was down with the
         neighbor.

         The ibBfdSessType is the type of the BFD session.

         The ibBfdVrfIndex is the index of the VPN interface.

         The ibBfdDiscrAuto describes whether the discriminator can be auto allocated.

         The ibBfdSessVsiPeerAddr is the peer ip of VSI.

         The ibBfdSessVsiName is the name of VSI.

         The ibBfdSessDefaultIp describes whether BFD session use default multicast IP as the detect peer ip.

         The ibBfdSessNextHop is the next hop of the BFD session for LSP.

         The ibBfdSessPWSecondaryFlag is the role of the PW bound with BFD session.

         The ibBfdSessVcId is the ID of VC.

         The ibBfdLocalDiscr is the local discriminator of the BFD session.
         "
    ::= { ibBfdNotifications 3 }

ibBfdSessStateDown NOTIFICATION-TYPE
    OBJECTS       { ibBfdSessIfIndex,
                    ibBfdSessIndex,
                    ibBfdSessState,
                    ibBfdSessName,
                    ibBfdVpnInstanceName,
                    ibBfdLocalAddr,
                    ibBfdRemoteAddr,
                    ibBfdIfName,
                    ibBfdSessLocalDiag,
                    ibBfdSessType,
                    ibBfdVrfIndex,
                    ibBfdDiscrAuto,
                    ibBfdSessVsiPeerAddr,
                    ibBfdSessVsiName,
                    ibBfdSessDefaultIp,
                    ibBfdSessNextHop,
                    ibBfdSessPWSecondaryFlag,
                    ibBfdSessVcId,
                    ibBfdLocalDiscr
    }
    STATUS        current
    DESCRIPTION
        "A notification sent when a session changes state to down.

         The session will enter state down when the communication path is out
         of work.

         The ibBfdSessIfIndex contains an interface's index under which
         the BFD session runs.

         The ibBfdSessIndex contains an index which represents a
         unique BFD session on this device.

         The ibBfdSessState is the state of the running BFD session.

         The ibBfdSessName is the name of the running BFD session.

         The ibBfdVpnInstanceName contains a VPN's name under which
         the BFD session runs.

         The ibBfdLocalAddr contains an IP address of the local interface
         from which the BFD packets is transmitted.

         The ibBfdRemoteAddr contains an IP address of the remote interface
         from which the BFD packets is transmitted.

         The ibBfdIfName is the name of the binding interface in the BFD session.

         The ibBfdSessLocalDiag is the BFD diagnostic code for the BFD session was down with the
         neighbor.

         The ibBfdSessType is the type of the BFD session.

         The ibBfdVrfIndex is the index of the VPN interface.

         The ibBfdDiscrAuto describes whether the discriminator can be auto allocated.

         The ibBfdSessVsiPeerAddr is the peer ip of VSI.

         The ibBfdSessVsiName is the name of VSI.

         The ibBfdSessDefaultIp describes whether BFD session use default multicast IP as the detect peer ip.

         The ibBfdSessNextHop is the next hop of the BFD session for LSP.

         The ibBfdSessPWSecondaryFlag is the role of the PW bound with BFD session.

         The ibBfdSessVcId is the ID of VC.

         The ibBfdLocalDiscr is the local discriminator of the BFD session.
         "
    ::= { ibBfdNotifications 4 }

ibBfdSessReachLimit NOTIFICATION-TYPE
    OBJECTS       { ibBfdSessNumberLimit
    }
    STATUS        current
    DESCRIPTION
        "A notification would be sent when the number of active BFD sessions
         reached this device's upper limit and no more session could be
         activated.

         The ibBfdSessNumberLimit is the active session limit of this device."
    ::= { ibBfdNotifications 5 }

END
