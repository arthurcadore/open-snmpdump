-- =============================================================================
-- Copyright (C) 2023 Intelbras S.A. All rights reserved.
--
-- Description: The EVPN(Ethernet VPN) MIB
-- Reference:
-- Version: V1.1
-- History:
-- V1.1 2022-05-23 Modified by Lei Gao
--    Add ibEvpnRouteMobilityTable and Added nodes ibEvpnMacMobilitySup
--    ibEvpnMacMobilitySupClear
-- V1.0 2017-10-21 Initial version Created by Jian Chen
-- =============================================================================
IB-EVPN-MIB DEFINITIONS ::= BEGIN
IMPORTS
        RowStatus, TruthValue, DisplayString
    FROM SNMPv2-TC
        MODULE-IDENTITY,
        OBJECT-TYPE,
        Unsigned32,
        NOTIFICATION-TYPE
    FROM SNMPv2-SMI
        InetAddressType,
        InetAddress
    FROM INET-ADDRESS-MIB
        ibCommon
    FROM IB-OID-MIB
        InterfaceIndex
    FROM IF-MIB;


-- =============================================================================
-- module identity part
-- =============================================================================
ibEvpn MODULE-IDENTITY
    LAST-UPDATED
        "202205230900Z"        -- May 23, 2022 at 09:00 GMT
    ORGANIZATION
        "Intelbras S.A. Industria de Telecomunicacao Eletronica Brasileria."
    CONTACT-INFO
        ""
    DESCRIPTION
        "Add ibEvpnRouteMobilityTable and Added nodes ibEvpnMacMobilitySup
         ibEvpnMacMobilitySupClear"
    REVISION
        "202205230900Z"   -- May 23, 2022 at 09:00 GMT
    DESCRIPTION
        "The EVPN MIB."
    REVISION
        "201710210900Z"   -- Oct 21, 2017 at 09:00 GMT
    DESCRIPTION
        "Initial version."
    ::= { ibCommon 173 }

-- =============================================================================
-- =================== ibEvpnMacMobilityNotifications definition =============
-- =============================================================================

ibEvpnMacMobilityNotifications OBJECT IDENTIFIER ::= { ibEvpn 0 }

-- =============================================================================
-- object definition begin
-- =============================================================================

ibEvpnObjects      OBJECT IDENTIFIER ::= { ibEvpn 1 }

-- =============================================================================
-- ibEvpnESTable Definition
-- =============================================================================
ibEvpnESTable  OBJECT-TYPE
    SYNTAX      SEQUENCE OF IbEvpnESEntry
    MAX-ACCESS  not-accessible
    STATUS      current
    DESCRIPTION
        "A table for EVPN ES parameters."
    ::= { ibEvpnObjects 1 }

ibEvpnESEntry  OBJECT-TYPE
    SYNTAX      IbEvpnESEntry
    MAX-ACCESS  not-accessible
    STATUS      current
    DESCRIPTION
        "Each entry represents the parameters of a EVPN ES."
    INDEX
    {
        ibEvpnESESI
    }
    ::= { ibEvpnESTable 1 }

IbEvpnESEntry ::=
    SEQUENCE
    {
        ibEvpnESESI               OCTET STRING,
        ibEvpnESIfIndex           InterfaceIndex,
        ibEvpnESIfName            DisplayString,
        ibEvpnESMode              Unsigned32
    }

ibEvpnESESI   OBJECT-TYPE
    SYNTAX      OCTET STRING(SIZE(1..10))
    MAX-ACCESS  not-accessible
    STATUS      current
    DESCRIPTION
        "The Ethernet Segment Identifier."
    ::= { ibEvpnESEntry 1 }

ibEvpnESIfIndex    OBJECT-TYPE
    SYNTAX      InterfaceIndex
    MAX-ACCESS  read-only
    STATUS      current
    DESCRIPTION
        "ES interface index."
    ::= { ibEvpnESEntry 2 }

ibEvpnESIfName    OBJECT-TYPE
    SYNTAX      DisplayString (SIZE (0..255))
    MAX-ACCESS  read-only
    STATUS      current
    DESCRIPTION
        "The name of ES interface."
    ::= { ibEvpnESEntry 3 }

ibEvpnESMode    OBJECT-TYPE
    SYNTAX      Unsigned32
    MAX-ACCESS  read-only
    STATUS      current
    DESCRIPTION
        "Redundancy mode of ES."
    ::= { ibEvpnESEntry 4 }

-- =============================================================================
-- End of ibEvpnESTable Definition
-- =============================================================================

-- =============================================================================
-- ibEvpnESMemberTable Definition
-- =============================================================================
ibEvpnESMemberTable  OBJECT-TYPE
    SYNTAX      SEQUENCE OF IbEvpnESMemberEntry
    MAX-ACCESS  not-accessible
    STATUS      current
    DESCRIPTION
        "A table for EVPN ES member information."
    ::= { ibEvpnObjects 2 }

ibEvpnESMemberEntry  OBJECT-TYPE
    SYNTAX      IbEvpnESMemberEntry
    MAX-ACCESS  not-accessible
    STATUS      current
    DESCRIPTION
        "Each entry contain the parameters of an ES member."
    INDEX
    {
        ibEvpnESESI,
        ibEvpnESMemberIPType,
        ibEvpnESMemberIP
    }
    ::= { ibEvpnESMemberTable 1 }

IbEvpnESMemberEntry ::=
    SEQUENCE
    {
        ibEvpnESMemberIPType        InetAddressType,
        ibEvpnESMemberIP            InetAddress,
        ibEvpnESMemberIsSelf        TruthValue
    }

ibEvpnESMemberIPType     OBJECT-TYPE
    SYNTAX      InetAddressType
    MAX-ACCESS  not-accessible
    STATUS      current
    DESCRIPTION
        "ES member IP address type."
    ::= { ibEvpnESMemberEntry 1 }

ibEvpnESMemberIP   OBJECT-TYPE
    SYNTAX       InetAddress
    MAX-ACCESS   not-accessible
    STATUS       current
    DESCRIPTION
        "ES member IP address."
    ::= { ibEvpnESMemberEntry 2 }

ibEvpnESMemberIsSelf  OBJECT-TYPE
    SYNTAX       TruthValue
    MAX-ACCESS   read-only
    STATUS       current
    DESCRIPTION
        "Whether the member is local."
    ::= { ibEvpnESMemberEntry 3 }

-- =============================================================================
-- End of ibEvpnESMemberTable Definition
-- =============================================================================

-- =============================================================================
-- ibEvpnESDFTable Definition
-- =============================================================================
ibEvpnESDFTable  OBJECT-TYPE
    SYNTAX      SEQUENCE OF IbEvpnESDFEntry
    MAX-ACCESS  not-accessible
    STATUS      current
    DESCRIPTION
        "A table for the ES DF information."
    ::= { ibEvpnObjects 3 }

ibEvpnESDFEntry  OBJECT-TYPE
    SYNTAX      IbEvpnESDFEntry
    MAX-ACCESS  not-accessible
    STATUS      current
    DESCRIPTION
        "An entry represents an (ES, VLAN) group."
    INDEX
    {
        ibEvpnESESI,
        ibEvpnESDFVLANID
    }
    ::= { ibEvpnESDFTable 1 }

IbEvpnESDFEntry ::=
    SEQUENCE
    {
        ibEvpnESDFVLANID            Unsigned32,
        ibEvpnESDFAcIfIndex         InterfaceIndex,
        ibEvpnESDFACEvcSrvInstId    Unsigned32,
        ibEvpnESDFMode              Unsigned32,
        ibEvpnESDFRouterIPType      InetAddressType,
        ibEvpnESDFRouterIP          InetAddress
    }

ibEvpnESDFVLANID     OBJECT-TYPE
    SYNTAX      Unsigned32
    MAX-ACCESS  not-accessible
    STATUS      current
    DESCRIPTION
        "VLAN assigned to an ES."
    ::= { ibEvpnESDFEntry 1 }

ibEvpnESDFAcIfIndex    OBJECT-TYPE
    SYNTAX      InterfaceIndex
    MAX-ACCESS  read-only
    STATUS      current
    DESCRIPTION
        "Index of an interface that hosts an Ethernet service instance for an ES."
    ::= { ibEvpnESDFEntry 2 }

ibEvpnESDFACEvcSrvInstId    OBJECT-TYPE
    SYNTAX      Unsigned32
    MAX-ACCESS  read-only
    STATUS      current
    DESCRIPTION
        "Ethernet service instance ID."
    ::= { ibEvpnESDFEntry 3 }

ibEvpnESDFMode    OBJECT-TYPE
    SYNTAX      Unsigned32
    MAX-ACCESS  read-only
    STATUS      current
    DESCRIPTION
        "ES redundancy mode."
    ::= { ibEvpnESDFEntry 4 }

ibEvpnESDFRouterIPType    OBJECT-TYPE
    SYNTAX      InetAddressType
    MAX-ACCESS  read-only
    STATUS      current
    DESCRIPTION
        "The designated forwarder IP address type."
    ::= { ibEvpnESDFEntry 5 }

ibEvpnESDFRouterIP    OBJECT-TYPE
    SYNTAX      InetAddress
    MAX-ACCESS  read-only
    STATUS      current
    DESCRIPTION
        "The designated forwarder IP address."
    ::= { ibEvpnESDFEntry 6 }

-- =============================================================================
-- End of ibEvpnESDFTable Definition
-- =============================================================================

-- =============================================================================
-- ibEvpnRouteMobilityTable Definition
-- =============================================================================
ibEvpnRouteMobilityTable  OBJECT-TYPE
    SYNTAX      SEQUENCE OF IbEvpnRouteMobilityEntry
    MAX-ACCESS  not-accessible
    STATUS      current
    DESCRIPTION
        "A table for the EVPN route mobility suppression information."
    ::= { ibEvpnObjects 4 }

ibEvpnRouteMobilityEntry  OBJECT-TYPE
    SYNTAX      IbEvpnRouteMobilityEntry
    MAX-ACCESS  not-accessible
    STATUS      current
    DESCRIPTION
        "Provides information about an EVPN route mobility entry."
    INDEX
    {
        ibEvpnVsiName,
        ibEvpnInstanceName
    }
    ::= { ibEvpnRouteMobilityTable 1 }

IbEvpnRouteMobilityEntry ::=
    SEQUENCE
    {
        ibEvpnVsiName            OCTET STRING,
        ibEvpnInstanceName       OCTET STRING,
        ibEvpnRouteRowStatus     RowStatus
    }

ibEvpnVsiName    OBJECT-TYPE
    SYNTAX      OCTET STRING(SIZE(1..31))
    MAX-ACCESS  accessible-for-notify
    STATUS      current
    DESCRIPTION
        "VSI name. The maximum length of a VSI
         is 31 characters."
    ::= { ibEvpnRouteMobilityEntry 1 }

ibEvpnInstanceName    OBJECT-TYPE
    SYNTAX      OCTET STRING(SIZE(1..31))
    MAX-ACCESS  accessible-for-notify
    STATUS      current
    DESCRIPTION
        "EVPN instance name. The maximum length of an EVPN instance
         is 31 characters."
    ::= { ibEvpnRouteMobilityEntry 2 }

ibEvpnRouteRowStatus OBJECT-TYPE
    SYNTAX      RowStatus
    MAX-ACCESS  read-create
    STATUS      current
    DESCRIPTION
        "Operation status of this table entry."
    ::= { ibEvpnRouteMobilityEntry 3 }

-- =============================================================================
-- End of ibEvpnRouteMobilityTable Definition
-- =============================================================================

-- ==================================================================
-- ibEvpnMacMobilityNotifications Definition
-- ==================================================================
ibEvpnMacMobilitySup NOTIFICATION-TYPE
    OBJECTS
        {
            ibEvpnVsiName,
            ibEvpnInstanceName
        }
    STATUS      current
    DESCRIPTION
        "This notification is generated when the move count for one or more MAC
         addresses crosses the threshold for the EVPN instance."
    ::= { ibEvpnMacMobilityNotifications 1 }

ibEvpnMacMobilitySupClear NOTIFICATION-TYPE
    OBJECTS
        {
            ibEvpnVsiName,
            ibEvpnInstanceName
        }
    STATUS      current
    DESCRIPTION
        "This notification is generated when the move count for all MAC
         addresses drops below the threshold for the EVPN instance."
    ::= { ibEvpnMacMobilityNotifications 2 }
-- =============================================================================
-- End of ibEvpnRouteMacMobilityNotifications Definition
-- =============================================================================

END
