--  =================================================================
-- Copyright (C) 2023 Intelbras S.A. All rights reserved.
--
-- Description: This MIB provides information about Ethernet Synchronous
--              Messaging Channel feature.
-- Reference:
-- Version: V1.0
-- History:
-- V1.0 2023-02-20, Du Wei, Initial version
-- =================================================================
IB-ESMC-MIB DEFINITIONS ::= BEGIN

IMPORTS
    OBJECT-TYPE, MODULE-IDENTITY, NOTIFICATION-TYPE
        FROM SNMPv2-SMI
    ibCommon
        FROM IB-OID-MIB;

ibEsmc MODULE-IDENTITY
    LAST-UPDATED "202302200000Z"
    ORGANIZATION
        "Intelbras S.A. Industria de Telecomunicacao Eletronica Brasileria."
    CONTACT-INFO
        ""
    DESCRIPTION
        "This MIB provides information about Ethernet Synchronous Messaging Channel feature."
    REVISION "202302200000Z"
    DESCRIPTION
        "The initial revision of this MIB module."
    ::= { ibCommon 260 }

--
-- Node definitions
--

ibEsmcNotifications OBJECT IDENTIFIER ::= { ibEsmc 1 }

ibEsmcNotification OBJECT IDENTIFIER ::= { ibEsmcNotifications 0 }

ibEsmcPacketLoss NOTIFICATION-TYPE
    OBJECTS { ibEsmcPortName }
    STATUS current
    DESCRIPTION
        "The trap is generated when esmc packet not received for more than 5000 ms."
    ::= { ibEsmcNotification 1 }

ibEsmcPacketLossResume NOTIFICATION-TYPE
    OBJECTS { ibEsmcPortName }
    STATUS current
    DESCRIPTION
        "The trap is generated when received esmc packet is normal."
    ::= { ibEsmcNotification 2 }

ibEsmcNotificationObjects OBJECT IDENTIFIER ::= { ibEsmcNotifications 1 }

ibEsmcPortName OBJECT-TYPE
    SYNTAX OCTET STRING
    MAX-ACCESS accessible-for-notify
    STATUS current
    DESCRIPTION
        "Port name."
    ::= { ibEsmcNotificationObjects 1 }

END
