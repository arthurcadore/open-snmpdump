-- ==================================================================
-- Copyright (C) 2023 Intelbras S.A. All rights reserved.
--
-- Description: MAC management MIB
-- Reference:
-- Version: V2.3
-- History:
--(1) Created by Zhangshilin, 2001.06.29
-- V2.0 2004-10-12 updated by gaolong
--      Import TEXTUAL-CONVENTION and MODULE-IDENTITY.
--      Add ibLswMacPort MODULE-IDENTITY clause.
--      Change ACCESS to MAX-ACCESS.
--      Change MAX-ACCESS clause value from write-only to read-write.
-- V2.1 2005-03-16 by gaolong
--      Change import clause of ibdot1qVlanIndex
-- V2.2 2005-07-28 by huna kf0518
--      Add ibdot1qTpFdbGroupSetTable
-- V2.3 2005-02-25 by wangyupeng
--      Add blackhole and security for ibdot1qTpFdbSetStatus
-- ==================================================================

-- ==================================================================
--
-- Varibles and types be imported
--
-- ==================================================================
IB-LswMAM-MIB DEFINITIONS ::= BEGIN
IMPORTS

    MacAddress, TEXTUAL-CONVENTION
        FROM SNMPv2-TC

    OBJECT-TYPE,Integer32, MODULE-IDENTITY
        FROM SNMPv2-SMI

    iblswCommon
        FROM IB-OID-MIB

    ibdot1qVlanIndex
        FROM IB-LswVLAN-MIB;

    ibLswMacPort MODULE-IDENTITY
            LAST-UPDATED "200106290000Z"
            ORGANIZATION
                "Intelbras S.A. Industria de Telecomunicacao Eletronica Brasileria."
            CONTACT-INFO
                ""
            DESCRIPTION
            " "
            REVISION "200106290000Z"
            DESCRIPTION
            " "
            ::= { iblswCommon 3 }

    InterfaceIndex ::= TEXTUAL-CONVENTION
       DISPLAY-HINT "d"
       STATUS       current
       DESCRIPTION
               "A unique value, greater than zero, for each interface
               or interface sub-layer in the managed system.  It is
               recommended that values are assigned contiguously
               starting from 1.  The value for each interface sub-
               layer must remain constant at least from one re-
               initialization of the entity's network management
               system to the next re-initialization."
       SYNTAX       Integer32

    PortList ::= TEXTUAL-CONVENTION
        STATUS      current
        DESCRIPTION
            "Each octet within this value specifies a set of eight
            ports, with the first octet specifying ports 1 through
            8, the second octet specifying ports 9 through 16, etc.
            Within each octet, the most significant bit represents
            the lowest numbered port, and the least significant bit
            represents the highest numbered port.  Thus, each port
            of the bridge is represented by a single bit within the
            value of this object.  If that bit has a value of '1'
            then that port is included in the set of ports; the port
            is not included if its bit has a value of '0'."
        SYNTAX      OCTET STRING




-- ==================================================================
--
-- ======================= definition begin =========================
--
-- ==================================================================



    ibdot1qMacSearchTable   OBJECT-TYPE
        SYNTAX  SEQUENCE OF IbDot1qMacSearchEntry
        MAX-ACCESS  not-accessible
        STATUS  current
        DESCRIPTION
                "Information table for searching port with mac address   "
        ::= { ibLswMacPort  1 }

    ibdot1qMacSearchEntry   OBJECT-TYPE
        SYNTAX  IbDot1qMacSearchEntry
        MAX-ACCESS  not-accessible
        STATUS  current
        DESCRIPTION
                " Information table for searching port with mac address entry  "
        INDEX   { ibdot1qMacSearchAddress, ibdot1qMacSearchVlanID }
        ::= { ibdot1qMacSearchTable  1 }

    IbDot1qMacSearchEntry ::=
       SEQUENCE {
                ibdot1qMacSearchAddress MacAddress ,
                ibdot1qMacSearchVlanID  INTEGER ,
                ibdot1qMacSearchPort    InterfaceIndex ,
                ibdot1qMacSearchAgeTime INTEGER
                }

    ibdot1qMacSearchAddress   OBJECT-TYPE
        SYNTAX  MacAddress
        MAX-ACCESS  read-only
        STATUS  current
        DESCRIPTION
                "MAC address"
        ::= { ibdot1qMacSearchEntry  1 }

    ibdot1qMacSearchVlanID OBJECT-TYPE
        SYNTAX  INTEGER (-1 | 1..4096)
        MAX-ACCESS  read-only
        STATUS  current
        DESCRIPTION
               " VLANID of the native VLAN of the MAC address to be searched for "
        ::= { ibdot1qMacSearchEntry  2 }

    ibdot1qMacSearchPort OBJECT-TYPE
        SYNTAX  InterfaceIndex
        MAX-ACCESS  read-only
        STATUS  current
        DESCRIPTION
               "Interface index corresponding to the MAC address"
        ::= { ibdot1qMacSearchEntry  3 }

    ibdot1qMacSearchAgeTime OBJECT-TYPE
        SYNTAX  INTEGER
        MAX-ACCESS  read-only
        STATUS  current
        DESCRIPTION
               " Address aging time"
        ::= { ibdot1qMacSearchEntry  4 }


    ibdot1qTpFdbSetTable   OBJECT-TYPE
        SYNTAX  SEQUENCE OF IbDot1qTpFdbSetEntry
        MAX-ACCESS  not-accessible
        STATUS  current
        DESCRIPTION
                "Unicast address setting table  "
        ::= { ibLswMacPort  2 }

    ibdot1qTpFdbSetEntry   OBJECT-TYPE
        SYNTAX  IbDot1qTpFdbSetEntry
        MAX-ACCESS  not-accessible
        STATUS  current
        DESCRIPTION
                " Unicast address setting table entry "
        INDEX   { ibdot1qVlanIndex, ibdot1qTpFdbSetAddress }
        ::= { ibdot1qTpFdbSetTable  1 }

    IbDot1qTpFdbSetEntry ::=
       SEQUENCE {
                ibdot1qTpFdbSetAddress  MacAddress ,
                ibdot1qTpFdbSetPort     InterfaceIndex ,
                ibdot1qTpFdbSetStatus   INTEGER,
                ibdot1qTpFdbSetOperate  INTEGER
                }

    ibdot1qTpFdbSetAddress   OBJECT-TYPE
        SYNTAX  MacAddress
        MAX-ACCESS  not-accessible
        STATUS  current
        DESCRIPTION
                "Unicast MAC address "
        ::= { ibdot1qTpFdbSetEntry  1 }


    ibdot1qTpFdbSetPort OBJECT-TYPE
        SYNTAX  InterfaceIndex

        MAX-ACCESS  read-write
        STATUS  current
        DESCRIPTION
               "Interface index corresponding to the MAC address "
        ::= { ibdot1qTpFdbSetEntry  2 }

    ibdot1qTpFdbSetStatus OBJECT-TYPE
        SYNTAX  INTEGER {
            other(1),
            learned(3),
            static(6),
            dynamic(7),
            blackhole(9),
            security(11)
                }
        MAX-ACCESS read-write
        STATUS      current
        DESCRIPTION
               "State corresponding to the MAC address"
        ::= { ibdot1qTpFdbSetEntry 3 }

    ibdot1qTpFdbSetOperate OBJECT-TYPE
        SYNTAX  INTEGER {
            add(1),
            delete(2)
            }
        MAX-ACCESS read-write
        STATUS      current
        DESCRIPTION
        "Add or delete an MAC address.  Read operation not supported."
        ::= { ibdot1qTpFdbSetEntry 4 }


    ibdot1qTpFdbGroupSetTable   OBJECT-TYPE
        SYNTAX  SEQUENCE OF IbDot1qTpFdbGroupSetEntry
        MAX-ACCESS  not-accessible
        STATUS  current
        DESCRIPTION
                "Multistcast address setting table, whose maximal row number
                 is dynamically changed by the influence of IGSP.  When
                 reaching the upper limit of the table, no more row could be
                 added, then an error will be returned."
        ::= { ibLswMacPort  3 }

    ibdot1qTpFdbGroupSetEntry   OBJECT-TYPE
        SYNTAX  IbDot1qTpFdbGroupSetEntry
        MAX-ACCESS  not-accessible
        STATUS  current
        DESCRIPTION
                "Multicast address setting table entry."
        INDEX   { ibdot1qVlanIndex, ibdot1qTpFdbGroupSetAddress }
        ::= { ibdot1qTpFdbGroupSetTable  1 }

    IbDot1qTpFdbGroupSetEntry ::=
       SEQUENCE {
                ibdot1qTpFdbGroupSetAddress  MacAddress,
                ibdot1qTpFdbGroupSetPort     PortList,
                ibdot1qTpFdbGroupSetOperate  INTEGER
                }

    ibdot1qTpFdbGroupSetAddress   OBJECT-TYPE
        SYNTAX  MacAddress
        MAX-ACCESS  not-accessible
        STATUS  current
        DESCRIPTION
                "Multicast MAC address."
        ::= { ibdot1qTpFdbGroupSetEntry  1 }

    ibdot1qTpFdbGroupSetPort OBJECT-TYPE
        SYNTAX      PortList
        MAX-ACCESS  read-write
        STATUS  current
        DESCRIPTION
                "The complete set of ports, in this VLAN, to which
                 frames destined to this Multicast MAC address are currently
                 being explicitly forwarded.  This does not include ports
                 for which this address is only implicitly forwarded."
        ::= { ibdot1qTpFdbGroupSetEntry  2 }

    ibdot1qTpFdbGroupSetOperate OBJECT-TYPE
        SYNTAX  INTEGER {
            add(1),
            delete(2)
            }
        MAX-ACCESS read-write
        STATUS      current
        DESCRIPTION
                "Add or delete a Multicast MAC address.  Read operation is
                 meaningless.  When adding a Multicast MAC address, it is
                 required to provide MacAddress, VLAN and PortList all.  For
                 deleting operation, MacAddress and VLAN must be provided,
                 but ibdot1qTpFdbGroupSetPort is optional."
        ::= { ibdot1qTpFdbGroupSetEntry 3 }


END
