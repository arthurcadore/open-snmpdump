-- ===========================================================
-- Copyright (C) 2023 Intelbras S.A. All rights reserved.
-- Description: The MIB is designed to manage the disk.
-- Reference:
-- Version: V1.1
-- History:
--   V1.0 2007-09-04 created by lizhicheng
--   V1.1 2010-02-05
--        Add ibDiskPowerOffReason to ibDiskEntry
-- =================================================================
IB-DISK-MIB DEFINITIONS ::= BEGIN
IMPORTS
        Integer32, OBJECT-TYPE, MODULE-IDENTITY
    FROM SNMPv2-SMI
        ibStorageRef, IbStorageEnableState, IbStorageActionType
    FROM IB-STORAGE-REF-MIB;

ibDisk MODULE-IDENTITY
    LAST-UPDATED "200709041452Z"
    ORGANIZATION
        "Intelbras S.A. Industria de Telecomunicacao Eletronica Brasileria."
    CONTACT-INFO
        ""
    DESCRIPTION
        "This MIB describes the general information of disk device, include
        the running status, disk interface, and chche management."
    ::= { ibStorageRef 3 }

ibDiskMibObjects OBJECT IDENTIFIER ::= { ibDisk 1 }


-- Disk Entity Extend Table
-- This table described some entity extend information about the disk.
ibDiskTable OBJECT-TYPE
    SYNTAX      SEQUENCE OF IbDiskEntry
    MAX-ACCESS  not-accessible
    STATUS      current
    DESCRIPTION
        "This table contains some entity extend information of the disk."
    ::= { ibDiskMibObjects 1 }

ibDiskEntry OBJECT-TYPE
    SYNTAX      IbDiskEntry
    MAX-ACCESS  not-accessible
    STATUS      current
    DESCRIPTION
        "An entry containing management information applicable to the disk."
    INDEX
        {
            ibDiskIndex
        }

    ::= { ibDiskTable 1 }

IbDiskEntry ::= SEQUENCE
    {
        ibDiskIndex               Integer32,
        ibDiskPortType            INTEGER,
        ibDiskPortSpeed           Integer32,
        ibDiskSize                Integer32,
        ibDiskFreeSpace           Integer32,
        ibDiskLocationState       IbStorageEnableState,
        ibDiskRunLedState         INTEGER,
        ibDiskFaultLedState       INTEGER,
        ibDiskInitialize          IbStorageActionType,
        ibDiskGlobalSpare         INTEGER,
        ibDiskLocalSpare          INTEGER,
        ibDiskReadCache           IbStorageEnableState,
        ibDiskWriteCache          IbStorageEnableState,
        ibDiskPowerOffReason      INTEGER
    }

ibDiskIndex OBJECT-TYPE
    SYNTAX      Integer32
    MAX-ACCESS  not-accessible
    STATUS      current
    DESCRIPTION
        "This object identifies the entity index of disk. The object
        identified by this index is the same object as identified by the
        same value of entPhysicalIndex."
    ::= { ibDiskEntry 1 }

ibDiskPortType OBJECT-TYPE
    SYNTAX      INTEGER
        {
            sata(1),
            pata(2),
            sas(3),
            scsi(4),
            ieee1394(5),
            fcal(6)
        }
    MAX-ACCESS  read-only
    STATUS      current
    DESCRIPTION
        "This object describes the interface type of disk.
        The value 'sata' means serial advanced technology attachment.
        The value 'pata' means parallel advanced technology attachment.
        The value 'sas' means serial attached SCSI.
        The value 'scsi' means small computer system interface.
        The value 'ieee1394' means a type of bus standard.
        The value 'fcal' means fiber channel arbitrated loop."
    ::= { ibDiskEntry 2 }

ibDiskPortSpeed OBJECT-TYPE
    SYNTAX      Integer32
    UNITS       "MB/second"
    MAX-ACCESS  read-only
    STATUS      current
    DESCRIPTION
        "This object identifies the speed of disk interface.
        The units is million bytes per second."
    ::= { ibDiskEntry 3 }

ibDiskSize OBJECT-TYPE
    SYNTAX      Integer32
    UNITS       "MB"
    MAX-ACCESS  read-only
    STATUS      current
    DESCRIPTION
        "This object describes the size of disk's total space. The units
        is million bytes."
    ::= { ibDiskEntry 4 }


ibDiskFreeSpace OBJECT-TYPE
    SYNTAX      Integer32
    UNITS       "MB"
    MAX-ACCESS  read-only
    STATUS      current
    DESCRIPTION
        "This object describes the size of spare space of the disk. The
        units is million bytes."
    ::= { ibDiskEntry 5 }

ibDiskLocationState OBJECT-TYPE
    SYNTAX      IbStorageEnableState
    MAX-ACCESS  read-write
    STATUS      current
    DESCRIPTION
        "This object identifies if the led used to confirm the
        position of disk is enable."
    DEFVAL { enable }
    ::= { ibDiskEntry 6 }

ibDiskRunLedState OBJECT-TYPE
    SYNTAX      INTEGER
        {
            on(1),
            blink(2),
            fastblink(3)
        }
    MAX-ACCESS  read-only
    STATUS      current
    DESCRIPTION
        "This object identifies the runing state of the disk.
        The value of 'on' means the blue led is on, and the disk works well.
        The value of 'blink' means the blue led is blinking, and the disk
        is being readed or writed.
        The value of 'fastblink' means the blue led is blinking very fast,
        and the disk is being located.
        This object can not be 'fastblink' when the value of associated
        ibDiskLocationState object is equal to 'disable'."
    ::= { ibDiskEntry 7 }

ibDiskFaultLedState OBJECT-TYPE
    SYNTAX      INTEGER
        {
            off(1),
            on(2),
            blink(3)
        }
    MAX-ACCESS  read-only
    STATUS      current
    DESCRIPTION
        "This object identifies the fault state of the disk.
        The value of 'off' means the yellow led is go out, and the disk
        works well.
        The value of 'on' means the yellow led is on, and the disk break
        down.
        The value of 'blink' means the yellow led is blinking, and a group
        of raid disk is being synchronized."
    ::= { ibDiskEntry 8 }

ibDiskInitialize OBJECT-TYPE
    SYNTAX      IbStorageActionType
    MAX-ACCESS  read-write
    STATUS      current
    DESCRIPTION
        "The operation of initialize the disk. When the value of this object
        is set to 'action', the operation of disk initialize are touched off."
    ::= { ibDiskEntry 9 }

ibDiskGlobalSpare OBJECT-TYPE
    SYNTAX      INTEGER
        {
            globalSpare(1),
            nonglobalSpare(2)
        }
    MAX-ACCESS  read-write
    STATUS      current
    DESCRIPTION
        "This object identifies if the disk is a global hot spare disk.
        The value 'globalSpare' means it is a global spare disk, and
        the value 'nonglobalSpare' means not."
    ::= { ibDiskEntry 10 }

ibDiskLocalSpare OBJECT-TYPE
    SYNTAX      INTEGER
        {
            localSpare(1),
            nonlocalSpare(2)
        }
    MAX-ACCESS  read-only
    STATUS      current
    DESCRIPTION
        "This object identifies if the disk is a specific hot spare disk.
        The value 'localSpare' means it is a local spare disk, and
        'nonlocalSpare' means not."
    ::= { ibDiskEntry 11 }

ibDiskReadCache OBJECT-TYPE
    SYNTAX      IbStorageEnableState
    MAX-ACCESS  read-write
    STATUS      current
    DESCRIPTION
        "This object identifies the state of read cache."
    DEFVAL { enable }
    ::= { ibDiskEntry 12 }


ibDiskWriteCache OBJECT-TYPE
    SYNTAX      IbStorageEnableState
    MAX-ACCESS  read-write
    STATUS      current
    DESCRIPTION
        "This object identifies the state of write cache."
    DEFVAL { enable }
    ::= { ibDiskEntry 13 }

ibDiskPowerOffReason OBJECT-TYPE
    SYNTAX      INTEGER
        {
            environmentUnstable(1),
            mediumError(2),
            smartCheckError(3),
            generalError(4)
        }
    MAX-ACCESS  read-only
    STATUS      current
    DESCRIPTION
        "This object describes the reason of disk poweroff.
        The value 'environmentUnstable' means disk poweroff and may poweron again.
        The value 'mediumError' means disk poweroff and never poweron.
        The value 'smartCheckError' means disk's SMART check failed and poweroff.
        The value 'generalError' means disk poweroff because of general error."
    ::= { ibDiskEntry 14 }

END
