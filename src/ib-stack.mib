-- =================================================================
-- Copyright (C) 2023 Intelbras S.A. All rights reserved.
--
-- Description: stack mib
-- Reference: STACK-MIB
-- Version: V1.7
-- History:
--   V1.0 Created by ranbin
--        Initial version 2008-04-30
--   V1.1 2012-02-24 Modified by zhengwei
--        Changed the range of link delay to 0 to 30000 ms
--   V1.2 2013-08-16 Updated by wangpengju
--        Added node ibStackPortForwardingPath to ibStackPortInfoTable
--        2013-10-23 Updated by zhengwei
--        Added notification nodes because MAD group work status changed:
--        ibStackMadBfdChangeNormal
--        ibStackMadBfdChangeFailure
--        ibStackMadLacpChangeNormal
--        ibStackMadLacpChangeFailure
--   V1.3 2014-08-11 Updated by SongHao
--        Added ibStackDomainId
--        2014-11-20 Updated by songhao
--        Added ibStackPortConfigActivate in ibStackGlobalConfig.
--        ibStackLinkDelayInterval was changed to in the range of 0 to 2147483647 ms
--   V1.4 2020-03-03 Updated by zhangwenbo
--        Added notification node ibStackPhysicalIntfLinkUp
--        Added notification node ibStackPhysicalIntfLinkDown
--        Added ibStackPhysicalIntfName
--   V1.5 2021-03-17 Updated by meishenhe
--        Added notification node ibStackPhysicalIntfRxTimeout
--   V1.6 2022-06-18 Updated by meishenhe
--        Added notification node ibStackMemberAdd
--        Added notification node ibStackMemberLeave
--        Added notification node ibStackLinkUp
--        Added notification nodeibStackLinkDown
--        Added notification node ibStackMemberLimit
--        Added notification node ibStackMemberPortLoopAlarm
--        Added notification node ibStackMemberPortLoopAlarmRecover
--        Added notification node ibStackBrigdgeMacChange
--        Added notification node ibStackLogicStackPortLinkErr
--        Added notification node ibStackLogicStackPortLinkErrRecover
--   V1.7 2022-09-20 Updated by meishenhe
--        Added notification node ibStackPortConfigureFailure
--        Added notification node ibStackSetUpFailure
-- =================================================================
IB-STACK-MIB DEFINITIONS ::= BEGIN

IMPORTS
        ibCommon
    FROM IB-OID-MIB
        entPhysicalIndex
    FROM ENTITY-MIB
        ifIndex, ifDescr
    FROM IF-MIB
        Integer32, OBJECT-TYPE, MODULE-IDENTITY, NOTIFICATION-TYPE, Unsigned32
    FROM SNMPv2-SMI
        DisplayString, MacAddress
    FROM SNMPv2-TC;

ibStack MODULE-IDENTITY
    LAST-UPDATED "202209221353Z"
    ORGANIZATION
        "Intelbras S.A. Industria de Telecomunicacao Eletronica Brasileria."
    CONTACT-INFO
        ""
    DESCRIPTION
        "This MIB is used to manage STM (Stack Topology Management)
         information for IRF (Intelligent Resilient Framework) device.
         This MIB is applicable to IRF-capable products.  Some objects in
         this MIB may be used only for some specific products, so users should
         refer to the related documents to acquire more detailed information."
    REVISION "202209221353Z"
    DESCRIPTION
        "Added notification node ibStackPortConfigureFailure
         Added notification node ibStackSetUpFailure"
    REVISION "202206180943Z"
    DESCRIPTION
        "Added notification node ibStackMemberAdd
         Added notification node ibStackMemberLeave
         Added notification node ibStackLinkUp
         Added notification node ibStackLinkDown
         Added notification node ibStackMemberLimit
         Added notification node ibStackMemberPortLoopAlarm
         Added notification node ibStackMemberPortLoopAlarmRecover
         Added notification node ibStackBrigdgeMacChange
         Added notification node ibStackLogicStackPortLinkErr
         Added notification node ibStackLogicStackPortLinkErrRecover"
    REVISION "202103250943Z"
    DESCRIPTION
        "Added notification node ibStackPhysicalIntfRxTimeout."
    REVISION "201411200850Z"
    DESCRIPTION
        "Added ibStackPortConfigActivate in ibStackGlobalConfig.
         ibStackLinkDelayInterval was changed to in the range of 0 to
         2147483647 ms."
    REVISION "201408110641Z"
    DESCRIPTION
        "Added ibStackDomainId."
    REVISION "201310230000Z"
    DESCRIPTION
        "Added notification nodes because MAD group work status changed:
        ibStackMadBfdChangeNormal
        ibStackMadBfdChangeFailure
        ibStackMadLacpChangeNormal
        ibStackMadLacpChangeFailure"
    REVISION "201308160000Z"
    DESCRIPTION
        "Added node ibStackPortForwardingPath to ibStackPortInfoTable."
    REVISION "201202240000Z"
    DESCRIPTION
        "Changed the range of link delay to 0 to 30000 ms."
    REVISION "200804301650Z"             -- 30th April, 2007 at 16:50 GMT
    DESCRIPTION
        "The initial revision of this MIB module."
    ::= { ibCommon 91 }


-- Scalar MIB objects, which are considered as global variables
-- Global Level Configuration

ibStackGlobalConfig OBJECT IDENTIFIER ::= { ibStack 1 }

ibStackMaxMember OBJECT-TYPE
    SYNTAX      Integer32
    MAX-ACCESS  read-only
    STATUS      current
    DESCRIPTION
        "The maximum number of members in a stack."
    ::= { ibStackGlobalConfig 1 }

ibStackMemberNum OBJECT-TYPE
    SYNTAX      Integer32
    MAX-ACCESS  read-only
    STATUS      current
    DESCRIPTION
        "The number of members currently in a stack."
    ::= { ibStackGlobalConfig 2 }

ibStackMaxConfigPriority OBJECT-TYPE
    SYNTAX      Integer32
    MAX-ACCESS  read-only
    STATUS      current
    DESCRIPTION
        "The highest priority that can be configured for a member in a stack."
    ::= { ibStackGlobalConfig 3 }

ibStackAutoUpdate OBJECT-TYPE
    SYNTAX      INTEGER
        {
            disabled(1),
            enabled(2)
        }
    MAX-ACCESS  read-write
    STATUS      current
    DESCRIPTION
        "The function for automatically updating the image from the master to
         a device that is attempting to join the stack.
         When a new device tries to join a stack, STM verifies the image
         consistency between the joining device and the master.
         If the joining device uses a different image version than the master,
         the function updates the joining device with the image of the master.
         When this function is disabled, the new device can't join the stack
         if it uses a different software version than the master.

        disabled: disable auto update function
        enabled: enable auto update function"
    ::= { ibStackGlobalConfig 4 }

ibStackMacPersistence OBJECT-TYPE
    SYNTAX      INTEGER
        {
            notPersist(1),
            persistForSixMin(2),
            persistForever(3)
        }
    MAX-ACCESS  read-write
    STATUS      current
    DESCRIPTION
        "The mode of bridge MAC address persistence.  When a stack starts,
         the bridge MAC address of the master is used as that of the stack.
         When the master leaves the stack, the bridge MAC address of the
         stack changes depending on the mode of bridge MAC address persistence.

        notPersist: The bridge MAC address of the new master is used
         as that of the stack immediately.
        persistForSixMin: The original bridge MAC address will be reserved for six
         minutes.  In this period, if the master that has left rejoins the stack,
         the bridge MAC address of the stack will not change.
         If the old master doesn't rejoin the stack within this period, the
         bridge MAC address of the new master will be used as that of the stack.
        persistForever: Whether the master leaves or not, the bridge MAC address
         of the stack will never change."
    ::= { ibStackGlobalConfig 5 }

ibStackLinkDelayInterval OBJECT-TYPE
    SYNTAX      Integer32 (0..2147483647)
    UNITS       "millisecond"
    MAX-ACCESS  read-write
    STATUS      current
    DESCRIPTION
        "Delay for stack ports to report a link down event.  If the link comes up
         before the delay timer expires, the stack port will not report the link
         down event.  If the link is not recovered before the delay timer expires,
         the stack port will report the change.  If the delay is set to 0,
         the stack ports will report a link down event without delay.

        0: no delay
        other value(ms): delay time"
    ::= { ibStackGlobalConfig 6 }

ibStackTopology OBJECT-TYPE
    SYNTAX      INTEGER
        {
            chainConn(1),
            ringConn(2)
        }
    MAX-ACCESS  read-only
    STATUS      current
    DESCRIPTION
        "Stack topology.

        chainConn: daisy-chain connection
        ringConn: ring connection"
    ::= { ibStackGlobalConfig 7 }

ibStackDomainId OBJECT-TYPE
    SYNTAX      Unsigned32 (0..4294967295)
    MAX-ACCESS  read-write
    STATUS      current
    DESCRIPTION
        "Domain ID of the IRF fabric that is used to uniquely identify an IRF fabric.
        Domain IDs prevent IRF fabrics from interfering with one another."
    ::= { ibStackGlobalConfig 8 }

ibStackPortConfigActivate OBJECT-TYPE
    SYNTAX INTEGER
        {
            none(1),
            set(2)
        }
    MAX-ACCESS read-write
    STATUS current
    DESCRIPTION
        "After connecting the physical interfaces between two devices and
        binding them to the correct IRF ports, you must
        activate the settings on the IRF ports.  This operation merges the two
        devices into one IRF fabric.  The system activates the IRF port
        settings automatically in the following situations:
        1. The configuration file that the device starts with contains
        IRF port bindings.
        2. You are binding physical interfaces to an IRF port after an IRF fabric
        is formed.

        none: If the user sets this object to none, this object will return
              a success without performing any operation.

        set: Activates the settings on the IRF ports.
             After the settings is activated, this object will return to
             none at the next reading."
    DEFVAL { none }
    ::= { ibStackGlobalConfig 9 }

-- Device Level Configuration
ibStackDeviceConfigTable OBJECT-TYPE
    SYNTAX      SEQUENCE OF IbStackDeviceConfigEntry
    MAX-ACCESS  not-accessible
    STATUS      current
    DESCRIPTION
        "This table contains objects to manage device information in a stack."
    ::= { ibStack 2 }

ibStackDeviceConfigEntry OBJECT-TYPE
    SYNTAX      IbStackDeviceConfigEntry
    MAX-ACCESS  not-accessible
    STATUS      current
    DESCRIPTION
        "This table contains objects to manage device information in a stack."
    INDEX
        {
            entPhysicalIndex
        }
    ::= { ibStackDeviceConfigTable 1 }

IbStackDeviceConfigEntry ::= SEQUENCE
    {
        ibStackMemberID          Integer32,
        ibStackConfigMemberID    Integer32,
        ibStackPriority          Integer32,
        ibStackPortNum           Integer32,
        ibStackPortMaxNum        Integer32
    }

ibStackMemberID OBJECT-TYPE
    SYNTAX      Integer32
    MAX-ACCESS  read-only
    STATUS      current
    DESCRIPTION
        "The member ID of the device in a stack."
    ::= { ibStackDeviceConfigEntry 1 }

ibStackConfigMemberID OBJECT-TYPE
    SYNTAX      Integer32
    MAX-ACCESS  read-write
    STATUS      current
    DESCRIPTION
        "The configured member ID of the device.  The valid value ranges from
         1 to the value in ibStackMaxMember.  The configured member ID will
         take effect at a reboot if it is unique within the stack."
    ::= { ibStackDeviceConfigEntry 2 }

ibStackPriority OBJECT-TYPE
    SYNTAX      Integer32
    MAX-ACCESS  read-write
    STATUS      current
    DESCRIPTION
        "The priority of a device in the stack.  The valid value ranges from
         1 to the value in ibStackMaxConfigPriority."
    ::= { ibStackDeviceConfigEntry 3 }

ibStackPortNum OBJECT-TYPE
    SYNTAX      Integer32
    MAX-ACCESS  read-only
    STATUS      current
    DESCRIPTION
        "The number of stack ports enabled on a device."
    ::= { ibStackDeviceConfigEntry 4 }

ibStackPortMaxNum OBJECT-TYPE
    SYNTAX      Integer32
    MAX-ACCESS  read-only
    STATUS      current
    DESCRIPTION
        "The maximum number of stack ports on a device."
    ::= { ibStackDeviceConfigEntry 5 }


-- Board Level Configuration
ibStackBoardConfigTable OBJECT-TYPE
    SYNTAX      SEQUENCE OF IbStackBoardConfigEntry
    MAX-ACCESS  not-accessible
    STATUS      current
    DESCRIPTION
        "This table contains objects to manage MPU information for a stack."
    ::= { ibStack 3 }

ibStackBoardConfigEntry OBJECT-TYPE
    SYNTAX      IbStackBoardConfigEntry
    MAX-ACCESS  not-accessible
    STATUS      current
    DESCRIPTION
        "This table contains objects to manage MPU information for a stack."
    INDEX
        {
            entPhysicalIndex
        }
    ::= { ibStackBoardConfigTable 1 }

IbStackBoardConfigEntry ::= SEQUENCE
    {
        ibStackBoardRole              INTEGER,
        ibStackBoardBelongtoMember    Integer32
    }

ibStackBoardRole OBJECT-TYPE
    SYNTAX      INTEGER
        {
            slave(1),
            master(2),
            loading(3),
            other(4)
        }
    MAX-ACCESS  read-only
    STATUS      current
    DESCRIPTION
        "The role of the MPU in a stack.

        slave: Standby MPU
        master: Master MPU
        loading: Standby MPU is loading the software image from the master.
        other: other"
    ::= { ibStackBoardConfigEntry 1 }

ibStackBoardBelongtoMember OBJECT-TYPE
    SYNTAX      Integer32
    MAX-ACCESS  read-only
    STATUS      current
    DESCRIPTION
        "Member ID of the device that holds the current board."
    ::= { ibStackBoardConfigEntry 2 }


-- stack port Information
ibStackPortInfoTable OBJECT-TYPE
    SYNTAX      SEQUENCE OF IbStackPortInfoEntry
    MAX-ACCESS  not-accessible
    STATUS      current
    DESCRIPTION
        "This table contains objects to manage stack port information
         for IRF stacked devices."
    ::= { ibStack 4 }

ibStackPortInfoEntry OBJECT-TYPE
    SYNTAX      IbStackPortInfoEntry
    MAX-ACCESS  not-accessible
    STATUS      current
    DESCRIPTION
        "This table contains objects to manage stack port information
         for IRF stacked devices."
    INDEX
        {
            ibStackMemberID,
            ibStackPortIndex
        }
    ::= { ibStackPortInfoTable 1 }

IbStackPortInfoEntry ::= SEQUENCE
    {
        ibStackPortIndex     Integer32,
        ibStackPortEnable    INTEGER,
        ibStackPortStatus    INTEGER,
        ibStackNeighbor      Integer32,
        ibStackPortForwardingPath    OCTET STRING
    }

ibStackPortIndex OBJECT-TYPE
    SYNTAX      Integer32
    MAX-ACCESS  accessible-for-notify
    STATUS      current
    DESCRIPTION
        "The index of a stack port of the device."
    ::= { ibStackPortInfoEntry 1 }

ibStackPortEnable OBJECT-TYPE
    SYNTAX      INTEGER
        {
            disabled(1),
            enabled(2)
        }
    MAX-ACCESS  read-only
    STATUS      current
    DESCRIPTION
        "The status of a stack port of the device.  If no physical
         interfaces are added to the stack port, its status is disabled.
         If the stack port has physical interfaces, its status is enabled.

        disabled: The stack port is disabled.
        enabled: The stack port is enabled."
    ::= { ibStackPortInfoEntry 2 }

ibStackPortStatus OBJECT-TYPE
    SYNTAX      INTEGER
        {
            up(1),
            down(2),
            silent(3),
            disabled(4)
        }
    MAX-ACCESS  read-only
    STATUS      current
    DESCRIPTION
        "The link status of a stack port on the device.

        up: A physical link is present on the stack port.
        down: No physical link is present on the stack port.
        silent: The link state of the stack port is up,
                but the port can't transmit or receive traffic.
        disabled: The stack port doesn't contain physical links."
    ::= { ibStackPortInfoEntry 3 }

ibStackNeighbor OBJECT-TYPE
    SYNTAX      Integer32
    MAX-ACCESS  read-only
    STATUS      current
    DESCRIPTION
        "The member ID of the stack port's neighbor.  0 means no
         neighbor exists."
    ::= { ibStackPortInfoEntry 4 }

ibStackPortForwardingPath OBJECT-TYPE
    SYNTAX      OCTET STRING (SIZE(0..511))
    MAX-ACCESS  read-only
    STATUS      current
    DESCRIPTION
        "List of egress member IDs on a stack port.
         Each member device uses the egress member ID lists to choose the outgoing
         stack port for known unicast frames to be sent out of other member devices.
         The egress member ID lists are comma separated.
         A zero-length string means no egress members exist.

         For example:
           In a ring stack of 1-2-3-4-5-7-1,
           if ibStackPortForwardingPath.1.1 returns '7,5,4',
           IRF-port 1/1 will be the outgoing port for frames to reach members 7, 5,
           and 4 from member 1."
    ::= { ibStackPortInfoEntry 5 }

-- Physical interface Information
ibStackPhyPortInfoTable OBJECT-TYPE
    SYNTAX      SEQUENCE OF IbStackPhyPortInfoEntry
    MAX-ACCESS  not-accessible
    STATUS      current
    DESCRIPTION
        "This table contains objects to manage information about physical
         interfaces that can be used for IRF stacking."
    ::= { ibStack 5 }

ibStackPhyPortInfoEntry OBJECT-TYPE
    SYNTAX      IbStackPhyPortInfoEntry
    MAX-ACCESS  not-accessible
    STATUS      current
    DESCRIPTION
        "This table contains objects to manage information about physical
         interfaces that can be used for IRF stacking."
    INDEX
        {
            entPhysicalIndex
        }
    ::= { ibStackPhyPortInfoTable 1 }

IbStackPhyPortInfoEntry ::= SEQUENCE
    {
        ibStackBelongtoPort    Integer32
    }

ibStackBelongtoPort OBJECT-TYPE
    SYNTAX      Integer32
    MAX-ACCESS  read-write
    STATUS      current
    DESCRIPTION
        "The index of the stack port to which the physical interface is added.
         0 means the physical interface is not added to any stack port.
         The value will take effect when IRF is enabled on the device."
    ::= { ibStackPhyPortInfoEntry 1 }

--
-- Notification definitions
--
-- =================================================================
-- Traps are defined below.
ibStackTrap OBJECT IDENTIFIER ::= { ibStack 6 }

ibStackTrapOjbects OBJECT IDENTIFIER ::= { ibStackTrap 0 }
-- All trap definitions should be placed under this object.

ibStackPortLinkStatusChange  NOTIFICATION-TYPE
    OBJECTS
        {
            ibStackMemberID,
            ibStackPortIndex,
            ibStackPortStatus
        }

    STATUS      current
    DESCRIPTION
        "The ibStackPortLinkStatusChange trap indicates that the link status
         of the stack port has changed."
    ::= { ibStackTrapOjbects 1 }

ibStackTopologyChange  NOTIFICATION-TYPE
    OBJECTS
        {
            ibStackTopology
        }
    STATUS      current
    DESCRIPTION
        "The ibStackTopologyChange trap indicates that the topology type of
         the IRF stack has changed."
    ::= { ibStackTrapOjbects 2 }

ibStackMadBfdChangeNormal NOTIFICATION-TYPE
    OBJECTS
        {
            ifIndex,
            ifDescr
        }
    STATUS      current
    DESCRIPTION
        "The ibStackMadBfdChangeNormal trap indicates that the BFD MAD function
        changed to the normal state."
    ::= { ibStackTrapOjbects 3 }

ibStackMadBfdChangeFailure NOTIFICATION-TYPE
    OBJECTS
        {
            ifIndex,
            ifDescr
        }
    STATUS      current
    DESCRIPTION
        "The ibStackMadBfdChangeFailure trap indicates that the BFD MAD function
        changed to the failure state."
    ::= { ibStackTrapOjbects 4 }

ibStackMadLacpChangeNormal NOTIFICATION-TYPE
    OBJECTS
        {
            ifIndex,
            ifDescr
        }
    STATUS      current
    DESCRIPTION
        "The ibStackMadLacpChangeNormal trap indicates that the LACP MAD function
        changed to the normal state."
    ::= { ibStackTrapOjbects 5 }

ibStackMadLacpChangeFailure NOTIFICATION-TYPE
    OBJECTS
        {
            ifIndex,
            ifDescr
        }
    STATUS      current
    DESCRIPTION
        "The ibStackMadLacpChangeFailure trap indicates that the LACP MAD function
        changed to the failure state."
    ::= { ibStackTrapOjbects 6 }

ibStackPhysicalIntfLinkUp NOTIFICATION-TYPE
    OBJECTS
        {
            ibStackMemberID,
            ibStackPortIndex,
            ibStackPhysicalIntfName
        }
    STATUS      current
    DESCRIPTION
        "The ibStackPhysicalIntfLinkUp trap indicates that the status
         of the stack physical interface has changed to the up state."
    ::= { ibStackTrapOjbects 7 }

ibStackPhysicalIntfLinkDown NOTIFICATION-TYPE
    OBJECTS
        {
            ibStackMemberID,
            ibStackPortIndex,
            ibStackPhysicalIntfName
        }
    STATUS      current
    DESCRIPTION
        "The ibStackPhysicalIntfLinkDown trap indicates that the status
         of the stack physical interface has changed to the down state."
    ::= { ibStackTrapOjbects 8 }

ibStackPhysicalIntfRxTimeout NOTIFICATION-TYPE
    OBJECTS
        {
            ibStackMemberID,
            ibStackPortIndex,
            ibStackPhysicalIntfName
        }
    STATUS      current
    DESCRIPTION
        "The ibStackPhysicalIntfRxTimeout trap indicates that the timer for the stack
         physical interface to receive packets has timed out."
    ::= { ibStackTrapOjbects 9 }

ibStackMemberAdd NOTIFICATION-TYPE
    OBJECTS
        {
            ibStackMemberID,
            ibStackMacAddress
        }
    STATUS      current
    DESCRIPTION
        "The ibStackMemberAdd trap indicates that
         the new stack member has joined."
    ::= { ibStackTrapOjbects 10 }

ibStackMemberLeave NOTIFICATION-TYPE
    OBJECTS
        {
            ibStackMemberID,
            ibStackMacAddress
        }
    STATUS      current
    DESCRIPTION
        "The ibStackMemberLeave trap indicates that
         the stack member has left."
    ::= { ibStackTrapOjbects 11 }

ibStackLinkUp NOTIFICATION-TYPE
    OBJECTS
        {
            ibStackPortIndex
        }
    STATUS      current
    DESCRIPTION
        "The ibStackLinkUp trap indicates that
         the stack logical interface has changed to the up state."
    ::= { ibStackTrapOjbects 12 }

ibStackLinkDown NOTIFICATION-TYPE
    OBJECTS
        {
            ibStackPortIndex
        }
    STATUS      current
    DESCRIPTION
        "The ibStackLinkDown trap indicates that
         the stack logical interface has changed to the down state."
    ::= { ibStackTrapOjbects 13 }

ibStackMemberLimit NOTIFICATION-TYPE
    OBJECTS
        {
            ibStackMemberThreshold
        }
    STATUS      current
    DESCRIPTION
        "The ibStackMemberLimit trap indicates that
         the number of stack members reached the upper limit, and new members failed to join the stack."
    ::= { ibStackTrapOjbects 14}

ibStackMemberPortLoopAlarm NOTIFICATION-TYPE
    OBJECTS
        {
            ibStackPortIndex
        }
    STATUS      current
    DESCRIPTION
        "The ibStackMemberPortLoopAlarm trap indicates that
         error packets are being forwarded in a ring on the stack port."
    ::= { ibStackTrapOjbects 15}

ibStackMemberPortLoopAlarmRecover NOTIFICATION-TYPE
    OBJECTS
        {
            ibStackPortIndex
        }
    STATUS      current
    DESCRIPTION
        "The ibStackMemberPortLoopAlarmRecover trap indicates that
         the fault of error packets' circular forwarding on the stack port is recovered."
    ::= { ibStackTrapOjbects 16}

ibStackBrigdgeMacChange NOTIFICATION-TYPE
    OBJECTS
        {
            ibStackMemberID
        }
    STATUS      current
    DESCRIPTION
        "The ibStackBrigdgeMacChange trap indicates that
         the MAC address of the stack system has changed to that of the new primary device."
    ::= { ibStackTrapOjbects 17}

ibStackLogicStackPortLinkErr NOTIFICATION-TYPE
    OBJECTS
        {
            ibStackLocalPhysicalIntfName,
            ibStackPeerPhysicalIntfName,
            ibStackLinkErrReason
        }
    STATUS      current
    DESCRIPTION
        "The ibStackLogicStackPortLinkErr trap indicates that
         the logical stack port has incorrectly connected."
    ::= { ibStackTrapOjbects 18}

ibStackLogicStackPortLinkErrRecover NOTIFICATION-TYPE
    OBJECTS
        {
            ibStackLocalPhysicalIntfName,
            ibStackPeerPhysicalIntfName,
            ibStackLinkErrReason
        }
    STATUS      current
    DESCRIPTION
        "The ibStackLogicStackPortLinkErrRecover trap indicates that
         the logical stack port is recovered."
    ::= { ibStackTrapOjbects 19}

ibStackPortConfigureFailure NOTIFICATION-TYPE
    OBJECTS
        {
            ibStackMemberID
        }
    STATUS      current
    DESCRIPTION
        "The ibStackPortConfigureFailure trap indicates that
         Stack port configuration failed."
    ::= { ibStackTrapOjbects 20}

ibStackSetUpFailure NOTIFICATION-TYPE
    OBJECTS
        {
            ibStackLocalSlotID,
            ibStackPeerSlotID,
            ibStackSetUpFailureReason
        }
    STATUS      current
    DESCRIPTION
        "The ibStackSetUpFailure trap indicates that
         Stack creation failed."
    ::= { ibStackTrapOjbects 21}

ibStackTrapObjectDefinitions OBJECT IDENTIFIER ::= { ibStackTrap 1 }
-- All objects used for TRAP only are defined here.

ibStackPhysicalIntfName OBJECT-TYPE
    SYNTAX         OCTET STRING (SIZE(1..255))
    MAX-ACCESS     accessible-for-notify
    STATUS         current
    DESCRIPTION
        "The textual name of the stack physical interface."
    ::= { ibStackTrapObjectDefinitions 1 }

ibStackMacAddress OBJECT-TYPE
    SYNTAX         MacAddress
    MAX-ACCESS     accessible-for-notify
    STATUS         current
    DESCRIPTION
        "The textual name of the stack mac address."
    ::= { ibStackTrapObjectDefinitions 2 }

ibStackMemberThreshold OBJECT-TYPE
    SYNTAX         OCTET STRING (SIZE(1..255))
    MAX-ACCESS     accessible-for-notify
    STATUS         current
    DESCRIPTION
        "The textual name of the stack member threshold"
    ::= { ibStackTrapObjectDefinitions 3 }

ibStackLocalPhysicalIntfName OBJECT-TYPE
    SYNTAX         OCTET STRING (SIZE(1..255))
    MAX-ACCESS     accessible-for-notify
    STATUS         current
    DESCRIPTION
        "The textual name of the stack local physical interface."
    ::= { ibStackTrapObjectDefinitions 4 }

ibStackPeerPhysicalIntfName OBJECT-TYPE
    SYNTAX         OCTET STRING (SIZE(1..255))
    MAX-ACCESS     accessible-for-notify
    STATUS         current
    DESCRIPTION
        "The textual name of the stack peer physical interface."
    ::= { ibStackTrapObjectDefinitions 5 }

ibStackLinkErrReason OBJECT-TYPE
    SYNTAX         DisplayString (SIZE(1..512))
    MAX-ACCESS     accessible-for-notify
    STATUS         current
    DESCRIPTION
        "The textual name of the stack link error reason."
    ::= { ibStackTrapObjectDefinitions 6 }

ibStackLocalSlotID OBJECT-TYPE
    SYNTAX         Integer32 (1..32)
    MAX-ACCESS     accessible-for-notify
    STATUS         current
    DESCRIPTION
        "Local stack member slot number"
    ::= { ibStackTrapObjectDefinitions 7 }

ibStackPeerSlotID OBJECT-TYPE
    SYNTAX         Integer32 (1..32)
    MAX-ACCESS     accessible-for-notify
    STATUS         current
    DESCRIPTION
        "Peer stack member slot number"
    ::= { ibStackTrapObjectDefinitions 8 }

ibStackSetUpFailureReason OBJECT-TYPE
    SYNTAX         DisplayString (SIZE(1..512))
    MAX-ACCESS     accessible-for-notify
    STATUS         current
    DESCRIPTION
        "The textual name of the stack creation failed error reason."
    ::= { ibStackTrapObjectDefinitions 9 }

END
