-- =====================================================================
-- Copyright (C) 2023 Intelbras S.A. All rights reserved.
--
-- Description: The file defines a MIB to provide WLAN roaming configuration.
-- Reference:
-- Version: V1.3
-- History:
-- V1.0 2008-7-23 created by heziqi
-- V1.1 2009-05-07 modified by Li Yugang
--      Add ibDot11RoamStatisGroup to ibDot11ROAM.
-- V1.2 2009-12-24 modified for Guangdong Mobile
--      Add ibDot11InterACRoamOutSuccCnt to ibDot11RoamStatisGroup.
--      2010-08-04 modefied by l07769 for Guangdong CMCC
--      Add ibDot11IntraACRoamingSuccCnt2, ibDot11InterACRoamingSuccCnt2
--      and ibDot11InterACRoamOutSuccCnt2 to ibDot11RoamStatis2Group.
-- V1.3 2016-3-11 modified by yubo 04460
--      Add ibDot11InterACRoamInSuccCnt to ibDot11RoamStatusGroup
--      Add ibDot11InterACRoamInSuccCnt2 to ibDot11RoamStatis2Group
-- =====================================================================
IB-DOT11-ROAM-MIB DEFINITIONS ::= BEGIN

IMPORTS
        TruthValue,
        MacAddress,
        RowStatus,
        TEXTUAL-CONVENTION
    FROM SNMPv2-TC
        MODULE-IDENTITY,
        OBJECT-TYPE,
        Integer32,
        Counter32
    FROM SNMPv2-SMI
        InetAddressType,
        InetAddress
    FROM INET-ADDRESS-MIB
        ibDot11
    FROM IB-DOT11-REF-MIB;

ibDot11ROAM MODULE-IDENTITY
    LAST-UPDATED "201603111800Z"        -- Mar 11, 2016 at 18:00 GMT
    ORGANIZATION
        "Intelbras S.A. Industria de Telecomunicacao Eletronica Brasileria."
    CONTACT-INFO
        ""
    DESCRIPTION
        "This MIB provides information about WLAN roaming configuration.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        BSS
        IEEE 802.11 Basic Service Set (Radio Cell).  The
        BSS of an AP comprises of the stations directly
        associating with the AP.

        Radio
        The chip set to receive and send wireless signal.

        HA
        The AC to which a wireless station is connected by
        associating with an AP for the first time is the
        HA of the station.

        FA
        An AC that is other than the HA and to which a
        station is currently connected is an FA of the
        station.

        Fast-roam capable station
        A wireless station which directly associates to
        a fast-roam service (rsn+dot1X) with one AC for
        the first time.

        Roam-out station
        A wireless station which has associated with an
        AC other than the HA in the mobility-group is
        referred to as a roam-out station at its HA.

        Roam-in station
        A wireless station which has associated with an
        AC other than the HA in the mobility-group is
        referred to as a roam-in station at the FA.

        Intra-AC roaming
        A procedure where a wireless station roams from
        one AP to another AP, which are connected to the
        same AC.

        Inter-AC roaming
        A procedure where a wireless station roams from
        one AP to another AP, which are connected to
        different ACs.

        Inter-AC fast roaming capability
        If a station uses 802.1x (RSN) authentication
        through negotiation, this station has inter-AC
        fast roaming capability.

        WLAN-tunnel
        One type of layer 2 interface which is bound with
        an IACTP data tunnel and used to tunnel
        unicast/broadcast frames between ACs."
    REVISION "201603111800Z"        -- Mar 11, 2016 at 18:00 GMT
    DESCRIPTION
            "add new nodes."
    REVISION "201008041800Z"        -- Aug 04, 2010 at 18:00 GMT
    DESCRIPTION
            "Modified to add new ibDot11RoamStatis2Group."
    REVISION "200905072000Z"
    DESCRIPTION
            "Modified to add new ibDot11RoamStatisGroup."
    REVISION "200807231200Z"
    DESCRIPTION
            "The initial revision of this MIB module."
    ::= { ibDot11 10 }

-- ==================================================================
-- Textual Conventions
-- ==================================================================
IbDot11RoamMobileTunnelType ::=  TEXTUAL-CONVENTION
    STATUS      current
    DESCRIPTION
        "The protocol type of the mobility-tunnel.
        This object has two defined values:
        - 'ipv4', which indicates that the protocol type of the mobility-tunnel
          is IPv4.
        - 'ipv6', which indicates that the protocol type of the mobility-tunnel
          is IPv6.
        "
    SYNTAX      INTEGER
        {
            ipv4(1),
            ipv6(2)
        }

IbDot11RoamAuthMode ::=  TEXTUAL-CONVENTION
    STATUS      current
    DESCRIPTION
        "The authentication mode of the mobility-tunnel.
        This object has two defined values:
        - 'none', which indicates that the authentication mode of the
          mobility-tunnel is None.
        - 'md5', which indicates that the authentication mode of the
          mobility-tunnel is MD5.
        "
    SYNTAX      INTEGER
        {
            none(1),
            md5(2)
        }

IbDot11RoamIACTPStatus ::=  TEXTUAL-CONVENTION
    STATUS      current
    DESCRIPTION
        "The status of IACTP state machine."
    SYNTAX      INTEGER
        {
            init(1),
            idle(2),
            joinRequestWait(3),
            joinResponseWait(4),
            joinConfirmWait(5),
            joinError(6),
            run(7)
        }

-- ==================================================================
-- Major sections
-- ==================================================================
ibDot11RoamCfgGroup OBJECT IDENTIFIER  ::= { ibDot11ROAM 1 }
--  Roaming Configuration Group has the following children:
--  ibDot11MobGrpTable            ::= { ibDot11RoamCfgGroup 1 }
--  ibDot11MobGrpMemberTable      ::= { ibDot11RoamCfgGroup 2 }

ibDot11RoamStatusGroup OBJECT IDENTIFIER  ::= { ibDot11ROAM 2 }
--  Roaming Status Group has the following children:
--  ibDot11RoamInInfoTable             ::= { ibDot11RoamStatusGroup 1 }
--  ibDot11RoamOutInfoTable            ::= { ibDot11RoamStatusGroup 2 }
--  ibDot11RoamTrackTable              ::= { ibDot11RoamStatusGroup 3 }

ibDot11RoamStatisGroup OBJECT IDENTIFIER  ::= { ibDot11ROAM 3 }
--  Roaming Statis Group has the following children:
--  ibDot11IntraACRoamingSuccCnt       ::= { ibDot11RoamStatusGroup 1 }
--  ibDot11InterACRoamingSuccCnt       ::= { ibDot11RoamStatusGroup 2 }
--  ibDot11InterACRoamOutSuccCnt       ::= { ibDot11RoamStatusGroup 3 }
--  ibDot11InterACRoamInSuccCnt        ::= { ibDot11RoamStatusGroup 4 }

ibDot11RoamStatis2Group OBJECT IDENTIFIER  ::= { ibDot11ROAM 4 }
--  Roaming Statis Group has the following children:
--  ibDot11IntraACRoamingSuccCnt2     ::= { ibDot11RoamStatus2Group 1 }
--  ibDot11InterACRoamingSuccCnt2     ::= { ibDot11RoamStatus2Group 2 }
--  ibDot11InterACRoamOutSuccCnt2     ::= { ibDot11RoamStatus2Group 3 }
--  ibDot11InterACRoamInSuccCnt2      ::= { ibDot11RoamStatus2Group 4 }

-- ==================================================================
-- ibDot11RoamCfgGroup Definition
-- ==================================================================
-- ==================================================================
-- ibDot11MobGrpTable Definition
-- ==================================================================
ibDot11MobGrpTable OBJECT-TYPE
    SYNTAX      SEQUENCE OF IbDot11MobGrpEntry
    MAX-ACCESS  not-accessible
    STATUS      current
    DESCRIPTION
        "The table defines the parameters for roaming group configuration."
    ::= { ibDot11RoamCfgGroup 1 }

ibDot11MobGrpEntry OBJECT-TYPE
    SYNTAX      IbDot11MobGrpEntry
    MAX-ACCESS  not-accessible
    STATUS      current
    DESCRIPTION
        "This entry contains information of mobile group."
    INDEX
        {
            ibDot11MobGrpName
        }
    ::= { ibDot11MobGrpTable 1 }

IbDot11MobGrpEntry ::= SEQUENCE
    {
        ibDot11MobGrpName        OCTET STRING,
        ibdot11MobGrpTunnelType  IbDot11RoamMobileTunnelType,
        ibDot11MobGrpSrcIPAddr   InetAddress,
        ibDot11MobGrpAuthMode    IbDot11RoamAuthMode,
        ibDot11MobGrpAuthKey     OCTET STRING,
        ibDot11MobGrpEnable      TruthValue,
        ibDot11MobGrpRowStatus   RowStatus
    }

ibDot11MobGrpName OBJECT-TYPE
    SYNTAX      OCTET STRING(SIZE(1..15))
    MAX-ACCESS  not-accessible
    STATUS      current
    DESCRIPTION
        "Represents the name of roam group."
    ::= { ibDot11MobGrpEntry 1 }

ibdot11MobGrpTunnelType OBJECT-TYPE
    SYNTAX      IbDot11RoamMobileTunnelType
    MAX-ACCESS  read-create
    STATUS      current
    DESCRIPTION
        "Represents the protocol type of mobility-tunnel."
    DEFVAL      { ipv4 }
    ::= { ibDot11MobGrpEntry 2 }

ibDot11MobGrpSrcIPAddr OBJECT-TYPE
    SYNTAX      InetAddress
    MAX-ACCESS  read-create
    STATUS      current
    DESCRIPTION
        "Represents the IP address of tunnel source.  The IP address
         type must be the same as ibdot11MobGrpTunnelType.
         The default value is zero."
    ::= { ibDot11MobGrpEntry 3 }

ibDot11MobGrpAuthMode OBJECT-TYPE
    SYNTAX      IbDot11RoamAuthMode
    MAX-ACCESS  read-create
    STATUS      current
    DESCRIPTION
        "Represents the authentication mode of IACTP tunnel.
         This object can be used to enable IACTP control message
         integrity authentication."
    DEFVAL      { none }
    ::= { ibDot11MobGrpEntry 4 }

ibDot11MobGrpAuthKey OBJECT-TYPE
    SYNTAX      OCTET STRING(SIZE(0..16))
    MAX-ACCESS  read-create
    STATUS      current
    DESCRIPTION
        "Represents the authentication key of IACTP tunnel.
         Authentication key to be used with the given
         authentication method.
         This object can not be modified when the value of
         ibDot11MobGrpAuthMode is 'none'."
    ::= { ibDot11MobGrpEntry 5 }

ibDot11MobGrpEnable OBJECT-TYPE
    SYNTAX      TruthValue
    MAX-ACCESS  read-create
    STATUS      current
    DESCRIPTION
        "State of a mobile group.
         'true'  : The WLAN mobility group will be enabled.
         'false' : The inter-AC tunnel communication for the
                   mobility group will be disabled.
         A mobility group can be enabled only when the source
         IP address is configured.  The other objects in this entry
         can become effective only when mobility group is enabled.
         The other objects in this entry can not be modified
         after enabling mobility group."
    DEFVAL      { false }
    ::= { ibDot11MobGrpEntry 6 }

ibDot11MobGrpRowStatus OBJECT-TYPE
    SYNTAX      RowStatus
    MAX-ACCESS  read-create
    STATUS      current
    DESCRIPTION
        "The status of this table entry."
    ::= { ibDot11MobGrpEntry 7 }

-- ==================================================================
-- ibDot11MobGrpMemberTable Definition
-- ==================================================================

ibDot11MobGrpMemberTable OBJECT-TYPE
    SYNTAX      SEQUENCE OF IbDot11MobGrpMemberEntry
    MAX-ACCESS  not-accessible
    STATUS      current
    DESCRIPTION
        "The table defines the parameters for roaming member configuration."
    ::= { ibDot11RoamCfgGroup 2 }

ibDot11MobGrpMemberEntry OBJECT-TYPE
    SYNTAX      IbDot11MobGrpMemberEntry
    MAX-ACCESS  not-accessible
    STATUS      current
    DESCRIPTION
        "This entry contains information of mobile group member."
    INDEX
        {
            ibDot11MobGrpName,
            ibDot11MobGrpMemberIpAddr
        }
    ::= { ibDot11MobGrpMemberTable 1 }

IbDot11MobGrpMemberEntry ::= SEQUENCE
    {
        ibDot11MobGrpMemberIpAddr      InetAddress,
        ibDot11MobGrpMemberStatus      IbDot11RoamIACTPStatus,
        ibDot11MobGrpMemberIf          OCTET STRING,
        ibDot11MobGrpMemberUpTime      Integer32,
        ibDot11MobGrpMemberRowStatus   RowStatus
    }

ibDot11MobGrpMemberIpAddr OBJECT-TYPE
    SYNTAX      InetAddress
    MAX-ACCESS  not-accessible
    STATUS      current
    DESCRIPTION
        "Represents the IP address of group member.  It can not be
         the same as the source IP address of the mobile group.
         The address type must be the same as the ibdot11MobGrpTunnelType."
    ::= { ibDot11MobGrpMemberEntry 1 }

ibDot11MobGrpMemberStatus OBJECT-TYPE
    SYNTAX      IbDot11RoamIACTPStatus
    MAX-ACCESS  read-only
    STATUS      current
    DESCRIPTION
        "Represents the status of group member."
    ::= { ibDot11MobGrpMemberEntry 2 }

ibDot11MobGrpMemberIf OBJECT-TYPE
    SYNTAX      OCTET STRING
    MAX-ACCESS  read-only
    STATUS      current
    DESCRIPTION
        "Represents the tunnel interface name of group member."
    ::= { ibDot11MobGrpMemberEntry 3 }

ibDot11MobGrpMemberUpTime OBJECT-TYPE
    SYNTAX      Integer32
    UNITS       "second"
    MAX-ACCESS  read-only
    STATUS      current
    DESCRIPTION
        "Represents the sustaining time from tunnel up.  If tunnel
         is down, MemberUpTime is zero."
    ::= { ibDot11MobGrpMemberEntry 4 }

ibDot11MobGrpMemberRowStatus OBJECT-TYPE
    SYNTAX      RowStatus
    MAX-ACCESS  read-create
    STATUS      current
    DESCRIPTION
        "The status of this table entry."
    ::= { ibDot11MobGrpMemberEntry 5 }

-- ==================================================================
-- ibDot11RoamStatusGroup Definition
-- ==================================================================
-- ==================================================================
-- ibDot11RoamInInfoTable Definition
-- ==================================================================
ibDot11RoamInInfoTable OBJECT-TYPE
    SYNTAX      SEQUENCE OF IbDot11RoamInInfoEntry
    MAX-ACCESS  not-accessible
    STATUS      current
    DESCRIPTION
        "The table can used to display the information of roaming in client."
    ::= { ibDot11RoamStatusGroup 1 }

ibDot11RoamInInfoEntry OBJECT-TYPE
    SYNTAX      IbDot11RoamInInfoEntry
    MAX-ACCESS  not-accessible
    STATUS      current
    DESCRIPTION
        "This entry contains information of roaming in client."
    INDEX
        {
            ibDot11RoamClientMAC
        }
    ::= { ibDot11RoamInInfoTable 1 }

IbDot11RoamInInfoEntry ::= SEQUENCE
    {
        ibDot11RoamClientMAC         MacAddress,
        ibDot11RoamInClientBSSID     MacAddress,
        ibDot11RoamInClientVlanID    Integer32,
        ibDot11RoamInHomeACIPType    InetAddressType,
        ibDot11RoamInHomeACIPAddr    InetAddress
    }

ibDot11RoamClientMAC OBJECT-TYPE
    SYNTAX      MacAddress
    MAX-ACCESS  not-accessible
    STATUS      current
    DESCRIPTION
        "Represents the MAC address of roaming in client."
    ::= { ibDot11RoamInInfoEntry 1 }

ibDot11RoamInClientBSSID OBJECT-TYPE
    SYNTAX      MacAddress
    MAX-ACCESS  read-only
    STATUS      current
    DESCRIPTION
        "Represents BSSID of the AP to which the Roam-In client is associated."
    ::= { ibDot11RoamInInfoEntry 2 }

ibDot11RoamInClientVlanID OBJECT-TYPE
    SYNTAX      Integer32
    MAX-ACCESS  read-only
    STATUS      current
    DESCRIPTION
        "Represents the VLAN ID of Roam-In client."
    ::= { ibDot11RoamInInfoEntry 3 }

ibDot11RoamInHomeACIPType OBJECT-TYPE
    SYNTAX      InetAddressType
    MAX-ACCESS  read-only
    STATUS      current
    DESCRIPTION
        "Represents the protocol type of home AC address."
    ::= { ibDot11RoamInInfoEntry 4 }

ibDot11RoamInHomeACIPAddr OBJECT-TYPE
    SYNTAX      InetAddress
    MAX-ACCESS  read-only
    STATUS      current
    DESCRIPTION
        "Represents the address of home AC."
    ::= { ibDot11RoamInInfoEntry 5 }

-- ==================================================================
-- ibDot11RoamOutInfoTable Definition
-- ==================================================================

ibDot11RoamOutInfoTable OBJECT-TYPE
    SYNTAX      SEQUENCE OF IbDot11RoamOutInfoEntry
    MAX-ACCESS  not-accessible
    STATUS      current
    DESCRIPTION
        "The table can used to display the information of roaming out client."
    ::= { ibDot11RoamStatusGroup 2 }

ibDot11RoamOutInfoEntry OBJECT-TYPE
    SYNTAX      IbDot11RoamOutInfoEntry
    MAX-ACCESS  not-accessible
    STATUS      current
    DESCRIPTION
        "This entry contains information of roaming out client."
    INDEX
        {
            ibDot11RoamClientMAC
        }
    ::= { ibDot11RoamOutInfoTable 1 }

IbDot11RoamOutInfoEntry ::= SEQUENCE
    {
        ibDot11RoamOutClientBSSID       MacAddress,
        ibDot11RoamOutClientVlanID      Integer32,
        ibDot11RoamOutForeignACIPType   InetAddressType,
        ibDot11RoamOutForeignACIPAddr   InetAddress,
        ibDot11RoamOutClientUpTime      Integer32
    }

ibDot11RoamOutClientBSSID OBJECT-TYPE
    SYNTAX      MacAddress
    MAX-ACCESS  read-only
    STATUS      current
    DESCRIPTION
        "Represents the BSSID of the AP to which the Roam-Out client is
         associated."
    ::= { ibDot11RoamOutInfoEntry 1 }

ibDot11RoamOutClientVlanID OBJECT-TYPE
    SYNTAX      Integer32
    MAX-ACCESS  read-only
    STATUS      current
    DESCRIPTION
        "Represents the VLAN ID of Roam-Out client."
    ::= { ibDot11RoamOutInfoEntry 2 }

ibDot11RoamOutForeignACIPType OBJECT-TYPE
    SYNTAX      InetAddressType
    MAX-ACCESS  read-only
    STATUS      current
    DESCRIPTION
        "Represents the protocol type of foreign AC address."
    ::= { ibDot11RoamOutInfoEntry 3 }

ibDot11RoamOutForeignACIPAddr OBJECT-TYPE
    SYNTAX      InetAddress
    MAX-ACCESS  read-only
    STATUS      current
    DESCRIPTION
        "Represents the address of foreign AC."
    ::= { ibDot11RoamOutInfoEntry 4 }

ibDot11RoamOutClientUpTime OBJECT-TYPE
    SYNTAX      Integer32
    UNITS       "second"
    MAX-ACCESS  read-only
    STATUS      current
    DESCRIPTION
        "Represents how long the Roam-Out client is associated with the foreign
         AC."
    ::= { ibDot11RoamOutInfoEntry 5 }

-- ==================================================================
-- ibDot11RoamTrackTable Definition
-- ==================================================================
ibDot11RoamTrackTable OBJECT-TYPE
    SYNTAX      SEQUENCE OF IbDot11RoamTrackEntry
    MAX-ACCESS  not-accessible
    STATUS      current
    DESCRIPTION
        "The table contains the roam-track information of a
         specified client on the client's HA."
    ::= { ibDot11RoamStatusGroup 3 }

ibDot11RoamTrackEntry OBJECT-TYPE
    SYNTAX      IbDot11RoamTrackEntry
    MAX-ACCESS  not-accessible
    STATUS      current
    DESCRIPTION
        "This entry contains information of a specified client on the
         client's HA."
    INDEX
        {
            ibDot11RoamTrackIndex
        }
    ::= { ibDot11RoamTrackTable 1 }

IbDot11RoamTrackEntry ::= SEQUENCE
    {
        ibDot11RoamTrackIndex        Integer32,
        ibDot11RoamTrackClientMAC    MacAddress,
        ibDot11RoamTrackBSSID        MacAddress,
        ibDot11RoamTrackUpTime       Integer32,
        ibDot11RoamTrackACIPType     InetAddressType,
        ibDot11RoamTrackACIPAddr     InetAddress
    }

ibDot11RoamTrackIndex OBJECT-TYPE
    SYNTAX      Integer32
    MAX-ACCESS  not-accessible
    STATUS      current
    DESCRIPTION
        "Represents the index of this entry."
    ::= { ibDot11RoamTrackEntry 1 }

ibDot11RoamTrackClientMAC OBJECT-TYPE
    SYNTAX      MacAddress
    MAX-ACCESS  read-only
    STATUS      current
    DESCRIPTION
        "Represents the MAC address of the roamed client."
    ::= { ibDot11RoamTrackEntry 2 }

ibDot11RoamTrackBSSID OBJECT-TYPE
    SYNTAX      MacAddress
    MAX-ACCESS  read-only
    STATUS      current
    DESCRIPTION
        "Represents the BSSID of the AP with which the client is associated."
    ::= { ibDot11RoamTrackEntry 3 }

ibDot11RoamTrackUpTime OBJECT-TYPE
    SYNTAX      Integer32
    UNITS       "second"
    MAX-ACCESS  read-only
    STATUS      current
    DESCRIPTION
        "Represents how long the client is associated with the BSSID."
    ::= { ibDot11RoamTrackEntry 4 }

ibDot11RoamTrackACIPType OBJECT-TYPE
    SYNTAX      InetAddressType
    MAX-ACCESS  read-only
    STATUS      current
    DESCRIPTION
        "Represents the protocol type of the IP address of the access
         controller with which the client is connected."
    ::= { ibDot11RoamTrackEntry 5 }

ibDot11RoamTrackACIPAddr OBJECT-TYPE
    SYNTAX      InetAddress
    MAX-ACCESS  read-only
    STATUS      current
    DESCRIPTION
        "Represents the IP address of the access controller with which
         the client is connected."
    ::= { ibDot11RoamTrackEntry 6 }

-- ==================================================================
-- ibDot11RoamStatisGroup Definition
-- ==================================================================
ibDot11IntraACRoamingSuccCnt OBJECT-TYPE
    SYNTAX      Integer32
    MAX-ACCESS  read-only
    STATUS      current
    DESCRIPTION
        "Represents the count of client successfully roam Intra-AC."
    ::= { ibDot11RoamStatisGroup 1 }

ibDot11InterACRoamingSuccCnt OBJECT-TYPE
    SYNTAX      Integer32
    MAX-ACCESS  read-only
    STATUS      current
    DESCRIPTION
        "Represents the count of client successfully roam in Inter-AC."
    ::= { ibDot11RoamStatisGroup 2 }

ibDot11InterACRoamOutSuccCnt OBJECT-TYPE
    SYNTAX      Integer32
    MAX-ACCESS  read-only
    STATUS      current
    DESCRIPTION
        "Represents the count of client successfully roam out Inter-AC."
    ::= { ibDot11RoamStatisGroup 3 }

ibDot11InterACRoamInSuccCnt OBJECT-TYPE
    SYNTAX      Integer32
    MAX-ACCESS  read-only
    STATUS      current
    DESCRIPTION
        "Represents the number of clients successfully roamed in inter-AC roaming."
    ::= { ibDot11RoamStatisGroup 4 }

-- ==================================================================
-- End of ibDot11RoamStatisGroup Definition
-- ==================================================================

-- ==================================================================
-- ibDot11RoamStatis2Group Definition
-- ==================================================================
ibDot11IntraACRoamingSuccCnt2 OBJECT-TYPE
    SYNTAX      Counter32
    MAX-ACCESS  read-only
    STATUS      current
    DESCRIPTION
        "Represents the count of client successfully roam Intra-AC in Counter32."
    ::= { ibDot11RoamStatis2Group 1 }

ibDot11InterACRoamingSuccCnt2 OBJECT-TYPE
    SYNTAX      Counter32
    MAX-ACCESS  read-only
    STATUS      current
    DESCRIPTION
        "Represents the count of client successfully roam in Inter-AC in Counter32."
    ::= { ibDot11RoamStatis2Group 2 }

ibDot11InterACRoamOutSuccCnt2 OBJECT-TYPE
    SYNTAX      Counter32
    MAX-ACCESS  read-only
    STATUS      current
    DESCRIPTION
        "Represents the count of client successfully roam out Inter-AC in Counter32."
    ::= { ibDot11RoamStatis2Group 3 }

ibDot11InterACRoamInSuccCnt2 OBJECT-TYPE
    SYNTAX      Counter32
    MAX-ACCESS  read-only
    STATUS      current
    DESCRIPTION
        "Represents the number of clients successfully roamed in inter-AC roaming in Counter32."
    ::= { ibDot11RoamStatis2Group 4 }

-- ==================================================================
-- End of ibDot11RoamStatis2Group Definition
-- ==================================================================
END
