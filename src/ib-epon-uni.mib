-- ===========================================================
-- Copyright (C) 2023 Intelbras S.A. All rights reserved.
--
-- Description: Epon MIB
-- Reference:  IF-MIB
-- Version:  V2.2
-- History:
-- V1.0 created by liuhongxu.
--   Initial version 2006-01-10
-- V1.1 Updated by chenzhaojie
--   Add enumeration values to ibEponUniVlanType
-- V1.2 Updated by chenzhaojie 2006-08-02
--   Add ibEponUniOutDroppedFrames
-- V1.3 Updated by chenzhaojie 2007-05-21
--   Add ibEponUniScalarGroup
--   Add enumeration values to ibEponUniVlanType
--   Add ibEponUniPortIsolate, ibEponUniVlanConfiguration
--   ibEponUniAutoNegotiation, ibEponUniRestartAutoNeg,
--   ibEponUniLinkStatus, ibEponUniInterfaceType
--   to ibEponUniSysManTable.
--   Add ibEponUniPortPolicyTable, ibEponUniMulticastTable.
--   Add ibEponUniMulticastControlTable, ibEponUniQosConfIndexNextTable,
--   ibEponUniQosConfTable, ibEponUniQosRuleTable.
-- V1.4 Updated by liuhongxu,andapeng 2007-10-13
--   Add ibEponUniMulticastFastleave to ibEponUniMulticastTable
--   Add ibEponUniMulticastIndex to ibEponUniMulticastControlTable
--   Add ibEponUniVitualCableTest to ibEponUniSysManTable
--   Add ibEponUniMirrorGroupTable, ibEponUniMirrorGroupIdNextTable
--   Add ibEponUniMulticastCtrlInfoTable
--   Add ibEponUniPortPolicyInboundCir,ibEponUniPortPolicyInboundBucketDepth,
--   ibEponUniPortPolicyInboundExtraBurst,ibEponUniPortPolicyOutboundCir
--   to ibEponUniPortPolicyTable.
--   Add ibEponUniMulticastIndexNextTable
--   Modify ibEponUniInterfaceType
-- V1.5 Updated by maguoqiang,wangke,zhaodan 2008-1-14
-- Deleted default values of these leaves:
--      ibEponUniMdi, ibEponUniPriority, ibEponUniVlanType, ibEponUniFlowControl,
--      ibEponUniDuplex, ibEponUniVlanVPNStatus, ibEponUniPortIsolate,
--      ibEponUniAutoNegotiation, ibEponUniVitualCableTest
--   Add ibEponUniMulticastSourceIpList to ibEponUniMulticastControlTable
--   Add ibEponUniMulticastResetInterval to ibEponUniMulticastControlTable
--   Modify ibEponUniVCTCableStatus and add 9 nodes:
--   Add    ibEponUniVCTCableLength
--          ibEponUniVCTImpedanceMismatch
--          ibEponUniVCTPairSkew
--          ibEponUniVCTPairSwap
--          ibEponUniVCTPolaritySwap
--          ibEponUniVCTInsertionLoss
--          ibEponUniVCTReturnLoss
--          ibEponUniVCTNearendCrosstalk to ibEponUniSysManTable
-- V1.6 Updated by zoudian 2008-3-17
--   Add    ibEponUniPortPolicyOutboundPir to ibEponUniPortPolicyTable
--   Modify ibEponUniPortPolicyOutboundCir
-- V1.7 Updated by zhaodan 2008-06-04
--   Add ibEponUniLinkUpTrap and ibEponUniLinkDownTrap.
--   Modify the MAX-ACCESS of ibEponUniIndex to accessible-for-notify.
-- V1.8 Updated by chenchao 2012-11-16
--   Add ibEponUniLoopBackDetectedTrap and ibEponUniLoopBackRecoveredTrap.
-- V1.9 Updated by zhuhaifeng 2018-02-02.
--   Add ibEponCTCAlarmTable and ibEponUniErrorInfo.
--   Add ibEponCTCAlarmTrap and ibEponCTCAlarmRecoverTrap.
--   Add ibUniStatisticsTable.
--   Add ibEponUniMacMax to ibEponUniSysManTable.
--   Modify ibEponUniVlanType and ibEponUniVlanConfiguration to ibEponUniSysManTable.
-- V2.0 Updated by zhuhaifeng 2018-11-28.
--   Add ibUniPoeTable, ibUniPoeInfoTable.
-- V2.1 Updated by yangke 2021-07-08.
--   Modify ibEponUniDescr.
-- V2.2 Updated by yangke 2021-09-10.
--   Modify ibEponUniTrunkPvid and ibEponUniMulticastIndex.
-- =================================================================
IB-EPON-UNI-MIB DEFINITIONS ::= BEGIN

IMPORTS
        ibEpon
    FROM IB-OID-MIB
        ifIndex, ifDescr
    FROM IF-MIB
        Integer32, Unsigned32, IpAddress, OBJECT-TYPE, MODULE-IDENTITY,
        NOTIFICATION-TYPE
    FROM SNMPv2-SMI
        MacAddress, TruthValue, RowStatus
    FROM SNMPv2-TC;

ibEponUni MODULE-IDENTITY
    LAST-UPDATED "202109101049Z"  --September 10, 2021
    ORGANIZATION
        "Intelbras S.A. Industria de Telecomunicacao Eletronica Brasileria."
    CONTACT-INFO
        ""
    DESCRIPTION
        "The objects in this MIB module are used to manage and
        display current configuration of UNI (user network interface)
        which is based on the ONU(Optical Network Unit)."
    REVISION    "202109101049Z"  -- September 10, 2021
    DESCRIPTION "Modify ibEponUniTrunkPvid and ibEponUniMulticastIndex." 
    REVISION    "202107081049Z"  -- July 08, 2021
    DESCRIPTION "Modify ibEponUniDescr."
    REVISION    "201811281049Z"  -- November 28, 2018
    DESCRIPTION "Add ibUniPoeTable, ibUniPoeInfoTable."
    REVISION    "201706061145Z"  -- June 06, 2017
    DESCRIPTION "Add ibEponUniMacMax to ibEponUniSysManTable."
    REVISION    "201703061145Z"  -- March 06, 2017
    DESCRIPTION "Add the objects of ibEponCTCAlarmTable, ibEponUniErrorInfo,
                 ibEponCTCAlarmTrap, ibEponCTCAlarmRecoverTrap, and ibUniStatisticsTable."
    ::= { ibEpon 5 }

ibEponUniSysMan OBJECT IDENTIFIER ::= { ibEponUni 1 }

ibEponUniSysManTable OBJECT-TYPE
    SYNTAX      SEQUENCE OF IbEponUniSysManEntry
    MAX-ACCESS  not-accessible
    STATUS      current
    DESCRIPTION
        "This table defines several UNI system parameters."
    ::= { ibEponUniSysMan 1 }

ibEponUniSysManEntry OBJECT-TYPE
    SYNTAX      IbEponUniSysManEntry
    MAX-ACCESS  not-accessible
    STATUS      current
    DESCRIPTION
        "The entry of ibEponUniSysManTable."
    INDEX
        {
            ifIndex,
            ibEponUniIndex
        }
    ::= { ibEponUniSysManTable 1 }


IbEponUniSysManEntry ::= SEQUENCE
    {
        ibEponUniIndex                     Integer32,
        ibEponUniDescr                     OCTET STRING,
        ibEponUniAdminStatus               INTEGER,
        ibEponUniMdi                       INTEGER,
        ibEponUniPriority                  Integer32,
        ibEponUniVlanType                  INTEGER,
        ibEponUniAccessVlan                Integer32,
        ibEponUniTrunkPvid                 Integer32,
        ibEponUniVLANTrunkAllowListLow     OCTET STRING,
        ibEponUniVLANTrunkAllowListHigh    OCTET STRING,
        ibEponUniInboundLineRate           Integer32,
        ibEponUniOutboundLineRate          Integer32,
        ibEponUniFlowControl               TruthValue,
        ibEponUniSpeed                     INTEGER,
        ibEponUniDuplex                    INTEGER,
        ibEponUniVlanVPNStatus             TruthValue,
        ibEponUniCountReset                INTEGER,
        ibEponUniPortIsolate               INTEGER,
        ibEponUniVlanConfiguration         OCTET STRING,
        ibEponUniAutoNegotiation           INTEGER,
        ibEponUniRestartAutoNeg            INTEGER,
        ibEponUniLinkStatus                INTEGER,
        ibEponUniInterfaceType             INTEGER,
        ibEponUniVitualCableTest           INTEGER,
        ibEponUniVCTCableStatus            INTEGER,
        ibEponUniVCTCableLength            Integer32,
        ibEponUniVCTImpedanceMismatch      INTEGER,
        ibEponUniVCTPairSkew               Integer32,
        ibEponUniVCTPairSwap               INTEGER,
        ibEponUniVCTPolaritySwap           INTEGER,
        ibEponUniVCTInsertionLoss          Integer32,
        ibEponUniVCTReturnLoss             Integer32,
        ibEponUniVCTNearendCrosstalk       Integer32,
        ibEponUniVlan                      Integer32,
        ibEponUniMacMax                    Integer32
    }

ibEponUniIndex OBJECT-TYPE
    SYNTAX      Integer32
    MAX-ACCESS  accessible-for-notify
    STATUS      current
    DESCRIPTION
        "The index value which uniquely identifies the FE(fast Ethernet)
        interface of the ONU."
    ::= { ibEponUniSysManEntry 1 }

ibEponUniDescr OBJECT-TYPE
    SYNTAX      OCTET STRING
    MAX-ACCESS  read-write
    STATUS      current
    DESCRIPTION
        "A textual string containing information about the interface.  This
        string should include the name of the manufacturer, the product name
        and the version of the interface hardware and software."
    ::= { ibEponUniSysManEntry 2 }

ibEponUniAdminStatus OBJECT-TYPE
    SYNTAX      INTEGER
        {
            up(1),
            down(2),
            testing(3)
        }
    MAX-ACCESS  read-write
    STATUS      current
    DESCRIPTION
        "The desired state of the user network interface. When a managed
        system initializes, all user network interfaces start with down(2)
        state. The testing(3)state indicates that no operational packets
        can be passed. As a result of either explicit management action or
        per configuration information retained by the managed system,
        ibEponUniAdminStatus is then changed to either the up(1) or
        testing(3) states (or remains in the down(2) state)."
    ::= { ibEponUniSysManEntry 3 }

ibEponUniMdi OBJECT-TYPE
    SYNTAX      INTEGER
        {
            mdi-ii(1),
            mdi-x(2),
            mdi-auto(3)
        }
    MAX-ACCESS  read-write
    STATUS      current
    DESCRIPTION
        "Type of the line connected to UNI interface:
        mdi-ii(straight-through cable),
        mdi-x (crossover cable),
        mdi-auto (auto-sensing)."
    ::= { ibEponUniSysManEntry 4 }

ibEponUniPriority OBJECT-TYPE
    SYNTAX      Integer32(0..7)
    MAX-ACCESS  read-write
    STATUS      current
    DESCRIPTION
        "The priority of user network interface.  If the value is larger,
        the priority will be higher."
    ::= { ibEponUniSysManEntry 5 }

ibEponUniVlanType OBJECT-TYPE
    SYNTAX      INTEGER
        {
            vlantrunk(1),
            access(2),
            hybrid(3),
            untagged(4),
            transparent(5),
            doubletagged(6),
            tag(7),
            translation(8),
            aggregation(9)
        }
    MAX-ACCESS  read-write
    STATUS      current
    DESCRIPTION
        "UNI vlan types."
    ::= { ibEponUniSysManEntry 6 }

ibEponUniAccessVlan OBJECT-TYPE
    SYNTAX      Integer32(1..4094)
    MAX-ACCESS  read-write
    STATUS      current
    DESCRIPTION
        "The vlan ID assigned to untagged frames or Priority-Tagged
        frames received on user network interface."
    ::= { ibEponUniSysManEntry 7 }

ibEponUniTrunkPvid OBJECT-TYPE
    SYNTAX      Integer32(1..4094)
    MAX-ACCESS  read-write
    STATUS      current
    DESCRIPTION
        "PVID(port vlan ID), the vlan ID assigned to untagged frames or
        Priority-Tagged frames received on user network interface."
    ::= { ibEponUniSysManEntry 8 }

ibEponUniVLANTrunkAllowListLow OBJECT-TYPE
    SYNTAX      OCTET STRING
    MAX-ACCESS  read-write
    STATUS      current
    DESCRIPTION
        "Each octet within this value specifies a set of eight VLANs,
        with the first octet specifying VLANs 1 through 8, the second
        octet specifying VLANs 9 through 16, etc.  Within each octet,
        the most significant bit represents the highest numbered VLAN,
        and the least significant bit represents the lowest numbered VLAN.
        Thus, each allowed vlan of the trunk port is represented by a
        single bit within the value of this object.  If that bit has a value
        of '1' then that vlan is allowed in the set of VLANs.  The vlan
        is not allowed if its bit has a value of '0'."
    ::= { ibEponUniSysManEntry 9 }

ibEponUniVLANTrunkAllowListHigh OBJECT-TYPE
    SYNTAX      OCTET STRING
    MAX-ACCESS  read-write
    STATUS      current
    DESCRIPTION
        "Each octet within this value specifies a set of eight VLANs,
        with the first octet specifying VLANs 2049 through 2056, the
        second octet specifying VLANs 2057 through 2064, etc. Within
        each octet, the most significant bit represents the highest
        numbered vlan, and the least significant bit represents the
        lowest numbered vlan. Thus, each allowed vlan of the trunk port
        is represented by a single bit within the value of this object.
        If that bit has a value of '1' then that vlan is allowed in the
        set of VLANs. The vlan is not allowed if its bit has a value of '0'.
        "
    ::= { ibEponUniSysManEntry 10 }

ibEponUniInboundLineRate OBJECT-TYPE
    SYNTAX      Integer32
    MAX-ACCESS  read-write
    STATUS      current
    DESCRIPTION
        "The value of the inbound line-rate.  measured with kbps.
        The upper limit of the line-rate is the value of
        ibEponUniLineRateMax in the entry.  It must be multiple
        of the value of ibEponUniLineRateStep. The default value of
        ibEponUniLineRate is the value of ibEponUniLineRateMax."
    ::= { ibEponUniSysManEntry 11 }

ibEponUniOutboundLineRate OBJECT-TYPE
    SYNTAX      Integer32
    MAX-ACCESS  read-write
    STATUS      current
    DESCRIPTION
        "The value of the outbound line-rate.  measured with kbps.
        The upper limit of the line-rate is the value of
        ibEponUniLineRateMax in the entry. It must be multiple
        of the value of ibEponUniLineRateStep.  The default value of
        ibEponUniLineRate is the value of ibEponUniLineRateMax."
    ::= { ibEponUniSysManEntry 12 }

ibEponUniFlowControl OBJECT-TYPE
    SYNTAX      TruthValue
    MAX-ACCESS  read-write
    STATUS      current
    DESCRIPTION
        "Flow control status.
        true(1)  - Flow control status enable.
        false(2) - Flow control status disable."
    ::= { ibEponUniSysManEntry 13 }

ibEponUniSpeed OBJECT-TYPE
    SYNTAX      INTEGER
        {
            auto(0),
            s10M(10),
            s100M(100),
            s1000M(1000),
            s10000M(10000),
            s24000M(24000)
        }
    MAX-ACCESS  read-write
    STATUS      current
    DESCRIPTION
        "User network interface speed."
    ::= { ibEponUniSysManEntry 14 }

ibEponUniDuplex OBJECT-TYPE
    SYNTAX      INTEGER
        {
            full(1),
            half(2),
            auto(3)
        }
    MAX-ACCESS  read-write
    STATUS      current
    DESCRIPTION
        "User network interface mode."
    ::= { ibEponUniSysManEntry 15 }

ibEponUniVlanVPNStatus OBJECT-TYPE
    SYNTAX      TruthValue
    MAX-ACCESS  read-write
    STATUS      current
    DESCRIPTION
        "vlan VPN status.
        true(1)  - vlan VPN status enable.
        false(2) - vlan VPN disable."
    ::= { ibEponUniSysManEntry 16 }

ibEponUniCountReset OBJECT-TYPE
    SYNTAX      INTEGER
        {
            reset(1)
        }
    MAX-ACCESS  read-write
    STATUS      current
    DESCRIPTION
        "Reset the counter which is about packets of the interface,
        then the counter will change to zero.  There is no sense in
        reading this object."
    ::= { ibEponUniSysManEntry 17 }

ibEponUniPortIsolate OBJECT-TYPE
    SYNTAX      INTEGER
        {
            enable(1),
            disable(2)
        }
    MAX-ACCESS  read-write
    STATUS      current
    DESCRIPTION
        "
        enable - enable UNI port isolate setting.
        disable - disable UNI port isolate setting.
        "
    ::= { ibEponUniSysManEntry 18 }


ibEponUniVlanConfiguration OBJECT-TYPE
    SYNTAX      OCTET STRING(SIZE(0..255))
    MAX-ACCESS  read-write
    STATUS      current
    DESCRIPTION
        "
        The vlan configuration of the related vlan mode.
        Transparent vlan mode: ibEponUniVlanConfiguration is a
        zero length string.
        Tag vlan mode: the first four octets were the tag
        assigned to untagged frames received on UNI, including TPID,
        VID, CFI and priority.
        Translation vlan mode: the first four octets were the old tag
        (including TPID, VID, CFI and priority), which is replaced
        by the new tag(including TPID, VID, CFI and priority),
        the second four octets.
        Doubletagged vlan mode: the first four octets were the tag
        assigned to untagged or tagged frames received on UNI, including TPID,
        VID, CFI and priority.
        Vlantrunk vlan mode: the first four octets were the old tag
        (including TPID, VID, CFI and priority), which is replaced
        by the new tag(including TPID, VID, CFI and priority) of
        the second four octets, the frames which assigned tag ranges from
        the third four octets to fourth four octets were transmited freely
        and so on for following octets.
        Aggregation vlan mode: the first four octets were the old tag
        (including TPID, VID, CFI and priority), which is replaced
        by the new tag(including TPID, VID, CFI and priority) of
        the second four octets, the frames which assigned tag ranges from
        the third four octets to fourth four octets(using low two octets as vlan tag)
        were replaced by the new tag(using high two octets as target vlan tag)
        and so on for following octets.
        "
    ::= { ibEponUniSysManEntry 23 }

ibEponUniAutoNegotiation OBJECT-TYPE
    SYNTAX      INTEGER
        {
            enable(1),
            disable(2)
        }
    MAX-ACCESS  read-write
    STATUS      current
    DESCRIPTION
        "
        enable - enable auto negotiation.
        disable - disable auto negotiation.
        "
    ::= { ibEponUniSysManEntry 25 }

ibEponUniRestartAutoNeg OBJECT-TYPE
    SYNTAX      INTEGER
        {
            autoNegotiation(1)
        }
    MAX-ACCESS  read-write
    STATUS      current
    DESCRIPTION
        "
        Force to restart the auto negotiation process.
        "
    ::= { ibEponUniSysManEntry 26 }


ibEponUniLinkStatus OBJECT-TYPE
    SYNTAX      INTEGER
        {
            up(1),
            down(2)
        }
    MAX-ACCESS  read-only
    STATUS      current
    DESCRIPTION
        "
        The link status of UNI.
        "
    ::= { ibEponUniSysManEntry 29 }

ibEponUniInterfaceType OBJECT-TYPE
    SYNTAX      INTEGER
        {
            gigabitethernetport(1),
            fastethernetport(2),
            voipport(3),
            e1port(4)
        }
    MAX-ACCESS  read-only
    STATUS      current
    DESCRIPTION
        "
        UNI interface type.
        "
    ::= { ibEponUniSysManEntry 30 }

-- BEGIN for UNI VCT
ibEponUniVitualCableTest OBJECT-TYPE
    SYNTAX      INTEGER{true(1),
        false(2)
        }
    MAX-ACCESS  read-write
    STATUS      current
    DESCRIPTION
        "
        True(1): Virtual cable test enable.
        False(2): Virtual cable test disable."
    DEFVAL{ false }
    ::= { ibEponUniSysManEntry 31 }

ibEponUniVCTCableStatus OBJECT-TYPE
    SYNTAX      INTEGER{normal(1),
        abnormal(2),
        abnormalOpen(3),
        abnormalShort(4),
        failure(5)
        }
    MAX-ACCESS  read-only
    STATUS      current
    DESCRIPTION
        "
        Get the cable status.
        Normal(1),cable is normal.
        Abnormal(2),cable is abnormal.
        AbnormalOpen(3),cable is abnormal because of open circuit.
        AbnormalShort(4),cable is abnormal because of short circuit.
        Failure(5),cable is abnormal because of testing failure.
        "
    ::= { ibEponUniSysManEntry 32 }

ibEponUniVCTCableLength OBJECT-TYPE
    SYNTAX      Integer32
    MAX-ACCESS  read-only
    STATUS      current
    DESCRIPTION
        "
        Get the cable length.
        When ibEponUniVCTCableStatus is normal,
        the node stands for the length from the UNI port to the port opposite.
        When ibEponUniVCTCableStatus is abnormal,
        it stands for the length from the UNI port to the failure place.
        Unit:meter(m).
        "
    ::= { ibEponUniSysManEntry 33 }

ibEponUniVCTImpedanceMismatch OBJECT-TYPE
    SYNTAX      INTEGER{not-support(1),
        true(2),
        false(3)
        }
    MAX-ACCESS  read-only
    STATUS      current
    DESCRIPTION
        "
        Get the cable impedance.
        Not-support(1),the UNI port does not support this function.
        True(2),impedance match.
        False(3),impedance mismatch."
    ::= { ibEponUniSysManEntry 34 }

ibEponUniVCTPairSkew OBJECT-TYPE
    SYNTAX      Integer32
    MAX-ACCESS  read-only
    STATUS      current
    DESCRIPTION
        "
        Get the symmetry of cable.
        If the function is not supported,
        the default value 0 will be returned.
        Unit:nanosecond(ns).
        "
    ::= { ibEponUniSysManEntry 35 }

ibEponUniVCTPairSwap OBJECT-TYPE
    SYNTAX      INTEGER{notSupport(1),
        true(2),
        false(3)
        }
    MAX-ACCESS  read-only
    STATUS      current
    DESCRIPTION
        "
        NotSupport(1),the UNI port does not support this function.
        True(2),pair swap.
        False(3),not pair swap."
    ::= { ibEponUniSysManEntry 36 }

ibEponUniVCTPolaritySwap OBJECT-TYPE
    SYNTAX      INTEGER{notSupport(1),
        true(2),
        false(3)
        }
    MAX-ACCESS  read-only
    STATUS      current
    DESCRIPTION
        "
        NotSupport(1),the UNI port does not support this function.
        True(2),polarity swap.
        False(3),not polarity swap."
    ::= { ibEponUniSysManEntry 37 }

ibEponUniVCTInsertionLoss OBJECT-TYPE
    SYNTAX      Integer32
    MAX-ACCESS  read-only
    STATUS      current
    DESCRIPTION
        "
        If the function is not supported,
        the default value 0 will be returned.
        Unit:decibel(db).
        "
    ::= { ibEponUniSysManEntry 38 }

ibEponUniVCTReturnLoss OBJECT-TYPE
    SYNTAX      Integer32
    MAX-ACCESS  read-only
    STATUS      current
    DESCRIPTION
        "
        If the function is not supported,
        the default value 0 will be returned.
        Unit:decibel(db).
        "
    ::= { ibEponUniSysManEntry 39 }

ibEponUniVCTNearendCrosstalk OBJECT-TYPE
    SYNTAX      Integer32
    MAX-ACCESS  read-only
    STATUS      current
    DESCRIPTION
        "
        If the function is not supported,
        the default value 0 will be returned.
        Unit:decibel(db).
        "
    ::= { ibEponUniSysManEntry 40 }
ibEponUniVlan   OBJECT-TYPE
    SYNTAX      Integer32
    MAX-ACCESS  accessible-for-notify
    STATUS      current
    DESCRIPTION
        "
        If the function is not supported,
        the default value 0 will be returned.
        Unit:decibel(db).
        "
    ::= { ibEponUniSysManEntry 41 }
ibEponUniMacMax   OBJECT-TYPE
    SYNTAX      Integer32
    MAX-ACCESS  read-write
    STATUS      current
    DESCRIPTION
        "
        The maximum number of MAC addresses that the UNI port can learn.
        no-limit(65535)
        others(0~65534)
        "
    DEFVAL { 65535 }
    ::= { ibEponUniSysManEntry 42 }
-- END for UNI VCT

ibEponUniCountTable OBJECT-TYPE
    SYNTAX      SEQUENCE OF IbEponUniCountEntry
    MAX-ACCESS  not-accessible
    STATUS      current
    DESCRIPTION
        "A list of interface counter about frames entries."
    ::= { ibEponUniSysMan 2 }

ibEponUniCountEntry OBJECT-TYPE
    SYNTAX      IbEponUniCountEntry
    MAX-ACCESS  not-accessible
    STATUS      current
    DESCRIPTION
        "An entry containing management information applicable
        to a particular interface."
    INDEX
        {
            ifIndex,
            ibEponUniIndex
        }
    ::= { ibEponUniCountTable 1 }

IbEponUniCountEntry ::= SEQUENCE
    {
        ibEponUniInStatsPkts                 Unsigned32,
        ibEponUniInStatsUnicastPkts          Unsigned32,
        ibEponUniInStatsBroadcastPkts        Unsigned32,
        ibEponUniInStatsMulticastPkts        Unsigned32,
        ibEponUniInPausePkts                 Unsigned32,
        ibEponUniInTotalErrors               Unsigned32,
        ibEponUniInStatsCRCAlignErrors       Unsigned32,
        ibEponUniInStatsUndersizePkts        Unsigned32,
        ibEponUniInStatsOversizePkts         Unsigned32,
        ibEponUniInErrorbyOther              Unsigned32,
        ibEponUniOutStatsPkts                Unsigned32,
        ibEponUniOutStatsUnicastPkts         Unsigned32,
        ibEponUniOutStatsBroadcastPkts       Unsigned32,
        ibEponUniOutStatsMulticastPkts       Unsigned32,
        ibEponUniOutStatsPausePkts           Unsigned32,
        ibEponUniOutTotalErrors              Unsigned32,
        ibEponUniOutStatsCollisions          Unsigned32,
        ibEponUniOutDelayExceededDiscards    Unsigned32,
        ibEponUniOutErrorbyOther             Unsigned32,
        ibEponUniOutDroppedFrames            Unsigned32
    }

ibEponUniInStatsPkts OBJECT-TYPE
    SYNTAX      Unsigned32
    MAX-ACCESS  read-only
    STATUS      current
    DESCRIPTION
        "The total number of frames (including bad frames,
        broadcast frames, and multicast frames) received."
    ::= { ibEponUniCountEntry 1 }

ibEponUniInStatsUnicastPkts OBJECT-TYPE
    SYNTAX      Unsigned32
    MAX-ACCESS  read-only
    STATUS      current
    DESCRIPTION
        "The total number of good frames received that are
        directed to the unicast address.  Note that this
        does not include multicast and broadcast frames."
    ::= { ibEponUniCountEntry 2 }

ibEponUniInStatsBroadcastPkts OBJECT-TYPE
    SYNTAX      Unsigned32
    MAX-ACCESS  read-only
    STATUS      current
    DESCRIPTION
        "The total number of good frames received that are
        directed to the broadcast address.  Note that this
        does not include multicast frames."
    ::= { ibEponUniCountEntry 3 }

ibEponUniInStatsMulticastPkts OBJECT-TYPE
    SYNTAX      Unsigned32
    MAX-ACCESS  read-only
    STATUS      current
    DESCRIPTION
        "The total number of good frames received that are
        directed to a multicast address.  Note that this number
        does not include frames directed to the broadcast address."
    ::= { ibEponUniCountEntry 4 }

ibEponUniInPausePkts OBJECT-TYPE
    SYNTAX      Unsigned32
    MAX-ACCESS  read-only
    STATUS      current
    DESCRIPTION
        "A count of MAC Control frames received on this
        interface by the pause(flow control) operation.
        This counter does not increment when the
        interface is in a half-duplex mode.
        Discontinuities in the value of this counter can
        occur at re-initialization of the management
        system."
    ::= { ibEponUniCountEntry 5 }

ibEponUniInTotalErrors OBJECT-TYPE
    SYNTAX      Unsigned32
    MAX-ACCESS  read-only
    STATUS      current
    DESCRIPTION
        "Total count of the error frames received on this interface."
    ::= { ibEponUniCountEntry 6 }

ibEponUniInStatsCRCAlignErrors OBJECT-TYPE
    SYNTAX      Unsigned32
    MAX-ACCESS  read-only
    STATUS      current
    DESCRIPTION
        "The total number of frames received that
        had a length (excluding framing bits, but
        including FCS octets) of between 64 and 1518
        octets, inclusive, but had either a bad
        Frame Check Sequence (FCS) with an integral
        number of octets (FCS Error) or a bad FCS with
        a non-integral number of octets (Alignment Error)."
    ::= { ibEponUniCountEntry 7 }

ibEponUniInStatsUndersizePkts OBJECT-TYPE
    SYNTAX      Unsigned32
    MAX-ACCESS  read-only
    STATUS      current
    DESCRIPTION
        "The total number of frames received that are
        less than 64 octets long (excluding framing bits,
        but including FCS octets) and are otherwise well formed."
    ::= { ibEponUniCountEntry 8 }

ibEponUniInStatsOversizePkts OBJECT-TYPE
    SYNTAX      Unsigned32
    MAX-ACCESS  read-only
    STATUS      current
    DESCRIPTION
        "The total number of frames received that are
        longer than 1518 octets (excluding framing bits,
        but including FCS octets) and are otherwise well formed."
    ::= { ibEponUniCountEntry 9 }

ibEponUniInErrorbyOther OBJECT-TYPE
    SYNTAX      Unsigned32
    MAX-ACCESS  read-only
    STATUS      current
    DESCRIPTION
        "The total number of error frames received on this interface."
    ::= { ibEponUniCountEntry 10 }

ibEponUniOutStatsPkts OBJECT-TYPE
    SYNTAX      Unsigned32
    MAX-ACCESS  read-only
    STATUS      current
    DESCRIPTION
        "The total number of frames (including bad frames,
        broadcast frames, and multicast frames) sent."
    ::= { ibEponUniCountEntry 11 }

ibEponUniOutStatsUnicastPkts OBJECT-TYPE
    SYNTAX      Unsigned32
    MAX-ACCESS  read-only
    STATUS      current
    DESCRIPTION
        "The total number of good frames sent that are
        directed to the unicast address.  Note that this
        does not include multicast and broadcast frames."
    ::= { ibEponUniCountEntry 12 }

ibEponUniOutStatsBroadcastPkts OBJECT-TYPE
    SYNTAX      Unsigned32
    MAX-ACCESS  read-only
    STATUS      current
    DESCRIPTION
        "The total number of good frames sent that are
        directed to the broadcast address.  Note that this
        does not include multicast frames."
    ::= { ibEponUniCountEntry 13 }

ibEponUniOutStatsMulticastPkts OBJECT-TYPE
    SYNTAX      Unsigned32
    MAX-ACCESS  read-only
    STATUS      current
    DESCRIPTION
        "The total number of good frames sent that are
        directed to a multicast address.  Note that this number
        does not include frames directed to the broadcast address."
    ::= { ibEponUniCountEntry 14 }

ibEponUniOutStatsPausePkts OBJECT-TYPE
    SYNTAX      Unsigned32
    MAX-ACCESS  read-only
    STATUS      current
    DESCRIPTION
        "The total number of MAC control frames sent on this
        interface by the pause operation.  This counter does
        not increment when the interface is in a half-duplex mode.
        Discontinuities in the value of this counter can
        occur at re-initialization of the management system."
    ::= { ibEponUniCountEntry 15 }

ibEponUniOutTotalErrors OBJECT-TYPE
    SYNTAX      Unsigned32
    MAX-ACCESS  read-only
    STATUS      current
    DESCRIPTION
        "The total number of error frames sent on this interface."
    ::= { ibEponUniCountEntry 16 }

ibEponUniOutStatsCollisions OBJECT-TYPE
    SYNTAX      Unsigned32
    MAX-ACCESS  read-only
    STATUS      current
    DESCRIPTION
        "The best estimate of the total number of collisions
        on this Ethernet segment.
        The value returned will depend on the location of the
        RMON probe.  Section 8.2.1.3 (10BASE-5) and section
        10.3.1.3 (10BASE-2) of IEEE standard 802.3 states that a
        station must detect a collision, in the receive mode, if
        three or more stations are transmitting simultaneously.  A
        repeater port must detect a collision when two or more
        stations are transmitting simultaneously.  Thus a probe
        placed on a repeater port could record more collisions
        than a probe connected to a station on the same segment
        could.  Probe location plays a much smaller role when considering
        10BASE-T.  14.2.1.4 (10BASE-T) of IEEE standard 802.3
        defines a collision as the simultaneous presence of signals
        on the DO and RD circuits (transmitting and receiving
        at the same time).  A 10BASE-T station can only detect
        collisions when it is transmitting.  Thus probes placed on
        a station and a repeater, should report the same number of
        collisions.  Note also that an RMON probe inside a repeater should
        ideally report collisions between the repeater and one or
        more other hosts (transmit collisions as defined by IEEE
        802.3k) plus receiver collisions observed on any coax
        segments to which the repeater is connected."
    ::= { ibEponUniCountEntry 17 }

ibEponUniOutDelayExceededDiscards OBJECT-TYPE
    SYNTAX      Unsigned32
    MAX-ACCESS  read-only
    STATUS      current
    DESCRIPTION
        "The number of frames discarded by this port due
        to excessive transit delay through the bridge.  It
        is incremented by both transparent and source route bridges."
    ::= { ibEponUniCountEntry 18 }

ibEponUniOutErrorbyOther OBJECT-TYPE
    SYNTAX      Unsigned32
    MAX-ACCESS  read-only
    STATUS      current
    DESCRIPTION
        "The total number of other error frames sent on this interface.
        Other error frames means the error frames out of collision frames
        and excessive delayed frames."
    ::= { ibEponUniCountEntry 19 }

ibEponUniOutDroppedFrames OBJECT-TYPE
    SYNTAX      Unsigned32
    MAX-ACCESS  read-only
    STATUS      current
    DESCRIPTION
        "
        The total number of frames dropped because of buffer failure.
        "
    ::= { ibEponUniCountEntry 20 }

ibEponUniIgmpInfoTable OBJECT-TYPE
    SYNTAX      SEQUENCE OF IbEponUniIgmpInfoEntry
    MAX-ACCESS  not-accessible
    STATUS      current
    DESCRIPTION
        "This table stores igmp information of UNI interface."
    ::= { ibEponUniSysMan 3 }

ibEponUniIgmpInfoEntry OBJECT-TYPE
    SYNTAX      IbEponUniIgmpInfoEntry
    MAX-ACCESS  not-accessible
    STATUS      current
    DESCRIPTION
        "The entry of ibEponUniIgmpInfoTable."
    INDEX
        {
            ifIndex,
            ibEponUniIndex,
            ibEponUniMacIndex
        }
    ::= { ibEponUniIgmpInfoTable 1 }

IbEponUniIgmpInfoEntry ::= SEQUENCE
    {
        ibEponUniMacIndex          Integer32,
        ibEponUniIgmpMacAddress    MacAddress,
        ibEponUniIgmpVlanId        Integer32
    }

ibEponUniMacIndex OBJECT-TYPE
    SYNTAX      Integer32
    MAX-ACCESS  not-accessible
    STATUS      current
    DESCRIPTION
        "The index uniquely identifies the igmp information in current
        UNI interface."
    ::= { ibEponUniIgmpInfoEntry 1 }

ibEponUniIgmpMacAddress OBJECT-TYPE
    SYNTAX      MacAddress
    MAX-ACCESS  read-only
    STATUS      current
    DESCRIPTION
        "A 6-octet read-only value carrying the individual MAC address
        indicates which igmp group the UNI interface belonging to."
    ::= { ibEponUniIgmpInfoEntry 2 }

ibEponUniIgmpVlanId OBJECT-TYPE
    SYNTAX      Integer32(1..4094)
    MAX-ACCESS  read-only
    STATUS      current
    DESCRIPTION
        "An integer range from 1 to 4094 indicates the vlan which the igmp
        Mac address has joined in."
    ::= { ibEponUniIgmpInfoEntry 3 }

ibEponUniParaMan OBJECT IDENTIFIER ::= { ibEponUniSysMan 4 }

ibEponUniLineRateMax OBJECT-TYPE
    SYNTAX      Integer32
    MAX-ACCESS  read-only
    STATUS      current
    DESCRIPTION
        "The maximum value of the line-rate(kbps) that user network
        interface can be set."
    ::= { ibEponUniParaMan 1 }

ibEponUniLineRateStep OBJECT-TYPE
    SYNTAX      Integer32
    MAX-ACCESS  read-only
    STATUS      current
    DESCRIPTION
        "The step of line-rate(kbps)."
    ::= { ibEponUniParaMan 2 }

ibEponUniNumberOnOnu OBJECT-TYPE
    SYNTAX      Integer32
    MAX-ACCESS  read-only
    STATUS      current
    DESCRIPTION
        "The user network interface number on ONU."
    ::= { ibEponUniParaMan 3 }


ibEponUniScalarGroup OBJECT IDENTIFIER ::= { ibEponUniSysMan 5 }

--
-- ibEponUniPortPolicyTable
--

ibEponUniPortPolicyTable OBJECT-TYPE
    SYNTAX      SEQUENCE OF IbEponUniPortPolicyEntry
    MAX-ACCESS  not-accessible
    STATUS      current
    DESCRIPTION
        "
        UNI port policy configuration.
        "
    ::= { ibEponUniSysMan 6 }

ibEponUniPortPolicyEntry OBJECT-TYPE
    SYNTAX      IbEponUniPortPolicyEntry
    MAX-ACCESS  not-accessible
    STATUS      current
    DESCRIPTION
        "
        The entry of ibEponUniPortPolicyTable.
        "
    INDEX
        {
            ifIndex,
            ibEponUniIndex
        }
    ::= { ibEponUniPortPolicyTable 1 }

IbEponUniPortPolicyEntry ::= SEQUENCE
    {
        ibEponUniPortPolicyStatus                INTEGER,
        ibEponUniPortPolicyCir                   Integer32,
        ibEponUniPortPolicyBucketDepth           Integer32,
        ibEponUniPortPolicyExtraBurst            Integer32,
        ibEponUniPortPolicyInboundCir            Integer32,
        ibEponUniPortPolicyInboundBucketDepth    Integer32,
        ibEponUniPortPolicyInboundExtraBurst     Integer32,
        ibEponUniPortPolicyOutboundCir           Integer32,
        ibEponUniPortPolicyOutboundPir           Integer32
    }

ibEponUniPortPolicyStatus OBJECT-TYPE
    SYNTAX      INTEGER
        {
            enable(1),
            disable(2)
        }
    MAX-ACCESS  read-write
    STATUS      current
    DESCRIPTION
        "
        enable - enable UNI upstream port policing.
        disable - disable UNI upstream port policing.
        "
    DEFVAL { disable }
    ::= { ibEponUniPortPolicyEntry 1 }

ibEponUniPortPolicyCir OBJECT-TYPE
    SYNTAX      Integer32
    MAX-ACCESS  read-write
    STATUS      current
    DESCRIPTION
        "
        The committed information rate,
        ranging from 1 to 102400, measured in kbps.
        "
    DEFVAL { 102400 }
    ::= { ibEponUniPortPolicyEntry 2 }

ibEponUniPortPolicyBucketDepth OBJECT-TYPE
    SYNTAX      Integer32
    MAX-ACCESS  read-write
    STATUS      current
    DESCRIPTION
        "
        The depth of the token bucket to tolerant the certain burst(CBS),
        ranging from 0 to 65535, measured in bytes.
        "
    DEFVAL { 0 }
    ::= { ibEponUniPortPolicyEntry 3 }

ibEponUniPortPolicyExtraBurst OBJECT-TYPE
    SYNTAX      Integer32
    MAX-ACCESS  read-write
    STATUS      current
    DESCRIPTION
        "
        The extra token to permit the forwarding engine to finish the packet
        being sent when the bucket depth is exhausted, ranging from 0 to 65535,
        measured in bytes.
        "
    DEFVAL { 0 }
    ::= { ibEponUniPortPolicyEntry 4 }

ibEponUniPortPolicyInboundCir OBJECT-TYPE
    SYNTAX      Integer32
    MAX-ACCESS  read-write
    STATUS      current
    DESCRIPTION
        "
        The inbound committed information rate, measured in kbps.
        "
    ::= { ibEponUniPortPolicyEntry 5 }

ibEponUniPortPolicyInboundBucketDepth OBJECT-TYPE
    SYNTAX      Integer32
    MAX-ACCESS  read-write
    STATUS      current
    DESCRIPTION
        "
        The inbound depth of the token bucket to tolerant the certain burst(CBS),
        ranging from 0 to 65535, measured in bytes.
        "
    DEFVAL { 0 }
    ::= { ibEponUniPortPolicyEntry 6 }

ibEponUniPortPolicyInboundExtraBurst OBJECT-TYPE
    SYNTAX      Integer32
    MAX-ACCESS  read-write
    STATUS      current
    DESCRIPTION
        "
        The inbound extra token to permit the forwarding engine to finish the packet
        being sent when the bucket depth is exhausted, ranging from 0 to 65535,
        measured in bytes.
        "
    DEFVAL { 0 }
    ::= { ibEponUniPortPolicyEntry 7 }

ibEponUniPortPolicyOutboundCir OBJECT-TYPE
    SYNTAX      Integer32
    MAX-ACCESS  read-write
    STATUS      current
    DESCRIPTION
        "
        The outbound committed information rate, stepped by 64, measured in kbps.
        "
    ::= { ibEponUniPortPolicyEntry 8 }

ibEponUniPortPolicyOutboundPir OBJECT-TYPE
    SYNTAX      Integer32
    MAX-ACCESS  read-write
    STATUS      current
    DESCRIPTION
        "
        The outbound peak information rate, stepped by 64, measured in kbps.
        "
    ::= { ibEponUniPortPolicyEntry 9 }
--
-- ibEponUniMulticastTable
--
ibEponUniMulticastTable OBJECT-TYPE
    SYNTAX      SEQUENCE OF IbEponUniMulticastEntry
    MAX-ACCESS  not-accessible
    STATUS      current
    DESCRIPTION
        "
        UNI multicast configuration.
        "
    ::= { ibEponUniSysMan 7 }

ibEponUniMulticastEntry OBJECT-TYPE
    SYNTAX      IbEponUniMulticastEntry
    MAX-ACCESS  not-accessible
    STATUS      current
    DESCRIPTION
        "
        The entry of ibEponUniPortPolicyTable.
        "
    INDEX
        {
            ifIndex,
            ibEponUniIndex
        }
    ::= { ibEponUniMulticastTable 1 }

IbEponUniMulticastEntry ::= SEQUENCE
    {
        ibEponUniMulticastGroupNumber    Integer32,
        ibEponUniMulticastVlanList       OCTET STRING,
        ibEponUniMulticastStripStatus    INTEGER,
        ibEponUniMulticastFastleave      TruthValue
    }

ibEponUniMulticastGroupNumber OBJECT-TYPE
    SYNTAX      Integer32
    MAX-ACCESS  read-write
    STATUS      current
    DESCRIPTION
        "
        The allowed multicast group number that can be handled
        at the same time by UNI.
        "
    DEFVAL { 64 }
    ::= { ibEponUniMulticastEntry 1 }


ibEponUniMulticastVlanList OBJECT-TYPE
    SYNTAX      OCTET STRING(SIZE(0..255))
    MAX-ACCESS  read-write
    STATUS      current
    DESCRIPTION
        "
        The multicast vlan list.
        The first two octets of the string represent the first VLAN ID;
        the second two octets of the string represent the second VLAN ID,
        and so on. It is a zero length string by default.
        "
    ::= { ibEponUniMulticastEntry 2 }

ibEponUniMulticastStripStatus OBJECT-TYPE
    SYNTAX      INTEGER
        {
            enable(1),
            disable(2)
        }
    MAX-ACCESS  read-write
    STATUS      current
    DESCRIPTION
        "
        true - strip the vlan tag of multicast packet.
        false - does not strip the vlan tag of multicast packet.
        "
    DEFVAL { disable }
    ::= { ibEponUniMulticastEntry 3 }

ibEponUniMulticastFastleave OBJECT-TYPE
    SYNTAX      TruthValue
    MAX-ACCESS  read-write
    STATUS      current
    DESCRIPTION
        "
        true(1)  - fast leave of IGMP enable on ONU.
        false(2) - fast leave of IGMP disable on ONU.
        "
    DEFVAL { false }
    ::= { ibEponUniMulticastEntry 4 }

--
-- ibEponUniTechAbilityTable
--
ibEponUniTechAbilityTable OBJECT-TYPE
    SYNTAX      SEQUENCE OF IbEponUniTechAbilityEntry
    MAX-ACCESS  not-accessible
    STATUS      current
    DESCRIPTION
        "
        UNI multicast configuration.
        "
    ::= { ibEponUniSysMan 8 }

ibEponUniTechAbilityEntry OBJECT-TYPE
    SYNTAX      IbEponUniTechAbilityEntry
    MAX-ACCESS  not-accessible
    STATUS      current
    DESCRIPTION
        "
        The entry of ibEponUniTechAbilityTable.
        "
    INDEX
        {
            ifIndex,
            ibEponUniIndex
        }
    ::= { ibEponUniTechAbilityTable 1 }

IbEponUniTechAbilityEntry ::= SEQUENCE
    {
        ibEponUniLocalTechAbility         OCTET STRING,
        ibEponUniAdvertisedTechAbility    OCTET STRING
    }
ibEponUniLocalTechAbility OBJECT-TYPE
    SYNTAX      OCTET STRING(SIZE(0..255))
    MAX-ACCESS  read-only
    STATUS      current
    DESCRIPTION
        "
        The local port capabilities of the UNI.
        Each two octets stand for a capability of UNI:
        the first two octets represent one capability and
        the second two octets represent another capability,
        and so on.
        The capabilities list:
        1 - undefined,
        2 - initializing, true ability not yet known,
        14 - 10BASE-T,
        142 - full duplex 10BASE-T,
        23 - 100BASE-T4,
        25 - 100BASE-TX,
        252 - full duplex 100BASE-TX,
        312 - PAUSE operation for full duplex links,
        313 - asymmetric PAUSE operation for full duplex links,
        314 - symmetric PAUSE operation for full duplex links,
        32 - 100BASE-T2,
        322 - full duplex 100BASE-T2,
        36 - 1000BASE-X,
        362 - full duplex 1000BASE-X,
        40 - 1000BASE-T UTP PHY,
        402 - full duplex 1000BASE-T UTP PHY,
        37 - remote fault bit 1(RF1),
        372 - remote fault bit 2(RF2),
        8029 - 802.9ISLAN-16T.
        "
    ::= { ibEponUniTechAbilityEntry 1 }

ibEponUniAdvertisedTechAbility OBJECT-TYPE
    SYNTAX      OCTET STRING(SIZE(0..255))
    MAX-ACCESS  read-only
    STATUS      current
    DESCRIPTION
        "
        The advertised port capabilities of the UNI.
        The capabilities list references the description of ibEponUniLocalTechAbility.
        "
    ::= { ibEponUniTechAbilityEntry 2 }

--
-- ibEponUniMulticastControlTable
--

ibEponUniMulticastControlTable OBJECT-TYPE
    SYNTAX      SEQUENCE OF IbEponUniMulticastControlEntry
    MAX-ACCESS  not-accessible
    STATUS      current
    DESCRIPTION
        "
        UNI multicast control parameters.
        "
    ::= { ibEponUniSysMan 9 }

ibEponUniMulticastControlEntry OBJECT-TYPE
    SYNTAX      IbEponUniMulticastControlEntry
    MAX-ACCESS  not-accessible
    STATUS      current
    DESCRIPTION
        "
        The entry of the table ibEponUniMulticastControlTable.
        "
    INDEX
        {
            ifIndex,
            ibEponUniIndex,
            ibEponUniMulticastIndex
        }
    ::= { ibEponUniMulticastControlTable 1 }

IbEponUniMulticastControlEntry ::= SEQUENCE
    {
        ibEponUniMulticastVlanIndex        Integer32,
        ibEponUniMulticastAddressList      OCTET STRING,
        ibEponUniMulticastAccessRule       INTEGER,
        ibEponUniMulticastChannelLimit     Integer32,
        ibEponUniMulticastPreTimeSlice     Integer32,
        ibEponUniMulticastPreTimes         Integer32,
        ibEponUniMulticastPreInterval      Integer32,
        ibEponUniMulticastRowStatus        RowStatus,
        ibEponUniMulticastIndex            Integer32,
        ibEponUniMulticastSourceIpList     OCTET STRING,
        ibEponUniMulticastResetInterval    Integer32
    }

ibEponUniMulticastVlanIndex OBJECT-TYPE
    SYNTAX      Integer32
    MAX-ACCESS  read-create
    STATUS      current
    DESCRIPTION
        "
        The multicast vlan ID.
        "
    ::= { ibEponUniMulticastControlEntry 1 }

ibEponUniMulticastAddressList OBJECT-TYPE
    SYNTAX      OCTET STRING(SIZE(0..255))
    MAX-ACCESS  read-create
    STATUS      current
    DESCRIPTION
        "
        The multicast address, each four octets represents a multicast address,
        the address section ranging from the first four octets to the second
        four octets, and the like.
        "
    ::= { ibEponUniMulticastControlEntry 2 }

ibEponUniMulticastAccessRule OBJECT-TYPE
    SYNTAX      INTEGER
        {
            deny(1),
            permit(2),
            preview(3)
        }
    MAX-ACCESS  read-create
    STATUS      current
    DESCRIPTION
        "
        deny - deny the multicast packet.
        permit - permit the multicast packet.
        preview - permit the multicast packet with conditions.
        "
    ::= { ibEponUniMulticastControlEntry 3 }

ibEponUniMulticastChannelLimit OBJECT-TYPE
    SYNTAX      Integer32
    MAX-ACCESS  read-create
    STATUS      current
    DESCRIPTION
        "
        The limitation of multicast preview channel number.
        "
    ::= { ibEponUniMulticastControlEntry 4 }

ibEponUniMulticastPreTimeSlice OBJECT-TYPE
    SYNTAX      Integer32
    MAX-ACCESS  read-create
    STATUS      current
    DESCRIPTION
        "
        The time slice of multicast preview.
        "
    ::= { ibEponUniMulticastControlEntry 5 }

ibEponUniMulticastPreTimes OBJECT-TYPE
    SYNTAX      Integer32
    MAX-ACCESS  read-create
    STATUS      current
    DESCRIPTION
        "
        The number of multicast preview times.
        "
    ::= { ibEponUniMulticastControlEntry 6 }

ibEponUniMulticastPreInterval OBJECT-TYPE
    SYNTAX      Integer32
    MAX-ACCESS  read-create
    STATUS      current
    DESCRIPTION
        "
        The interval between two consecutive previews, measured in minute.
        "
    ::= { ibEponUniMulticastControlEntry 7 }

ibEponUniMulticastRowStatus OBJECT-TYPE
    SYNTAX      RowStatus
    MAX-ACCESS  read-create
    STATUS      current
    DESCRIPTION
        "
        The status of this table entry. The active,
        createAndGo and the destory statuses are supported.
        "
    ::= { ibEponUniMulticastControlEntry 8 }

ibEponUniMulticastIndex OBJECT-TYPE
    SYNTAX      Integer32
    MAX-ACCESS  not-accessible
    STATUS      current
    DESCRIPTION
        "
        The index of the entry.
        "
    ::= { ibEponUniMulticastControlEntry 9 }

ibEponUniMulticastSourceIpList OBJECT-TYPE
    SYNTAX      OCTET STRING(SIZE(0..255))
    MAX-ACCESS  read-create
    STATUS      current
    DESCRIPTION
        "
        This list contains many source ip addresses.
        Each ip address is contained in four octets.
        "
    ::= { ibEponUniMulticastControlEntry 10 }

ibEponUniMulticastResetInterval OBJECT-TYPE
    SYNTAX      Integer32
    MAX-ACCESS  read-create
    STATUS      current
    DESCRIPTION
        "
        The interval is measured in minute.
        From the last preview limitation is reached, a customer can preview again
        after this interval is expired.
        "
    ::= { ibEponUniMulticastControlEntry 11 }

--
-- ibEponUniQosIndexNextTable
--

ibEponUniQosIndexNextTable OBJECT-TYPE
    SYNTAX      SEQUENCE OF IbEponUniQosIndexNextEntry
    MAX-ACCESS  not-accessible
    STATUS      current
    DESCRIPTION
        "
        The next index table.
        "
    ::= { ibEponUniSysMan 10 }

ibEponUniQosIndexNextEntry OBJECT-TYPE
    SYNTAX      IbEponUniQosIndexNextEntry
    MAX-ACCESS  not-accessible
    STATUS      current
    DESCRIPTION
        "
        The entry of the table ibEponUniQosIndexNextTable.
        "
    INDEX
        {
            ifIndex,
            ibEponUniIndex
        }
    ::= { ibEponUniQosIndexNextTable 1 }

IbEponUniQosIndexNextEntry ::= SEQUENCE
    {
        ibEponUniQosConfIndexNext    Integer32
    }

ibEponUniQosConfIndexNext OBJECT-TYPE
    SYNTAX      Integer32
    MAX-ACCESS  read-only
    STATUS      current
    DESCRIPTION
        "
        This object contains an appropriate value to be used for
        ibEponUniQosConfIndex when creating rows in the
        ibEponUniQosConfTable.
        "
    ::= { ibEponUniQosIndexNextEntry 1 }

--
-- ibEponUniQosConfTable
--

ibEponUniQosConfTable OBJECT-TYPE
    SYNTAX      SEQUENCE OF IbEponUniQosConfEntry
    MAX-ACCESS  not-accessible
    STATUS      current
    DESCRIPTION
        "
        UNI Qos configuration.
        "
    ::= { ibEponUniSysMan 11 }

ibEponUniQosConfEntry OBJECT-TYPE
    SYNTAX      IbEponUniQosConfEntry
    MAX-ACCESS  not-accessible
    STATUS      current
    DESCRIPTION
        "
        The entry of the table ibEponUniQosConfTable.
        "
    INDEX
        {
            ifIndex,
            ibEponUniIndex,
            ibEponUniQosConfIndex
        }
    ::= { ibEponUniQosConfTable 1 }

IbEponUniQosConfEntry ::= SEQUENCE
    {
        ibEponUniQosConfIndex             Integer32,
        ibEponUniQosConfRuleIndexNext     Integer32,
        ibEponUniQosConfMappedQueue       Integer32,
        ibEponUniQosConfMarkedPriority    Integer32,
        ibEponUniQosConfRowStatus         RowStatus
    }

ibEponUniQosConfIndex OBJECT-TYPE
    SYNTAX      Integer32
    MAX-ACCESS  not-accessible
    STATUS      current
    DESCRIPTION
        "
        The rule index.
        "
    ::= { ibEponUniQosConfEntry 1 }

ibEponUniQosConfRuleIndexNext OBJECT-TYPE
    SYNTAX      Integer32
    MAX-ACCESS  read-only
    STATUS      current
    DESCRIPTION
        "
        This object contains an appropriate value to be used for
        ibEponUniQosRuleIndex when creating rows in the
        ibEponUniQosRuleTable.
        "
    ::= { ibEponUniQosConfEntry 2 }

ibEponUniQosConfMappedQueue OBJECT-TYPE
    SYNTAX      Integer32
    MAX-ACCESS  read-create
    STATUS      current
    DESCRIPTION
        "
        The queue that the ethernet frames will be mapped.
        "
    ::= { ibEponUniQosConfEntry 3 }

ibEponUniQosConfMarkedPriority OBJECT-TYPE
    SYNTAX      Integer32
    MAX-ACCESS  read-create
    STATUS      current
    DESCRIPTION
        "
        Priority of the ethernet frames to be marked, which
        compliant with the 802.1D user priority standard.
        "
    ::= { ibEponUniQosConfEntry 4 }

ibEponUniQosConfRowStatus OBJECT-TYPE
    SYNTAX      RowStatus
    MAX-ACCESS  read-create
    STATUS      current
    DESCRIPTION
        "
        The status of this table entry. The active,
        createAndGo and the destory statuses are supported.
        "
    ::= { ibEponUniQosConfEntry 5 }

--
-- ibEponUniQosRuleTable
--

ibEponUniQosRuleTable OBJECT-TYPE
    SYNTAX      SEQUENCE OF IbEponUniQosRuleEntry
    MAX-ACCESS  not-accessible
    STATUS      current
    DESCRIPTION
        "
        Qos sub rule of the UNI.
        "
    ::= { ibEponUniSysMan 12 }

ibEponUniQosRuleEntry OBJECT-TYPE
    SYNTAX      IbEponUniQosRuleEntry
    MAX-ACCESS  not-accessible
    STATUS      current
    DESCRIPTION
        "
        The entry of the table ibEponUniQosRuleTable.
        "
    INDEX
        {
            ifIndex,
            ibEponUniIndex,
            ibEponUniQosConfIndex,
            ibEponUniQosRuleIndex
        }
    ::= { ibEponUniQosRuleTable 1 }

IbEponUniQosRuleEntry ::= SEQUENCE
    {
        ibEponUniQosRuleIndex         Integer32,
        ibEponUniQosRuleSelector      INTEGER,
        ibEponUniQosRuleValue         Integer32,
        ibEponUniQosRuleMacAddress    MacAddress,
        ibEponUniQosRuleOperator      INTEGER,
        ibEponUniQosRuleRowStatus     RowStatus
    }

ibEponUniQosRuleIndex OBJECT-TYPE
    SYNTAX      Integer32(1..255)
    MAX-ACCESS  not-accessible
    STATUS      current
    DESCRIPTION
        "
        The sub rule index.
        "
    ::= { ibEponUniQosRuleEntry 1 }

ibEponUniQosRuleSelector OBJECT-TYPE
    SYNTAX      INTEGER
        {
            dstmac(1),
            srcmac(2),
            ethernetpriority(3),
            vlanid(4),
            ethernettype(5),
            dstip(6),
            srcip(7),
            ipprototype(8),
            ipv4tosdscp(9),
            ipv6precedence(10),
            srcport(11),
            dstport(12)
        }
    MAX-ACCESS  read-create
    STATUS      current
    DESCRIPTION
        "
        The ethernet frame selector.
        dstmac - based on destination MAC address.
        srcmac - based on source MAC address.
        ethernetpriority -  based on ethernet priority.
        vlanid - based on VLAN ID.
        ethernettype - based on ethernet type.
        dstip - based on destination IP address.
        srcip - based on source IP address.
        ipprototype - based on IP type(ipv4 or ipv6).
        ipv4tosdscp - based on IP TOS/DSCP.
        ipv6 - based IP precedence.
        srcport - based on layer 4 source port.
        dstport - based on layer 4 destination port.
        "
    ::= { ibEponUniQosRuleEntry 2 }

ibEponUniQosRuleValue OBJECT-TYPE
    SYNTAX      Integer32
    MAX-ACCESS  read-create
    STATUS      current
    DESCRIPTION
        "
        The rule value based on the ibEponUniQosRuleSelector.
        "
    ::= { ibEponUniQosRuleEntry 3 }

ibEponUniQosRuleMacAddress OBJECT-TYPE
    SYNTAX      MacAddress
    MAX-ACCESS  read-create
    STATUS      current
    DESCRIPTION
        "
        MAC Address.
        "
    ::= { ibEponUniQosRuleEntry 4 }

ibEponUniQosRuleOperator OBJECT-TYPE
    SYNTAX      INTEGER
        {
            nevermatch(1),
            equal(2),
            notequal(3),
            lessthanequal(4),
            greaterthanequal(5),
            fieldexist(6),
            fieldnotexist(7),
            alwaysmatch(8)
        }
    MAX-ACCESS  read-create
    STATUS      current
    DESCRIPTION
        "
        nervermatch - value never match.
        equal - field equal to the value.
        notequal - field not equal to the value.
        lessthanequal - field less than or equal to the value.
        greaterthanequal - field greater than or equal to the value.
        fieldexist - value is ignored if field exists.
        fieldnotexist - value is ignored if field does not exist.
        alwaysmatch - value always match.
        "
    ::= { ibEponUniQosRuleEntry 5 }

ibEponUniQosRuleRowStatus OBJECT-TYPE
    SYNTAX      RowStatus
    MAX-ACCESS  read-create
    STATUS      current
    DESCRIPTION
        "
        The status of this table entry. Only active,
        createAndGo and the destory are supported.
        "
    ::= { ibEponUniQosRuleEntry 6 }

--
-- ibEponUniMirrorGroupTable
--

ibEponUniMirrorGroupTable OBJECT-TYPE
    SYNTAX      SEQUENCE OF IbEponUniMirrorGroupEntry
    MAX-ACCESS  not-accessible
    STATUS      current
    DESCRIPTION
        "
        Qos sub rule of the UNI.
        "
    ::= { ibEponUniSysMan 13 }

ibEponUniMirrorGroupEntry OBJECT-TYPE
    SYNTAX      IbEponUniMirrorGroupEntry
    MAX-ACCESS  not-accessible
    STATUS      current
    DESCRIPTION
        "
        The entry of the ibEponUniMirrorGroupTable.
        "
    INDEX
        {
            ifIndex,
            ibEponUniMirrorGroupID
        }
    ::= { ibEponUniMirrorGroupTable 1 }

IbEponUniMirrorGroupEntry ::= SEQUENCE
    {
        ibEponUniMirrorGroupID             Integer32,
        ibEponUniMirrorInboundPortList     OCTET STRING,
        ibEponUniMirrorOutboundPortList    OCTET STRING,
        ibEponUniMonitorPort               Integer32,
        ibEponUniMirrorRowStatus           RowStatus
    }

ibEponUniMirrorGroupID OBJECT-TYPE
    SYNTAX      Integer32
    MAX-ACCESS  not-accessible
    STATUS      current
    DESCRIPTION
        "Epon UNI mirror group ID."
    ::= { ibEponUniMirrorGroupEntry 1 }

ibEponUniMirrorInboundPortList OBJECT-TYPE
    SYNTAX      OCTET STRING
    MAX-ACCESS  read-write
    STATUS      current
    DESCRIPTION
        "
        UNI inbound port list.
        Each octet within this value specifies a set of eight ports,
        with the first octet specifying ports 1 through 8, the second
        octet specifying ports 9 through 16, etc.  Within each octet,
        the most significant bit represents the highest numbered UNI,
        and the least significant bit represents the lowest numbered UNI.
        Thus, each UNI port is represented by a single bit within the
        value of this object.  If that bit has a value of '1' then that
        port is allowed in the set of ports.  the port is not allowed if
        its bit has a value of '0'.
        "
    ::= { ibEponUniMirrorGroupEntry 2 }

ibEponUniMirrorOutboundPortList OBJECT-TYPE
    SYNTAX      OCTET STRING
    MAX-ACCESS  read-create
    STATUS      current
    DESCRIPTION
        "
        UNI outbound port list. For more information, see ibEponUniMirrorInboundPortList.
        "
    ::= { ibEponUniMirrorGroupEntry 3 }

ibEponUniMonitorPort OBJECT-TYPE
    SYNTAX      Integer32
    MAX-ACCESS  read-create
    STATUS      current
    DESCRIPTION
        "
        UNI monitor port.
        "
    ::= { ibEponUniMirrorGroupEntry 4 }

ibEponUniMirrorRowStatus OBJECT-TYPE
    SYNTAX      RowStatus
    MAX-ACCESS  read-create
    STATUS      current
    DESCRIPTION
        "
        RowStatus, Now support three status: createAndGo, active, destroy.
        "
    ::= { ibEponUniMirrorGroupEntry 5 }

--
-- ibEponUniMirrorGroupIdNextTable
--

ibEponUniMirrorGroupIdNextTable OBJECT-TYPE
    SYNTAX      SEQUENCE OF IbEponUniMirrorGroupIdNextEntry
    MAX-ACCESS  not-accessible
    STATUS      current
    DESCRIPTION
        "
        The next index table, which is used by ibEponUniMirrorGroupTable.
        "
    ::= { ibEponUniSysMan 14 }

ibEponUniMirrorGroupIdNextEntry OBJECT-TYPE
    SYNTAX      IbEponUniMirrorGroupIdNextEntry
    MAX-ACCESS  not-accessible
    STATUS      current
    DESCRIPTION
        "
        The entry of the table ibEponUniMirrorGroupIdNextEntry.
        "
    INDEX
        {
            ifIndex
        }
    ::= { ibEponUniMirrorGroupIdNextTable 1 }

IbEponUniMirrorGroupIdNextEntry ::= SEQUENCE
    {
        ibEponUniMirrorGroupIDNext    Integer32
    }

ibEponUniMirrorGroupIDNext OBJECT-TYPE
    SYNTAX      Integer32
    MAX-ACCESS  read-only
    STATUS      current
    DESCRIPTION
        "
        This object contains an appropriate value to be used for
        ibEponUniMirrorGroupID when creating rows in the
        ibEponUniMirrorGroupTable.
        "
    ::= { ibEponUniMirrorGroupIdNextEntry 1 }

--
-- ibEponUniMulticastCtrlInfoTable
--

ibEponUniMulticastCtrlInfoTable OBJECT-TYPE
    SYNTAX      SEQUENCE OF IbEponUniMulticastCtrlInfoEntry
    MAX-ACCESS  not-accessible
    STATUS      current
    DESCRIPTION
        "
        UNI multicast information which is active .
        "
    ::= { ibEponUniSysMan 15 }

ibEponUniMulticastCtrlInfoEntry OBJECT-TYPE
    SYNTAX      IbEponUniMulticastCtrlInfoEntry
    MAX-ACCESS  not-accessible
    STATUS      current
    DESCRIPTION
        "
        The entry of the table ibEponUniMulticastCtrlInfoTable.
        "
    INDEX
        {
            ifIndex,
            ibEponUniIndex,
            ibEponUniMultActVlan,
            ibEponUniMultActAddress
        }
    ::= { ibEponUniMulticastCtrlInfoTable 1 }

IbEponUniMulticastCtrlInfoEntry ::= SEQUENCE
    {
        ibEponUniMultActVlan          Integer32,
        ibEponUniMultActAddress       IpAddress,
        ibEponUniMultActAccessRule    INTEGER,
        ibEponUniMultActPreTimes      Integer32,
        ibEponUniMultActPreRemain     Integer32
    }

ibEponUniMultActVlan OBJECT-TYPE
    SYNTAX      Integer32
    MAX-ACCESS  not-accessible
    STATUS      current
    DESCRIPTION
        "
        The multicast vlan ID which is active.
        "
    ::= { ibEponUniMulticastCtrlInfoEntry 1 }

ibEponUniMultActAddress OBJECT-TYPE
    SYNTAX      IpAddress
    MAX-ACCESS  not-accessible
    STATUS      current
    DESCRIPTION
        "
        The multicast address which is active.
        "
    ::= { ibEponUniMulticastCtrlInfoEntry 2 }

ibEponUniMultActAccessRule OBJECT-TYPE
    SYNTAX      INTEGER
        {
            deny(1),
            permit(2),
            preview(3)
        }
    MAX-ACCESS  read-only
    STATUS      current
    DESCRIPTION
        "
        deny - deny the multicast packet.
        permit - permit the multicast packet.
        preview - permit the multicast packet with conditions.
        "
    ::= { ibEponUniMulticastCtrlInfoEntry 3 }

ibEponUniMultActPreTimes OBJECT-TYPE
    SYNTAX      Integer32
    MAX-ACCESS  read-only
    STATUS      current
    DESCRIPTION
        "
        The number of multicast preview times which is active.
        "
    ::= { ibEponUniMulticastCtrlInfoEntry 4 }

ibEponUniMultActPreRemain OBJECT-TYPE
    SYNTAX      Integer32
    MAX-ACCESS  read-only
    STATUS      current
    DESCRIPTION
        "
        The remanent time slice of multicast preview which is active.
        "
    ::= { ibEponUniMulticastCtrlInfoEntry 5 }

--
-- ibEponUniMulticastIndexNextTable
--

ibEponUniMulticastIndexNextTable OBJECT-TYPE
    SYNTAX      SEQUENCE OF IbEponUniMulticastIndexNextEntry
    MAX-ACCESS  not-accessible
    STATUS      current
    DESCRIPTION
        "
        The next index table, which is used by ibEponUniMulticastControlTable.
        "
    ::= { ibEponUniSysMan 16 }

ibEponUniMulticastIndexNextEntry OBJECT-TYPE
    SYNTAX      IbEponUniMulticastIndexNextEntry
    MAX-ACCESS  not-accessible
    STATUS      current
    DESCRIPTION
        "
        The entry of the table ibEponUniMulticastIndexNextEntry.
        "
    INDEX
        {
            ifIndex,
            ibEponUniIndex
        }
    ::= { ibEponUniMulticastIndexNextTable 1 }

IbEponUniMulticastIndexNextEntry ::= SEQUENCE
    {
        ibEponUniMulticastConfIndexNext    Integer32
    }

ibEponUniMulticastConfIndexNext OBJECT-TYPE
    SYNTAX      Integer32
    MAX-ACCESS  read-only
    STATUS      current
    DESCRIPTION
        "
        This object contains an appropriate value to be used for
        ibEponUniMulticastIndex when creating rows in the
        ibEponUniMulticastControlTable.
        "
    ::= { ibEponUniMulticastIndexNextEntry 1 }

--
-- ibEponCTCAlarmTable
--

ibEponCTCAlarmTable OBJECT-TYPE
    SYNTAX      SEQUENCE OF IbEponCTCAlarmEntry
    MAX-ACCESS  not-accessible
    STATUS      current
    DESCRIPTION
        "
        This table is used for setting CTC alarm of an ONU.
        "
    ::= { ibEponUniSysMan 17 }

ibEponCTCAlarmEntry OBJECT-TYPE
    SYNTAX      IbEponCTCAlarmEntry
    MAX-ACCESS  not-accessible
    STATUS      current
    DESCRIPTION
        "
        The entry of the ibEponCTCAlarmTable.
        "
    INDEX
        {
            ifIndex,
            ibEponCTCAlarmID
        }
    ::= { ibEponCTCAlarmTable 1 }

IbEponCTCAlarmEntry ::= SEQUENCE
    {
        ibEponCTCAlarmID              INTEGER,
        ibEponCTCAlarmProtocol        INTEGER,
        ibEponCTCAlarmEnable          TruthValue,
        ibEponCTCAlarmTriggerThresVal OCTET STRING,
        ibEponCTCAlarmClearThresVal   OCTET STRING
    }

ibEponCTCAlarmID OBJECT-TYPE
    SYNTAX      INTEGER
        {
-- ONU alarm ID
            onuEquipmentAlarm(1),
            onuPowerAlarm(2),
            onuBatteryMissing(3),
            onuBatteryFailure(4),
            onuBatteryVoltLow(5),
            onuPhysicalIntrusionAlarm(6),
            onuONUSelfTestFailure(7),
            onuONUTempHighAlarm(9),
            onuONUTempLowAlarm(10),
            onuIADConnectionFailure(11),
            onuPonIFSwitch(12),
            onuSleepStatusUpdate(13),
-- PON alarm ID
            ponRXPowerHighAlarm(257),
            ponRXPowerLowAlarm(258),
            ponTXPowerHighAlarm(259),
            ponTXPowerLowAlarm(260),
            ponTXBiasHighAlarm(261),
            ponTXBiasLowAlarm(262),
            ponVccHighAlarm(263),
            ponVccLowAlarm(264),
            ponTempHighAlarm(265),
            ponTempLowAlarm(266),
            ponRXPowerHighWarning(267),
            ponRXPowerLowWarning(268),
            ponTXPowerHighWarning(269),
            ponTXPowerLowWarning(270),
            ponTXBiasHighWarning(271),
            ponTXBiasLowWarning(272),
            ponVccHighWarning(273),
            ponVccLowWarning(274),
            ponTempHighWarning(275),
            ponTempLowWarning(276),
            ponDownstreamDropEventsAlarm(277),
            ponUpstreamDropEventsAlarm(278),
            ponDownstreamCRCErrorFramesAlarm(279),
            ponUpstreamCRCErrorFramesAlarm(280),
            ponDownstreamUndersizeFramesAlarm(281),
            ponUpstreamUndersizeFramesAlarm(282),
            ponDownstreamOversizeFramesAlarm(283),
            ponUpstreamOversizeFramesAlarm(284),
            ponDownstreamFragmentsAlarm(285),
            ponUpstreamFragmentsAlarm(286),
            ponDownstreamJabbersAlarm(287),
            ponUpstreamJabbersAlarm(288),
            ponDownstreamDiscardsAlarm(289),
            ponUpstreamDiscardsAlarm(290),
            ponDownstreamErrorsAlarm(291),
            ponUpstreamErrorsAlarm(292),
            ponDownstreamDropEventsWarning(293),
            ponUpstreamDropEventsWarning(294),
            ponDownstreamCRCErrorFramesWarning(295),
            ponUpstreamCRCErrorFramesWarning(296),
            ponDownstreamUndersizeFramesWarning(297),
            ponUpstreamUndersizeFramesWarning(298),
            ponDownstreamOversizeFramesWarning(299),
            ponUpstreamOversizeFramesWarning(300),
            ponDownstreamFragmentsWarning(301),
            ponUpstreamFragmentsWarning(302),
            ponDownstreamJabbersWarning(303),
            ponUpstreamJabbersWarning(304),
            ponDownstreamDiscardsWarning(305),
            ponUpstreamDiscardsWarning(306),
            ponDownstreamErrorsWarning(307),
            ponUpstreamErrorsWarning(308),
-- UNI alarm ID
            uniEthPortAutoNegFailure(769),
            uniEthPortLOS(770),
            uniEthPortFailure(771),
            uniEthPortLoopback(772),
            uniEthPortCongestion(773),
            uniDownstreamDropEventsAlarm(774),
            uniUpstreamDropEventsAlarm(775),
            uniDownstreamCRCErrorFramesAlarm(776),
            uniUpstreamCRCErrorFramesAlarm(777),
            uniDownstreamUndersizeFramesAlarm(778),
            uniUpstreamUndersizeFramesAlarm(779),
            uniDownstreamOversizeFramesAlarm(780),
            uniUpstreamOversizeFramesAlarm(781),
            uniDownstreamFragmentsAlarm(782),
            uniUpstreamFragmentsAlarm(783),
            uniDownstreamJabbersAlarm(784),
            uniUpstreamJabbersAlarm(785),
            uniDownstreamDiscardsAlarm(786),
            uniUpstreamDiscardsAlarm(787),
            uniDownstreamErrorsAlarm(788),
            uniUpstreamErrorsAlarm(789),
            uniStatusChangeTimesAlarm(790),
            uniDownstreamDropEventsWarning(791),
            uniUpstreamDropEventsWarning(792),
            uniDownstreamCRCErrorFramesWarning(793),
            uniUpstreamCRCErrorFramesWarning(794),
            uniDownstreamUndersizeFramesWarning(795),
            uniUpstreamUndersizeFramesWarning(796),
            uniDownstreamOversizeFramesWarning(797),
            uniUpstreamOversizeFramesWarning(798),
            uniDownstreamFragmentsWarning(799),
            uniUpstreamFragmentsWarning(800),
            uniDownstreamJabbersWarning(801),
            uniUpstreamJabbersWarning(802),
            uniDownstreamDiscardsWarning(803),
            uniUpstreamDiscardsWarning(804),
            uniDownstreamErrorsWarning(805),
            uniUpstreamErrorsWarning(806),
            uniStatusChangeTimesWarning(807),
            uniPOTSPortFailure(1025),
            uniE1PortFailure(1281),
            uniE1TimingUnlock(1282),
            uniE1LOS(1283)
        }
    MAX-ACCESS  read-only
    STATUS      current
    DESCRIPTION
        "
        The CTC alarm ID. There are 3 types of CTC alarms.
        ONU alarm:   0x0001~0x00ff
        PON alarm:   0x0101~0x01ff
        UNI alarm:   0x0301~0x05ff
        "
    ::= { ibEponCTCAlarmEntry 1 }

ibEponCTCAlarmProtocol OBJECT-TYPE
    SYNTAX      INTEGER
        {
            auto(0),
            ctc21(33),
            ctc30(48)
        }
    MAX-ACCESS  read-write
    STATUS      current
    DESCRIPTION
        "
        Choose a CTC protocol to set CTC alarm of an ONU.
        auto(0)  - Automatically select a CTC protocol.
        ctc21(33) - Use CTC2.1 protocol.
        ctc30(48) - Use CTC3.0 or later protocols.
        "
    DEFVAL { auto }
    ::= { ibEponCTCAlarmEntry 2 }

ibEponCTCAlarmEnable OBJECT-TYPE
    SYNTAX      TruthValue
    MAX-ACCESS  read-write
    STATUS      current
    DESCRIPTION
        "
        Enable or disable a CTC alarm of an ONU.
        true(1)  - alarm enable.
        false(2) - alarm disable.
        "
    ::= { ibEponCTCAlarmEntry 3 }

ibEponCTCAlarmTriggerThresVal OBJECT-TYPE
    SYNTAX      OCTET STRING
    MAX-ACCESS  read-write
    STATUS      current
    DESCRIPTION
        "
        Trigger threshold value of a CTC alarm on an ONU.
        For different CTC alarms, there are different units(dBm, mA, V, C).
        "
    ::= { ibEponCTCAlarmEntry 4 }

ibEponCTCAlarmClearThresVal OBJECT-TYPE
    SYNTAX      OCTET STRING
    MAX-ACCESS  read-write
    STATUS      current
    DESCRIPTION
        "
        Clear threshold value of a CTC alarm on an ONU.
        For different CTC alarms, there are different units(dBm, mA, V, C).
        "
    ::= { ibEponCTCAlarmEntry 5 }

ibEponUniErrorInfo OBJECT IDENTIFIER ::= { ibEponUniSysMan 18 }

ibEponCTCAlarmInfo OBJECT-TYPE
    SYNTAX      OCTET STRING
    MAX-ACCESS  accessible-for-notify
    STATUS      current
    DESCRIPTION
        "
        The information of an ONU CTC alarm.
        "
    ::= { ibEponUniErrorInfo 1 }

--
-- ibUniStatisticsTable
--

ibUniStatisticsTable OBJECT-TYPE
    SYNTAX      SEQUENCE OF IbUniStatisticsEntry
    MAX-ACCESS  not-accessible
    STATUS      current
    DESCRIPTION
        "
        This table is used for enabling or disabling statistics and setting period of a UNI.
        "
    ::= { ibEponUniSysMan 19 }

ibUniStatisticsEntry OBJECT-TYPE
    SYNTAX      IbUniStatisticsEntry
    MAX-ACCESS  not-accessible
    STATUS      current
    DESCRIPTION
        "
        The entry of the ibUniStatisticsTable.
        "
    INDEX
        {
            ifIndex,
            ibEponUniIndex
        }
    ::= { ibUniStatisticsTable 1 }

IbUniStatisticsEntry ::= SEQUENCE
    {
        ibUniStatisticsPeriodVal  Unsigned32,
        ibUniStatisticsEnable     TruthValue
    }

ibUniStatisticsPeriodVal OBJECT-TYPE
    SYNTAX      Unsigned32
    MAX-ACCESS  read-write
    STATUS      current
    DESCRIPTION
        "
        UNI statistics period value.
        "
    ::= { ibUniStatisticsEntry 1 }

ibUniStatisticsEnable OBJECT-TYPE
    SYNTAX      TruthValue
    MAX-ACCESS  read-write
    STATUS      current
    DESCRIPTION
        "
        Enable or disable statistics of an UNI.
        true(1)  - statistics enable.
        false(2) - statistics disable.
        "
    ::= { ibUniStatisticsEntry 2 }

--
-- ibUniPoeTable
--

ibUniPoeTable OBJECT-TYPE
    SYNTAX      SEQUENCE OF IbUniPoeEntry
    MAX-ACCESS  not-accessible
    STATUS      current
    DESCRIPTION
        "
        This table is used for configuring the PoE function for UNIs.
        "
    ::= { ibEponUniSysMan 20 }

ibUniPoeEntry OBJECT-TYPE
    SYNTAX      IbUniPoeEntry
    MAX-ACCESS  not-accessible
    STATUS      current
    DESCRIPTION
        "
        The entry of the ibUniPoeTable.
        "
    INDEX
        {
            ifIndex,
            ibEponUniIndex
        }
    ::= { ibUniPoeTable 1 }

IbUniPoeEntry ::= SEQUENCE
    {
        ibUniPoeEnable            TruthValue,
        ibUniPoeMode              INTEGER,
        ibUniPoePriority          INTEGER,
        ibUniPoeMaxPowerClass     INTEGER,
        ibUniPoeMaxPowerValue     Integer32,
        ibUniPoeLegacyEnable      TruthValue
    }

ibUniPoeEnable OBJECT-TYPE
    SYNTAX      TruthValue
    MAX-ACCESS  read-write
    STATUS      current
    DESCRIPTION
        "
        Enable PoE for an UNI.
        "
    DEFVAL { false }
    ::= { ibUniPoeEntry 1 }

ibUniPoeMode OBJECT-TYPE
    SYNTAX      INTEGER
        {
            signal(0),
            spare(1)
        }
    MAX-ACCESS  read-write
    STATUS      current
    DESCRIPTION
        "
        Set the PoE mode for an UNI.
        "
    DEFVAL { 0 }
    ::= { ibUniPoeEntry 2 }

ibUniPoePriority OBJECT-TYPE
    SYNTAX      INTEGER
        {
            high(0),
            critical(1),
            low(2)
        }
    MAX-ACCESS  read-write
    STATUS      current
    DESCRIPTION
        "
        Set the PoE priority for an UNI.
        "
    DEFVAL { 0 }
    ::= { ibUniPoeEntry 3 }

ibUniPoeMaxPowerClass OBJECT-TYPE
    SYNTAX      INTEGER
        {
            default(0),
            class0(1),
            class1(2),
            class2(3),
            class3(4),
            class4(5),
            undefined(255)
        }
    MAX-ACCESS  read-write
    STATUS      current
    DESCRIPTION
        "
        Set the PoE max power class for an UNI.
        "
    DEFVAL { 0 }
    ::= { ibUniPoeEntry 4 }

ibUniPoeMaxPowerValue OBJECT-TYPE
    SYNTAX      Integer32
    UNITS       "mW"
    MAX-ACCESS  read-write
    STATUS      current
    DESCRIPTION
        "
        Set the PoE max power value for an UNI.
        "
    DEFVAL { 0 }
    ::= { ibUniPoeEntry 5 }

ibUniPoeLegacyEnable OBJECT-TYPE
    SYNTAX      TruthValue
    MAX-ACCESS  read-write
    STATUS      current
    DESCRIPTION
        "
        Enable PoE legacy PD detection for an UNI.
        "
    ::= { ibUniPoeEntry 6 }

--
-- ibUniPoeInfoTable
--

ibUniPoeInfoTable OBJECT-TYPE
    SYNTAX      SEQUENCE OF IbUniPoeInfoEntry
    MAX-ACCESS  not-accessible
    STATUS      current
    DESCRIPTION
        "
        This table is used for getting UNIs' PoE information.
        "
    ::= { ibEponUniSysMan 21 }

ibUniPoeInfoEntry OBJECT-TYPE
    SYNTAX      IbUniPoeInfoEntry
    MAX-ACCESS  not-accessible
    STATUS      current
    DESCRIPTION
        "
        The entry of the ibUniPoeInfoTable.
        "
    INDEX
        {
            ifIndex,
            ibEponUniIndex
        }
    ::= { ibUniPoeInfoTable 1 }

IbUniPoeInfoEntry ::= SEQUENCE
    {
        ibUniPoeInfoCapability    INTEGER,
        ibUniPoeInfoEnable        TruthValue,
        ibUniPoeInfoLegacyEnable  TruthValue,
        ibUniPoeInfoMode          INTEGER,
        ibUniPoeInfoPriority      INTEGER,
        ibUniPoeInfoMaxPwrClass   INTEGER,
        ibUniPoeInfoMaxPwrValue   Integer32,
        ibUniPoeInfoPdClass       INTEGER,
        ibUniPoeInfoPwrSuppStat   INTEGER,
        ibUniPoeInfoSignalErrCnt  Integer32,
        ibUniPoeInfoPwrDeniedCnt  Integer32,
        ibUniPoeInfoPwrOverCnt    Integer32,
        ibUniPoeInfoCurOverCnt    Integer32,
        ibUniPoeInfoPdUndetectCnt Integer32,
        ibUniPoeInfoMaxPower      Integer32,
        ibUniPoeInfoCurOutputPwr  Integer32,
        ibUniPoeInfoAvgOutputPwr  Integer32,
        ibUniPoeInfoPeakOutputPwr Integer32
    }

ibUniPoeInfoCapability OBJECT-TYPE
    SYNTAX      INTEGER
        {
            incapable(0),
            capable(1)
        }
    MAX-ACCESS  read-only
    STATUS      current
    DESCRIPTION
        "
        UNI PoE capability.
        "
    ::= { ibUniPoeInfoEntry 1 }

ibUniPoeInfoEnable OBJECT-TYPE
    SYNTAX      TruthValue
    MAX-ACCESS  read-only
    STATUS      current
    DESCRIPTION
        "
        UNI PoE enabling status.
        "
    ::= { ibUniPoeInfoEntry 2 }

ibUniPoeInfoLegacyEnable OBJECT-TYPE
    SYNTAX      TruthValue
    MAX-ACCESS  read-only
    STATUS      current
    DESCRIPTION
        "
        UNI PoE legacy PD detection enabling status.
        "
    DEFVAL { false }
    ::= { ibUniPoeInfoEntry 3 }

ibUniPoeInfoMode OBJECT-TYPE
    SYNTAX      INTEGER
        {
            signal(0),
            spare(1)
        }
    MAX-ACCESS  read-only
    STATUS      current
    DESCRIPTION
        "
        UNI PoE mode.
        "
    ::= { ibUniPoeInfoEntry 4 }

ibUniPoeInfoPriority OBJECT-TYPE
    SYNTAX      INTEGER
        {
            high(0),
            critical(1),
            low(2)
        }
    MAX-ACCESS  read-only
    STATUS      current
    DESCRIPTION
        "
        UNI PoE priority.
        "
    ::= { ibUniPoeInfoEntry 5 }

ibUniPoeInfoMaxPwrClass OBJECT-TYPE
    SYNTAX      INTEGER
        {
            default(0),
            class0(1),
            class1(2),
            class2(3),
            class3(4),
            class4(5),
            undefined(255)
        }
    MAX-ACCESS  read-only
    STATUS      current
    DESCRIPTION
        "
        UNI PoE max power class.
        "
    ::= { ibUniPoeInfoEntry 6 }

ibUniPoeInfoMaxPwrValue OBJECT-TYPE
    SYNTAX      Integer32
    UNITS       "mW"
    MAX-ACCESS  read-only
    STATUS      current
    DESCRIPTION
        "
        UNI PoE max power value.
        "
    ::= { ibUniPoeInfoEntry 7 }

ibUniPoeInfoPdClass OBJECT-TYPE
    SYNTAX      INTEGER
        {
            default(0),
            class0(1),
            class1(2),
            class2(3),
            class3(4),
            class4(5),
            undefined(255)
        }
    MAX-ACCESS  read-only
    STATUS      current
    DESCRIPTION
        "
        UNI PoE powered device class.
        "
    ::= { ibUniPoeInfoEntry 8 }

ibUniPoeInfoPwrSuppStat OBJECT-TYPE
    SYNTAX      INTEGER
        {
            noNeed(0),
            searching(1),
            power(2),
            force(3),
            forceFailed(4),
            powerFailed(5)
        }
    MAX-ACCESS  read-only
    STATUS      current
    DESCRIPTION
        "
        UNI PoE power supply status.
        "
    ::= { ibUniPoeInfoEntry 9 }

ibUniPoeInfoSignalErrCnt OBJECT-TYPE
    SYNTAX      Integer32
    MAX-ACCESS  read-only
    STATUS      current
    DESCRIPTION
        "
        UNI PoE signal error count.
        "
    ::= { ibUniPoeInfoEntry 10 }

ibUniPoeInfoPwrDeniedCnt OBJECT-TYPE
    SYNTAX      Integer32
    MAX-ACCESS  read-only
    STATUS      current
    DESCRIPTION
        "
        UNI PoE power denied count.
        "
    ::= { ibUniPoeInfoEntry 11 }

ibUniPoeInfoPwrOverCnt OBJECT-TYPE
    SYNTAX      Integer32
    MAX-ACCESS  read-only
    STATUS      current
    DESCRIPTION
        "
        UNI PoE power overload count.
        "
    ::= { ibUniPoeInfoEntry 12 }

ibUniPoeInfoCurOverCnt OBJECT-TYPE
    SYNTAX      Integer32
    MAX-ACCESS  read-only
    STATUS      current
    DESCRIPTION
        "
        UNI PoE current overload count.
        "
    ::= { ibUniPoeInfoEntry 13 }

ibUniPoeInfoPdUndetectCnt OBJECT-TYPE
    SYNTAX      Integer32
    MAX-ACCESS  read-only
    STATUS      current
    DESCRIPTION
        "
        UNI PoE powered device undetected count.
        "
    ::= { ibUniPoeInfoEntry 14 }

ibUniPoeInfoMaxPower OBJECT-TYPE
    SYNTAX      Integer32
    UNITS       "mW"
    MAX-ACCESS  read-only
    STATUS      current
    DESCRIPTION
        "
        UNI PoE max power.
        "
    ::= { ibUniPoeInfoEntry 15 }

ibUniPoeInfoCurOutputPwr OBJECT-TYPE
    SYNTAX      Integer32
    UNITS       "mW"
    MAX-ACCESS  read-only
    STATUS      current
    DESCRIPTION
        "
        UNI PoE current output power.
        "
    ::= { ibUniPoeInfoEntry 16 }

ibUniPoeInfoAvgOutputPwr OBJECT-TYPE
    SYNTAX      Integer32
    UNITS       "mW"
    MAX-ACCESS  read-only
    STATUS      current
    DESCRIPTION
        "
        UNI PoE average output power.
        "
    ::= { ibUniPoeInfoEntry 17 }

ibUniPoeInfoPeakOutputPwr OBJECT-TYPE
    SYNTAX      Integer32
    UNITS       "mW"
    MAX-ACCESS  read-only
    STATUS      current
    DESCRIPTION
        "
        UNI PoE peak output power.
        "
    ::= { ibUniPoeInfoEntry 18 }

--
-- ibEponUni NOTIFICATION
--

ibEponUniTrap OBJECT IDENTIFIER ::= { ibEponUni 2 }

ibEponUniTrapPrefix OBJECT IDENTIFIER ::= { ibEponUniTrap 0 }

ibEponUniLinkUpTrap NOTIFICATION-TYPE
    OBJECTS
        {
            ifIndex,
            ifDescr,
            ibEponUniIndex,
            ibEponUniDescr,
            ibEponUniAdminStatus
        }
    STATUS      current
    DESCRIPTION
        "
        A ibEponUniLinkUpTrap notification is sent
        when the UNI up event is detected
        and the transmitting switch is turned on.
        "
    ::= { ibEponUniTrapPrefix 1 }

ibEponUniLinkDownTrap NOTIFICATION-TYPE
    OBJECTS
        {
            ifIndex,
            ifDescr,
            ibEponUniIndex,
            ibEponUniDescr,
            ibEponUniAdminStatus
        }
    STATUS      current
    DESCRIPTION
        "
        A ibEponUniLinkDownTrap notification is sent
        when the UNI down event is detected
        and the transmitting switch is turned on.
        "
    ::= { ibEponUniTrapPrefix 2 }

ibEponUniLoopBackDetectedTrap NOTIFICATION-TYPE
    OBJECTS
        {
            ifIndex,
            ifDescr,
            ibEponUniIndex,
            ibEponUniDescr,
            ibEponUniVlan
        }
    STATUS      current
    DESCRIPTION
        "
        A ibEponUniLoopBackDetectedTrap notification is sent
        when the UNI loopback event is detected.
        "
    ::= { ibEponUniTrapPrefix 3 }
ibEponUniLoopBackRecoveredTrap NOTIFICATION-TYPE
    OBJECTS
        {
            ifIndex,
            ifDescr,
            ibEponUniIndex,
            ibEponUniDescr,
            ibEponUniVlan
        }
    STATUS      current
    DESCRIPTION
        "
        A ibEponUniLoopBackRecoveredTrap notification is sent
        when the UNI loopback is recovered.
        "
    ::= { ibEponUniTrapPrefix 4 }

ibEponCTCAlarmTrap NOTIFICATION-TYPE
    OBJECTS
        {
            ifIndex,
            ifDescr,
            ibEponCTCAlarmID,
            ibEponUniIndex,
            ibEponUniDescr,
            ibEponCTCAlarmInfo
        }
    STATUS      current
    DESCRIPTION
        "
        A ibEponCTCAlarmTrap notification is sent
        when an ONU CTC alarm is detected.
        "
    ::= { ibEponUniTrapPrefix 5 }

ibEponCTCAlarmRecoverTrap NOTIFICATION-TYPE
    OBJECTS
        {
            ifIndex,
            ifDescr,
            ibEponCTCAlarmID,
            ibEponUniIndex,
            ibEponUniDescr,
            ibEponCTCAlarmInfo
        }
    STATUS      current
    DESCRIPTION
        "
        A ibEponCTCAlarmRecoverTrap notification is sent
        when an ONU CTC alarm is cleared.
        "
    ::= { ibEponUniTrapPrefix 6 }

END
