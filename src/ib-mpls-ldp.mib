-- =============================================================================
-- Copyright (C) 2023 Intelbras S.A. All rights reserved.
--
-- Description:Multiprotocol Label Switching Label Distribution Protocol MIB
-- Reference:
-- Version: V1.7
-- History:
--  VERSION    AUTHOR/          Change Description
--  OLD/NEW     DATE
--
--  #/1.1     Lingesh M        + Initial create.
--             27/08/99
--  #/1.2     27/09/99         + Replaced the MIB objects
--                                  - ibMplsLdpLsrMaxIngressCrlspTnls
--                                  - ibMplsLdpLsrMaxInbetwnCrlspTnls
--                               with ibMplsLdpLsrMaxCrlspTnls
--  1.2/1.3   19/10/99         + Added ibMplsLdpPeerType in Peer Table.
--            04/10/99         + Added ibMplsLdpEntityIfTable.
--  1.3/1.4   23/11/99         + Added MIB object for Hello Hold Time in Entity
--                               Table, modified Cr-lsp Tnl index of type
--                               read-create to not-accessible.
--                             + Removed ibMplsLdpSessionRowStatus mib-object.
--
--   1.1      03/01/2k         + MPLS Release 1.0.0.0
--             Naren
--
--   1.2      27/01/2k         + Modified for MPLS Implementation
--             Naren             Following objects are added in the Incarnation table
--                                 ibMplsLdpLsrMaxVcmCapability
--                                 ibMplsLdpLsrVcmPathVecInAllLblMapPresent
--                                 ibMplsLdpLsrRequestRetrytimerValue
--                                 ibMplsLdpLsrNumOfRequestRetryAttempts
--                               Following Notifications are added
--                                 ibMplsLdpIncarnUpEventFailure
--                                 ibMplsLdpIncarnDownEventFailure
--                                 ibMplsLdpEntityUpEventFailure
--                                 ibMplsLdpEntityDownEventFailure
--
--   1.3      03/04/2k         + Changed FS related identification to ib
--             David             related identification.
--   1.4      03/14/2003       add ibMplsLdpSessionUpEventFailure and ibMplsLdpSessionDownEventFailure
--   V1.5 2004-10-12 updated by gaolong
--        Change SYNTAX clause value from INTEGER to Unsigned because the value range is (1..4294967295).
--        Change MAX-ACCESS clause value of ibMplsLdpCrlspTnlIndex to accessible-for-notify
--        because this index node is used when sending notification.
--   V1.6 2004-11-5  updated by liuxiaolong
--        Change DEFVAL clause value of ibMplsLdpLsrHopCountLimit to 32.
--   V1.7 2022-08-11 Modified by Zhou wan, Modified ibMplsLdpNotifications
-- ====================================================================================
--
-- Full Copyright Notice of the MIB that was extracted from Draft-ietf-mpls-ldp-mib-01 as follows:
--
--Copyright (C) The Internet Society (1999). All Rights Reserved.
--
--
--   This document and translations of it may be copied and furnished to
--   others, and derivative works that comment on or otherwise explain it
--   or assist in its implementation may be prepared, copied, published
--   and distributed, in whole or in part, without restriction of any
--   kind, provided that the above copyright notice and this paragraph are
--   included on all such copies and derivative works.  However, this
--   document itself may not be modified in any way, such as by removing
--   the copyright notice or references to the Internet Society or other
--   Internet organizations, except as needed for the  purpose of
--   developing Internet standards in which case the procedures for
--   copyrights defined in the Internet Standards process must be
--   followed, or as required to translate it into languages other than
--   English.
--
--   The limited permissions granted above are perpetual and will not be
--   revoked by the Internet Society or its successors or assigns.
--
--   This document and the information contained herein is provided on an
--   "AS IS" basis and THE INTERNET SOCIETY AND THE INTERNET ENGINEERING
--   TASK FORCE DISCLAIMS ALL WARRANTIES, EXPRESS OR IMPLIED, INCLUDING
--   BUT NOT LIMITED TO ANY WARRANTY THAT THE USE OF THE INFORMATION
--   HEREIN WILL NOT INFRINGE ANY RIGHTS OR ANY IMPLIED WARRANTIES OF
--   MERCHANTABILITY OR FITNESS FOR A PARTICULAR PURPOSE.
--
--   MPLS Label Distribution Protocol MIB Definitions
IB-MPLS-LDP-MIB DEFINITIONS ::= BEGIN

     IMPORTS
         ibMpls
             FROM IB-OID-MIB
         OBJECT-TYPE, MODULE-IDENTITY, NOTIFICATION-TYPE,
         Counter32, Unsigned32,IpAddress
             FROM SNMPv2-SMI
         TEXTUAL-CONVENTION, TruthValue, RowStatus, TimeInterval
             FROM SNMPv2-TC;

     ibMplsLdp MODULE-IDENTITY
         LAST-UPDATED "202208111100Z"     -- August 11, 2022 at 11:00 GMT
         ORGANIZATION
             "Intelbras S.A. Industria de Telecomunicacao Eletronica Brasileria."
         CONTACT-INFO
             ""
         DESCRIPTION  "All rights reserved"
         REVISION
             "202208111100Z"   -- August 11, 2022 at 11:00 GMT
         DESCRIPTION
             "Modified ibMplsLdpNotifications."
         REVISION     "9611082155Z"
         DESCRIPTION  "The MIB for MPLS LDP module.
                       This MIB has been derived from the MPLS Working
                       group LDP MIB <drst-ietf-mpls-ldp-mib-01.txt> and
                       MPLS Working group TE MIB <draft-ietf-mpls-te-mib
                       -01.txt>."

         ::= { ibMpls 2 }

     --********************************************************************
     -- MPLS LDP Textual Conventions
     --********************************************************************
     --

           DisplayString ::=
               OCTET STRING
          -- This data type is used to model textual information taken
          -- from the NVT ASCII character set.  By convention, objects
          -- with this syntax are declared as having
          --
                (SIZE (0..255))

           PhysAddress ::=
               OCTET STRING
          -- This data type is used to model media addresses.  For many
          -- types of media, this will be in a binary representation.
          -- For example, an ethernet address would be represented as
          -- a string of 6 octets.

  BitRate ::= INTEGER

  BurstSize ::= INTEGER


     MplsLsrIdentifier ::= TEXTUAL-CONVENTION
         STATUS      current
         DESCRIPTION
             "The Label Switch Router (LSR) identifier
             is the first 4 bytes or the IP Address component
             of the Label Distribution Protocol (LDP) identifier."
         SYNTAX      OCTET STRING (SIZE (4))

     MplsLdpGenAddr ::= TEXTUAL-CONVENTION
         STATUS      current
         DESCRIPTION
             "The value of an network layer or data link layer address."
         SYNTAX      OCTET STRING (SIZE (0..64))

     MplsLdpIdentifier ::= TEXTUAL-CONVENTION
         STATUS      current
         DESCRIPTION
             "The LDP identifier is a six octet quantity
             which is used to identify an Label Switch Router
             (LSR) label space.

             The first four octets encode an IP address
             assigned to the LSR, and the last two octets
             identify a specific label space within the LSR."
         SYNTAX      OCTET STRING (SIZE (6))

     AtmVpIdentifier ::= TEXTUAL-CONVENTION
          STATUS      current
          DESCRIPTION
              "The VPI value for a VPL. The value VPI=0 is not
              used for a VPL not associated with a VCL. For ATM
              UNIs supporting VPCs the VPI value ranges from 1
              to 255. For ATM UNIs supporting VCCs the VPI value
              ranges from 0 to 255.  The maximum VPI value
              cannot exceed the value allowable by
              atmInterfaceMaxVpiBits defined in ATM-MIB."
          SYNTAX INTEGER (0..4095)

     AtmVcIdentifier ::= TEXTUAL-CONVENTION
          STATUS      current
          DESCRIPTION
              "The VCI value for a VCL. The maximum VCI value
              cannot exceed the value allowable by
              atmInterfaceMaxVciBits defined in ATM-MIB."
          SYNTAX INTEGER (0..65535)

     AddressFamilyNumbers ::= TEXTUAL-CONVENTION
        STATUS        current
        DESCRIPTION
            "An address family.  Values are defined in RFC 1700 -
             Assigned Numbers.  All values may not be relevant in
             all contexts when used in this MIB, but are included
             for completeness."
        REFERENCE
            "RFC  1700   Assigned Numbers, Reynolds and  Postel,
             Oct. 1994"
        SYNTAX        INTEGER {
                        other(0),
                         ipv4(1),
                         ipv6(2),
                         nsap(3),
                         hdlc(4),
                         bbn1822(5),
                         ieee802(6),
                         e163(7),
                         e164(8),
                         f69(9),
                         x121(10),
                         ipx(11),
                         appleTalk(12),
                         decnetIV(13),
                         banyanVines(14),
                         e164WithNsap(15)
                     }


     MplsLabel ::= TEXTUAL-CONVENTION
        STATUS        current
        DESCRIPTION
            "Represents an MPLS label.  Note that the contents of
             a  label  field are interpreted in an interface-type
             specific fashion.  For example, the label carried in
             the MPLS shim header is 20 bits wide and the top  12
             bits  must  be zero.  The frame relay label  can  be
             either 10, 17 or 23 bits wide depending on the  size
             of the DLCI field size and the top 22, 15, or 9 bits
             must  be  zero, respectively.  For an ATM interface,
             the  lowermost 16 bits are interpreted as  the  VCI,
             the  next  8 bits as the VPI and the remaining  bits
             must  be  zero.   Also  note the  permissible  label
             values  are  also a function of the interface  type.
             For  example,  the value 3 has special semantics  in
             the  control plane for an MPLS shim header label and
             is not a valid label value in the datapath."
        REFERENCE
            "1.  MPLS  Label Stack Encoding, Rosen et al,  draft-
             ietf-mpls-label-encaps-04.txt, April 1999.
            2.  Use  of  Label Switching on Frame Relay Networks,
             Conta et al, draft-ietf-mpls-fr-03.txt, Nov. 1998."
        SYNTAX INTEGER

     MplsTunnelIndex ::= TEXTUAL-CONVENTION
        STATUS        current
        DESCRIPTION
            "Index into mplsTunnelTable."
        SYNTAX        INTEGER (0..65535)

     ibMplsLdpObjects       OBJECT IDENTIFIER ::= { ibMplsLdp 1 }
     ibMplsLdpNotifications OBJECT IDENTIFIER ::= { ibMplsLdp 2 }
     ibMplsLdpScalarGroup   OBJECT IDENTIFIER ::= { ibMplsLdp 3 }


     --****************************************************************
     -- MPLS LDP Objects
     --****************************************************************

     ibMplsLdpLsrObjects            OBJECT IDENTIFIER ::= { ibMplsLdpObjects 1 }
     ibMplsLdpEntityObjects         OBJECT IDENTIFIER ::= { ibMplsLdpObjects 2 }
     ibMplsLdpPeerObjects           OBJECT IDENTIFIER ::= { ibMplsLdpObjects 3 }
     ibMplsLdpSessionObjects        OBJECT IDENTIFIER ::= { ibMplsLdpObjects 4 }
     ibMplsLdpHelloAdjacencyObjects OBJECT IDENTIFIER ::= { ibMplsLdpObjects 5 }
     ibMplsLdpCrlspTnlObjects       OBJECT IDENTIFIER ::= { ibMplsLdpObjects 6 }

     --
     -- The MPLS Label Distribution Protocol Label Switch Router Objects
     --
     ibMplsLdpLsrIncarnTable OBJECT-TYPE
         SYNTAX      SEQUENCE OF IbMplsLdpLsrIncarnEntry
         MAX-ACCESS  not-accessible
         STATUS      current
         DESCRIPTION
             "MPLS provides support for multiple incarnations of the
              MPLS Stack in a target. The LSR defined in the standard <IETF
              DRAFT> MIB is treated as an incarnation in this MIB. Using a
              local policy the Network administrator must group the LDP Entities
              that should be placed in an incarnation."
         ::= { ibMplsLdpLsrObjects 1 }

     ibMplsLdpLsrIncarnEntry OBJECT-TYPE
         SYNTAX      IbMplsLdpLsrIncarnEntry
         MAX-ACCESS  not-accessible
         STATUS      current
         DESCRIPTION
             "An entry in this table represents an LSR incarnation.
              All the entries in this table are created initially when the
              LDP is initiated. The row status of each entry will be in
              'notInService' state initially. The row status must be set to
              'active' after the necessary configurations are complete with
              respect to an incarnation.

              Currenlty the LSR ID of the incarnation is the only mandatory
              parameter that must be set before the rowStatus is set to
              'active'.

              An LSR Incarnation Entity is uniquely indexed by its Incarnation
              Identifier."
         INDEX       {  ibMplsLdpLsrIncarnID }
         ::= { ibMplsLdpLsrIncarnTable 1 }

     IbMplsLdpLsrIncarnEntry ::= SEQUENCE {
         ibMplsLdpLsrID                                MplsLsrIdentifier,
         ibMplsLdpLsrLoopDetectionPresent              TruthValue,
         ibMplsLdpLsrLoopDetectionAdminStatus          INTEGER,
         ibMplsLdpLsrPathVectorLimit                   INTEGER,
         ibMplsLdpLsrHopCountLimit                     INTEGER,
         ibMplsLdpLsrLoopPreventionPresent             TruthValue,
         ibMplsLdpLsrLoopPreventionAdminStatus         INTEGER,
         ibMplsLdpLsrLabelRetentionMode                INTEGER,
         ibMplsLdpLsrIncarnID                          INTEGER,
         ibMplsLdpLsrMaxLdpEntities                    INTEGER,
         ibMplsLdpLsrMaxLocalPeers                     INTEGER,
         ibMplsLdpLsrMaxRemotePeers                    INTEGER,
         ibMplsLdpLsrMaxIfaces                         INTEGER,
         ibMplsLdpLsrMaxLsps                           INTEGER,
         ibMplsLdpLsrMaxCrlspTnls                      INTEGER,
         ibMplsLdpLsrMaxErhopPerCrlspTnl               INTEGER,
         ibMplsLdpLsrRowStatus                         RowStatus,
         ibMplsLdpLsrMaxVcmCapability                  INTEGER,
         ibMplsLdpLsrVcmPathVecInAllLblMapPresent      TruthValue,
         ibMplsLdpLsrRequestRetrytimerValue            INTEGER,
         ibMplsLdpLsrNumOfRequestRetryAttempts         INTEGER
    }

     ibMplsLdpLsrID OBJECT-TYPE
         SYNTAX      MplsLsrIdentifier
         MAX-ACCESS  read-write
         STATUS      current
         DESCRIPTION
             "The LSR's Identifier."
         ::= { ibMplsLdpLsrIncarnEntry 1 }

     ibMplsLdpLsrLoopDetectionPresent OBJECT-TYPE
         SYNTAX      TruthValue
         MAX-ACCESS  read-only
         STATUS      current
         DESCRIPTION
             "A indication of whether this LSR supports loop detection.  A
             value of 'true' indicates this LSR does support loop detection.
             A value of 'false' indicates this LSR does not support
             loop detection."
         DEFVAL  { true }
         ::= { ibMplsLdpLsrIncarnEntry 2 }

     ibMplsLdpLsrLoopDetectionAdminStatus OBJECT-TYPE
         SYNTAX      INTEGER {
                         enabled(1),
                         disabled(2)
                     }
         MAX-ACCESS  read-write
         STATUS      current
         DESCRIPTION
             "To enable loop detection the value of this object should be
             'enabled(1)'.  Otherwise, to turn off loop detection, set this
             value to 'disabled(2)'."
         DEFVAL  { enabled }
         ::= { ibMplsLdpLsrIncarnEntry 3 }

     ibMplsLdpLsrPathVectorLimit OBJECT-TYPE
         SYNTAX      INTEGER
         MAX-ACCESS  read-write
         STATUS      current
         DESCRIPTION
             "This object only has meaning if ibMplsLdpLsrLoopDetectionPresent
             has the value of 'true'.

             The value of this object represents the limit of path vectors which
             this LSR uses to treat the message as if it had traversed a loop."
         DEFVAL  { 32 }
         ::= { ibMplsLdpLsrIncarnEntry 4 }

     ibMplsLdpLsrHopCountLimit OBJECT-TYPE
         SYNTAX      INTEGER
         MAX-ACCESS  read-write
         STATUS      current
         DESCRIPTION
             "This object only has meaning if ibMplsLdpLsrLoopDetectionPresent
             has the value of 'true'.

             The value of this object represents the limit on the Hop Count
             which this LSR uses to treat the message as if it had traversed a
             loop."
         DEFVAL  { 32 }
         ::= { ibMplsLdpLsrIncarnEntry 5 }

     ibMplsLdpLsrLoopPreventionPresent OBJECT-TYPE
         SYNTAX      TruthValue
         MAX-ACCESS  read-only
         STATUS      current
         DESCRIPTION
             "A indication of whether this LSR supports loop prevention.  A
             value of 'true' indicates this LSR does support loop prevention.
             A value of 'false' indicates this LSR does not support loop
             prevention.

             Current release of MPLS does not provide support to assign
             this MIB object with a value 'true'."
         DEFVAL  { false }
         ::= { ibMplsLdpLsrIncarnEntry 6 }

     ibMplsLdpLsrLoopPreventionAdminStatus OBJECT-TYPE
         SYNTAX      INTEGER {
                         enabled(1),
                         disabled(2)
                     }
         MAX-ACCESS  read-write
         STATUS      current
         DESCRIPTION
             "To enable loop prevention the value of this object should be
             'enabled(1)'.  Otherwise, to turn off loop prevention, set this
             value to 'disabled(2)'.

             Current release of MPLS does not provide support to assign
             this MIB object with a value 'enabled'."
         DEFVAL  { disabled }
         ::= { ibMplsLdpLsrIncarnEntry 7 }

     ibMplsLdpLsrLabelRetentionMode OBJECT-TYPE
         SYNTAX      INTEGER {
                         conservative(1),
                         liberal(2)
                     }
         MAX-ACCESS  read-write
         STATUS      current
         DESCRIPTION
             "The LSR can be configured to use either conservative or liberal
              label retention mode.

             If the value of this object is conservative(1) then advertized
             label mappings are retained only if they will be used to forward
             packets, i.e. if label came from a valid next hop.  If the value of
             this object is liberal(2) then all advertized label mappings are
             retained whether they are from a valid next hop or not.

             Current release of MPLS does not provide support to assign
             this MIB object with a value 'liberal'."
         DEFVAL  { conservative }
         ::= { ibMplsLdpLsrIncarnEntry 8 }

     ibMplsLdpLsrIncarnID   OBJECT-TYPE
         SYNTAX     INTEGER
         MAX-ACCESS read-only
         STATUS     current
         DESCRIPTION
             "The incarnation acts as index to all the elements in this
              table."
         ::= { ibMplsLdpLsrIncarnEntry  9 }

     ibMplsLdpLsrMaxLdpEntities OBJECT-TYPE
         SYNTAX      INTEGER (1..1024)
         MAX-ACCESS  read-write
         STATUS      current
         DESCRIPTION
             "The maximum number of LDP entities that can be supported by this
              Incarnation."
         ::= { ibMplsLdpLsrIncarnEntry 10 }

     ibMplsLdpLsrMaxLocalPeers OBJECT-TYPE
         SYNTAX      INTEGER (1..1024)
         MAX-ACCESS  read-write
         STATUS      current
         DESCRIPTION
             "The maximum number of Local LDP peers that can be supported by
              this Incarnation."
         ::= { ibMplsLdpLsrIncarnEntry 11 }

     ibMplsLdpLsrMaxRemotePeers OBJECT-TYPE
         SYNTAX      INTEGER (1..1024)
         MAX-ACCESS  read-write
         STATUS      current
         DESCRIPTION
             "The maximum number of Remote LDP peers that can be supported by
              this Incarnation."
         ::= { ibMplsLdpLsrIncarnEntry 12 }

     ibMplsLdpLsrMaxIfaces OBJECT-TYPE
         SYNTAX      INTEGER
         MAX-ACCESS  read-write
         STATUS      current
         DESCRIPTION
             "The maximum number of Label enabled Interfaces that can be
              supported by this Incarnation."
         ::= { ibMplsLdpLsrIncarnEntry 13 }

     ibMplsLdpLsrMaxLsps OBJECT-TYPE
         SYNTAX      INTEGER
         MAX-ACCESS  read-write
         STATUS      current
         DESCRIPTION
             "The maximum number of Label Switched Paths that can be
              supported by this Incarnation."
         ::= { ibMplsLdpLsrIncarnEntry 14 }

     ibMplsLdpLsrMaxCrlspTnls OBJECT-TYPE
         SYNTAX      INTEGER
         MAX-ACCESS  read-write
         STATUS      current
         DESCRIPTION
             "The maximum number of CRLSPs that can be supported by this
             Incarnation."
         ::= { ibMplsLdpLsrIncarnEntry 15 }


     ibMplsLdpLsrMaxErhopPerCrlspTnl OBJECT-TYPE
         SYNTAX      INTEGER
         MAX-ACCESS  read-write
         STATUS      current
         DESCRIPTION
             " The maximum number of ER-Hops that can be supported in a
              CRLSP tunnel."
         ::= { ibMplsLdpLsrIncarnEntry 16 }

     ibMplsLdpLsrRowStatus OBJECT-TYPE
         SYNTAX      RowStatus
         MAX-ACCESS  read-create
         STATUS      current
              DESCRIPTION
                  "An object that allows entries in this table to
                  be created and deleted using the
                  RowStatus convention."
         ::= { ibMplsLdpLsrIncarnEntry 17 }

     ibMplsLdpLsrMaxVcmCapability OBJECT-TYPE
         SYNTAX      INTEGER
         MAX-ACCESS  read-write
         STATUS      current
         DESCRIPTION
                  "  "
         ::= { ibMplsLdpLsrIncarnEntry 18 }

     ibMplsLdpLsrVcmPathVecInAllLblMapPresent OBJECT-TYPE
         SYNTAX      TruthValue
         MAX-ACCESS  read-write
         STATUS      current
         DESCRIPTION
                  "  "
         ::= { ibMplsLdpLsrIncarnEntry 19 }

     ibMplsLdpLsrRequestRetrytimerValue  OBJECT-TYPE
         SYNTAX      INTEGER
         MAX-ACCESS  read-write
         STATUS      current
         DESCRIPTION
                  "  "
         ::= { ibMplsLdpLsrIncarnEntry 20 }

     ibMplsLdpLsrNumOfRequestRetryAttempts OBJECT-TYPE
         SYNTAX      INTEGER
         MAX-ACCESS  read-write
         STATUS      current
         DESCRIPTION
                  "  "
         ::= { ibMplsLdpLsrIncarnEntry 21 }


     --
     -- The MPLS Label Distribution Protocol Entity Table
     --

     ibMplsLdpEntityTable OBJECT-TYPE
         SYNTAX      SEQUENCE OF IbMplsLdpEntityEntry
         MAX-ACCESS  not-accessible
         STATUS      current
         DESCRIPTION
             "This table contains information about the
             MPLS Label Distribution Protocol Entities which
             exist on this Label Switch Router (LSR)."
         ::= { ibMplsLdpEntityObjects 1 }

     ibMplsLdpEntityEntry OBJECT-TYPE
         SYNTAX      IbMplsLdpEntityEntry
         MAX-ACCESS  not-accessible
         STATUS      current
         DESCRIPTION
             "An entry in this table represents an LDP entity.
             An entry can be created by a network administrator
             or by an SNMP agent as instructed by LDP.

             An LPD Entity is uniquely indexed by its LPD
             Identifier."
         INDEX       {   ibMplsLdpLsrIncarnID, ibMplsLdpEntityIfIndex  }
         ::= { ibMplsLdpEntityTable 1 }

     IbMplsLdpEntityEntry ::= SEQUENCE {
         ibMplsLdpEntityID                            MplsLdpIdentifier,
         ibMplsLdpEntityLabelSpaceType                INTEGER,
         ibMplsLdpEntityDefVpi                        AtmVpIdentifier,
         ibMplsLdpEntityDefVci                        AtmVcIdentifier,
         ibMplsLdpEntityUnlabTrafVpi                  AtmVpIdentifier,
         ibMplsLdpEntityUnlabTrafVci                  AtmVcIdentifier,
         ibMplsLdpEntityMergeCapability               INTEGER,
         ibMplsLdpEntityVcDirectionality              INTEGER,
         ibMplsLdpEntityWellKnownDiscoveryPort        INTEGER,
         ibMplsLdpEntityMtu                           INTEGER,
         ibMplsLdpEntityKeepAliveHoldTimer            INTEGER,
         ibMplsLdpEntityFailedInitSessionThreshold    INTEGER,
         ibMplsLdpEntityLabelDistributionMethod       INTEGER,
         ibMplsLdpEntityLabelAllocationMethod         INTEGER,
         ibMplsLdpEntityHelloHoldTimer                INTEGER,
         ibMplsLdpEntityRowStatus                     RowStatus
     }

     ibMplsLdpEntityID OBJECT-TYPE
         SYNTAX      MplsLdpIdentifier
         MAX-ACCESS  accessible-for-notify
         STATUS      current
         DESCRIPTION
             "The LDP identifier which uniquely identifies
             the LDP Entity.  This is s six octet quantity
             which is used to identify an Label Switch Router
             (LSR) label space.

             The first four octets encode an IP address
             assigned to the LSR, and the last two octets
             identify a specific label space within the
             LSR."
         REFERENCE
             "LDP Specification, Section on LDP Identifiers."
         ::= { ibMplsLdpEntityEntry 1 }


     ibMplsLdpEntityLabelSpaceType OBJECT-TYPE
         SYNTAX      INTEGER {
                         unknown(1),
                         perInterface(2),
                         perPlatform(3)
                         }
         MAX-ACCESS  read-create
         STATUS      current
         DESCRIPTION
             "The type of label spaces associated with this
             LDP Entity.  The values are

                'unknown(1)'        The type of label space is
                                    not known.

                'perInterface(2)'   The type of label space is
                                    tied to an interface.
                'perPlatform(3)'    The type of label space is
                                    tied to the platform."
         REFERENCE
             "LDP Specification, Section on Label Spaces."
         ::= { ibMplsLdpEntityEntry 2 }

     ibMplsLdpEntityDefVpi OBJECT-TYPE
         SYNTAX      AtmVpIdentifier
         MAX-ACCESS  read-create
         STATUS      current
         DESCRIPTION
             "The Default VPI value used in the label for the default
             VPI."
         ::= { ibMplsLdpEntityEntry 3 }

     ibMplsLdpEntityDefVci OBJECT-TYPE
         SYNTAX      AtmVcIdentifier
         MAX-ACCESS  read-create
         STATUS      current
         DESCRIPTION
             "The Default VCI value used in the label for the default
             VCI."
         ::= { ibMplsLdpEntityEntry  4 }

     ibMplsLdpEntityUnlabTrafVpi OBJECT-TYPE
         SYNTAX      AtmVpIdentifier
         MAX-ACCESS  read-create
         STATUS      current
         DESCRIPTION
             "VPI value of the VCC supporting unlabeled traffic."
         DEFVAL  { 0 }
         ::= { ibMplsLdpEntityEntry 5 }

     ibMplsLdpEntityUnlabTrafVci OBJECT-TYPE
         SYNTAX      AtmVcIdentifier
         MAX-ACCESS  read-create
         STATUS      current
         DESCRIPTION
             "VCI value of the VCC supporting unlabeled traffic."
         DEFVAL  { 32 }
         ::= { ibMplsLdpEntityEntry 6 }

     ibMplsLdpEntityMergeCapability OBJECT-TYPE
         SYNTAX      INTEGER {
                         noMerge(0),
                         vpMerge(1),
                         vcMerge(2),
                         vpVcMerge(3)
                      }
         MAX-ACCESS  read-create
         STATUS      current
         DESCRIPTION
             "Sets the merge capability for this LDP entity.

              Current Release of MPLS does not provide support for
              any kind of Merge."
         REFERENCE
             "draft-ietf-mpls-ldp-04.txt, Section 3.5.3"
         ::= { ibMplsLdpEntityEntry 7 }

     ibMplsLdpEntityVcDirectionality OBJECT-TYPE
         SYNTAX      INTEGER {
                         bidirectional(1),
                         unidirectional(2)
                     }
         MAX-ACCESS  read-create
         STATUS      current
         DESCRIPTION
             "Sets the VC directionality for this LDP entity."
         REFERENCE
             "draft-ietf-mpls-ldp-04.txt, Section 3.5.3"
         ::= { ibMplsLdpEntityEntry 8 }

     ibMplsLdpEntityWellKnownDiscoveryPort OBJECT-TYPE
         SYNTAX      INTEGER
         MAX-ACCESS  read-create
         STATUS      current
         DESCRIPTION
             "The well known LDP Discovery Port."
         ::= { ibMplsLdpEntityEntry 9 }

     ibMplsLdpEntityMtu OBJECT-TYPE
         SYNTAX      INTEGER (0..65535)
         MAX-ACCESS  read-create
         STATUS      current
         DESCRIPTION
             "The maximum transmission unit (MTU) that was configured
             for this entity."
         ::= { ibMplsLdpEntityEntry 10 }

     ibMplsLdpEntityKeepAliveHoldTimer OBJECT-TYPE
         SYNTAX      INTEGER (1..65535)
         UNITS       "seconds"
         MAX-ACCESS  read-create
         STATUS      current
         DESCRIPTION
             "The two octet value which is the proposed keep alive hold
             timer for this LDP Entity."
         ::= { ibMplsLdpEntityEntry 11 }

     ibMplsLdpEntityFailedInitSessionThreshold OBJECT-TYPE
         SYNTAX      INTEGER
         MAX-ACCESS  read-create
         STATUS      current
         DESCRIPTION
             "When attempting to establish a session with a
             given Peer, the given LDP Entity should
             send out a notification when exceeding this threshold.
             A value of 0 (zero) for this object
             indicates that the threshold is infinity.
             In other words, a notification will not
             be sent if the value of this object is 0 (zero)."
         ::= { ibMplsLdpEntityEntry 12 }


     ibMplsLdpEntityLabelDistributionMethod OBJECT-TYPE
         SYNTAX      INTEGER {
                        downstreamOnDemand(1),
                        downstreamUnsolicited(2)
                     }
         MAX-ACCESS  read-create
         STATUS      current
         DESCRIPTION
             "For any given LDP session, the method of
             label distribution must be specified.

             Current release of MPLS does not provide support for
             'downstreamUnsolicited'."
         REFERENCE
             "draft-ietf-mpls-arch-04.txt [20]."
         ::= { ibMplsLdpEntityEntry 13 }

     ibMplsLdpEntityLabelAllocationMethod OBJECT-TYPE
         SYNTAX      INTEGER {
                        ordered(1),
                        independent(2)
                     }
         MAX-ACCESS  read-create
         STATUS      current
         DESCRIPTION
             "For any given LDP session, the method of
             label allocation must be specified. Label can be allocated
             in either ordered mode or in the independent mode."
         DEFVAL  { ordered }
         ::= { ibMplsLdpEntityEntry 14 }

     ibMplsLdpEntityHelloHoldTimer OBJECT-TYPE
         SYNTAX      INTEGER (1..65535)
         UNITS       "seconds"
         MAX-ACCESS  read-create
         STATUS      current
         DESCRIPTION
             "The two octet value which is the proposed hello hold
             timer for this LDP Entity."
         ::= { ibMplsLdpEntityEntry 15 }

     ibMplsLdpEntityRowStatus OBJECT-TYPE
         SYNTAX      RowStatus
         MAX-ACCESS  read-create
         STATUS      current
              DESCRIPTION
                  "An object that allows entries in this table to
                  be created and deleted using the
                  RowStatus convention."
         ::= { ibMplsLdpEntityEntry 16 }

     --
     -- The MPLS LDP Entity Interface Table
     --

     ibMplsLdpEntityIfTable OBJECT-TYPE
         SYNTAX      SEQUENCE OF IbMplsLdpEntityIfEntry
         MAX-ACCESS  not-accessible
         STATUS      current
         DESCRIPTION
             "This table contains information about the
             interfaces that are associated with an LDP Entity.
             There should be atleast one interface associated with
             each LDP Entity. If the LDP Entity supports 'per interface
             based label space' label type then, atmost one interface can be
             associated with the LDP entity. If the LDP Entity supports
             'per platform based label space' label type then, more than one
             interface can be associated with the LDP Entity."
         ::= { ibMplsLdpEntityObjects 2 }

     ibMplsLdpEntityIfEntry OBJECT-TYPE
         SYNTAX      IbMplsLdpEntityIfEntry
         MAX-ACCESS  not-accessible
         STATUS      current
         DESCRIPTION
             "An entry in this table represents an Interface that is
             associated with a LDP entity.

             An entry can be created by a network administrator
             or by an SNMP agent as instructed by LDP.

             An interface (row in this table) can be created/deleted only when
             the associted LDP Entity row status has the value notInService
             or notReady."
         INDEX       {   ibMplsLdpLsrIncarnID, ibMplsLdpEntityIfIndex }
         ::= { ibMplsLdpEntityIfTable 1 }

     IbMplsLdpEntityIfEntry ::= SEQUENCE {
         ibMplsLdpEntityIfIndex                       Unsigned32,
         ibMplsLdpEntityIfIpv4Address                 IpAddress,
         ibMplsLdpEntityIfRowStatus                   RowStatus
     }

     ibMplsLdpEntityIfIndex OBJECT-TYPE
         SYNTAX      Unsigned32 (1..4294967295)
         MAX-ACCESS  not-accessible
         STATUS      current
         DESCRIPTION
             "Identifier that uniquely identifies the Interface with
             respect to an LDP Entity.

             The ifIndex value corresponds to the IfIndex value of the
             MIB-II"
         ::= { ibMplsLdpEntityIfEntry 1 }

     ibMplsLdpEntityIfIpv4Address OBJECT-TYPE
        SYNTAX        IpAddress
        MAX-ACCESS    read-create
        STATUS        current
        DESCRIPTION
            "The IPv4 address associated with the interface."
        ::= { ibMplsLdpEntityIfEntry 2 }

     ibMplsLdpEntityIfRowStatus OBJECT-TYPE
         SYNTAX      RowStatus
         MAX-ACCESS  read-create
         STATUS      current
              DESCRIPTION
                  "An object that allows entries in this table to
                  be created and deleted using the
                  RowStatus convention."
         ::= { ibMplsLdpEntityIfEntry 3 }

     --
     -- The MPLS LDP Entity Configurable ATM Label Range Table
     --

     ibMplsLdpEntityConfAtmLabelRangeTable OBJECT-TYPE
         SYNTAX SEQUENCE OF IbMplsLdpEntityConfAtmLabelRangeEntry
         MAX-ACCESS not-accessible
         STATUS current
         DESCRIPTION
             "The MPLS LDP Entity Configurable ATM Label Range Table.
             The purpose of this table is to provide a mechanism
             for specifying a contiguous range of vpi's
             with a contiguous range of vci's, or a 'label range'
             for LDP Entities.

             LDP Entities which use ATM must have at least one
             entry in this table."
         ::= { ibMplsLdpEntityObjects 3 }

     ibMplsLdpEntityConfAtmLabelRangeEntry OBJECT-TYPE
         SYNTAX IbMplsLdpEntityConfAtmLabelRangeEntry
         MAX-ACCESS not-accessible
         STATUS current
         DESCRIPTION
             "A row in the LDP Entity Configurable ATM Label
             Range Table.  One entry in this table contains
             information on a single range of labels
             represented by the configured Upper and Lower
             Bounds VPI/VCI pairs.
             NOTE:  The ranges for a specific LDP Entity
             are UNIQUE and non-overlapping.  For example,
             for a specific LDP Entity index, there could
             be one entry having ConfLowerBound vpi/vci == 0/32, and
             ConfUpperBound vpi/vci == 0/100, and a second entry for this
             same interface with ConfLowerBound vpi/vci == 0/101 and
             ConfUpperBound vpi/vci == 0/200.  However, there could not be
             a third entry with ConfLowerBound vpi/vci == 0/200 and
             ConfUpperBound vpi/vci == 0/300 because this label range overlaps
             with the second entry (i.e. both entries now have 0/200).

             A row will not be created unless a unique and non-overlapping
             range is specified.  Thus, row creation implies a one-shot
             row creation of LDP EntityID and ConfLowerBound vpi/vci and
             ConfUpperBound vpi/vci.  At least one label range entry
             for a specific LDP Entity MUST include the default VPI/VCI
             values denoted in the LDP Entity Table."
         INDEX { ibMplsLdpLsrIncarnID, ibMplsLdpEntityIfIndex,
                 ibMplsLdpEntityConfAtmLabelRangeLowerBoundVPI,
                 ibMplsLdpEntityConfAtmLabelRangeLowerBoundVCI  }
         ::= { ibMplsLdpEntityConfAtmLabelRangeTable 1 }

     IbMplsLdpEntityConfAtmLabelRangeEntry ::= SEQUENCE {
         ibMplsLdpEntityConfAtmLabelRangeLowerBoundVPI  AtmVpIdentifier,
         ibMplsLdpEntityConfAtmLabelRangeLowerBoundVCI  AtmVcIdentifier,
         ibMplsLdpEntityConfAtmLabelRangeUpperBoundVPI  AtmVpIdentifier,
         ibMplsLdpEntityConfAtmLabelRangeUpperBoundVCI  AtmVcIdentifier,
         ibMplsLdpEntityConfAtmLabelRangeRowStatus      RowStatus
     }

     ibMplsLdpEntityConfAtmLabelRangeLowerBoundVPI OBJECT-TYPE
         SYNTAX AtmVpIdentifier
         MAX-ACCESS not-accessible
         STATUS current
         DESCRIPTION
             "The minimum VPI number configured for this range."
         ::= { ibMplsLdpEntityConfAtmLabelRangeEntry 1 }

     ibMplsLdpEntityConfAtmLabelRangeLowerBoundVCI OBJECT-TYPE
         SYNTAX AtmVcIdentifier
         MAX-ACCESS not-accessible
         STATUS current
         DESCRIPTION
             "The minimum VCI number configured for this range."
         ::= { ibMplsLdpEntityConfAtmLabelRangeEntry 2 }

     ibMplsLdpEntityConfAtmLabelRangeUpperBoundVPI OBJECT-TYPE
         SYNTAX AtmVpIdentifier
         MAX-ACCESS read-create
         STATUS current
         DESCRIPTION
             "The maximum VPI number configured for this range."
         ::= { ibMplsLdpEntityConfAtmLabelRangeEntry 3 }

     ibMplsLdpEntityConfAtmLabelRangeUpperBoundVCI OBJECT-TYPE
         SYNTAX AtmVcIdentifier
         MAX-ACCESS read-create
         STATUS current
         DESCRIPTION
             "The maximum VCI number configured for this range."
        ::= { ibMplsLdpEntityConfAtmLabelRangeEntry 4 }

     ibMplsLdpEntityConfAtmLabelRangeRowStatus OBJECT-TYPE
         SYNTAX RowStatus
         MAX-ACCESS read-create
         STATUS current
              DESCRIPTION
                  "An object that allows entries in this
                  table to be created and deleted using
                  the RowStatus convention."
         ::= { ibMplsLdpEntityConfAtmLabelRangeEntry 5 }


     --
     -- The MPLS LDP Entity Statistics Table
     --

     ibMplsLdpEntityStatsTable OBJECT-TYPE
         SYNTAX      SEQUENCE OF IbMplsLdpEntityStatsEntry
         MAX-ACCESS  not-accessible
         STATUS      current
         DESCRIPTION
             "This table is a read-only table which augments
             the MplsLdpConfEntityTable.  The purpose of this
             table is to keep statistical information about
             the LDP Entities on the LSR."
         ::= { ibMplsLdpEntityObjects 4 }

     ibMplsLdpEntityStatsEntry OBJECT-TYPE
         SYNTAX      IbMplsLdpEntityStatsEntry
         MAX-ACCESS  not-accessible
         STATUS      current
         DESCRIPTION
             "A row in this table contains statistical information
             about an LDP Entity."
         AUGMENTS       {   ibMplsLdpEntityEntry  }
         ::= { ibMplsLdpEntityStatsTable 1 }

     IbMplsLdpEntityStatsEntry ::= SEQUENCE {
         ibMplsLdpAttemptedSessions      Counter32
     }

     ibMplsLdpAttemptedSessions OBJECT-TYPE
         SYNTAX      Counter32
         MAX-ACCESS  read-only
         STATUS      current
         DESCRIPTION
             "A count of the total attempted sessions for
             this LDP Entity."
         ::= { ibMplsLdpEntityStatsEntry 1 }


     --
     -- The MPLS LDP Peer Table
     --


     ibMplsLdpPeerTable OBJECT-TYPE
         SYNTAX      SEQUENCE OF IbMplsLdpPeerEntry
         MAX-ACCESS  not-accessible
         STATUS      current
         DESCRIPTION
             "Information about LDP peers which have been discovered
             by the LDP Entities that are managed by this agent."
         ::= { ibMplsLdpPeerObjects 1 }

     ibMplsLdpPeerEntry OBJECT-TYPE
         SYNTAX      IbMplsLdpPeerEntry
         MAX-ACCESS  not-accessible
         STATUS      current
         DESCRIPTION
             "Information about a single Peer."
         INDEX       { ibMplsLdpLsrIncarnID, ibMplsLdpEntityIfIndex,
                       ibMplsLdpPeerIndex }
         ::= { ibMplsLdpPeerTable 1 }

     IbMplsLdpPeerEntry ::= SEQUENCE {
         ibMplsLdpPeerIndex                      Unsigned32,
         ibMplsLdpPeerID                         MplsLdpIdentifier,
         ibMplsLdpPeerInternetworkAddrType       AddressFamilyNumbers,
         ibMplsLdpPeerInternetworkAddr           MplsLdpGenAddr,
         ibMplsLdpPeerDefaultMtu                 INTEGER,
         ibMplsLdpPeerKeepAliveHoldTimer         INTEGER,
         ibMplsLdpPeerLabelDistributionMethod    INTEGER,
         ibMplsLdpPeerType                       INTEGER,
         ibMplsLdpPeerRowStatus                  RowStatus
     }

     ibMplsLdpPeerIndex OBJECT-TYPE
         SYNTAX      Unsigned32 (1..4294967295)
         MAX-ACCESS  not-accessible
         STATUS      current
         DESCRIPTION
             "An identifier for the LDP peer that is unique within the
              scope of this agent."
         ::= { ibMplsLdpPeerEntry 1 }

     ibMplsLdpPeerID OBJECT-TYPE
         SYNTAX      MplsLdpIdentifier
         MAX-ACCESS  read-create
         STATUS      current
         DESCRIPTION
             "The LDP identifier of this LDP Peer."
         ::= { ibMplsLdpPeerEntry 2 }

     ibMplsLdpPeerInternetworkAddrType OBJECT-TYPE
         SYNTAX      AddressFamilyNumbers
         MAX-ACCESS  read-create
         STATUS      current
         DESCRIPTION
             "The type of the internetwork layer address of this
             LDP peer. This object indicates how the value of
             ibMplsLdpPeerInternetworkAddr is to be interpreted."
         ::= { ibMplsLdpPeerEntry 3 }

     ibMplsLdpPeerInternetworkAddr OBJECT-TYPE
         SYNTAX      MplsLdpGenAddr
         MAX-ACCESS  read-create
         STATUS      current
         DESCRIPTION
             "The value of the internetwork layer address of this LDP peer."
         ::= { ibMplsLdpPeerEntry 4 }

     ibMplsLdpPeerDefaultMtu OBJECT-TYPE
         SYNTAX      INTEGER (0..65535)
         MAX-ACCESS  read-create
         STATUS      current
         DESCRIPTION
             "The default maximum transmission unit (MTU) of the
             LDP Peer."
         DEFVAL      { 9180 }
         ::= { ibMplsLdpPeerEntry 5 }

     ibMplsLdpPeerKeepAliveHoldTimer OBJECT-TYPE
         SYNTAX      INTEGER (1..65535)
         UNITS       "seconds"
         MAX-ACCESS  read-create
         STATUS      current
         DESCRIPTION
             "The two octet unsigned non zero INTEGER that indicates
             the number of seconds that this Peer proposes for the
             value of the KeepAlive Interval."
         ::= { ibMplsLdpPeerEntry 6 }

     ibMplsLdpPeerLabelDistributionMethod OBJECT-TYPE
         SYNTAX      INTEGER {
                        downstreamOnDemand(1),
                        downstreamUnsolicited(2)
                     }
         MAX-ACCESS  read-create
         STATUS      current
         DESCRIPTION
             "For any given LDP session, the method of
             label distribution must be specified."
         REFERENCE
             "draft-ietf-mpls-arch-05.txt [20]."
         ::= { ibMplsLdpPeerEntry 7 }

     ibMplsLdpPeerType OBJECT-TYPE
         SYNTAX      INTEGER {
                        local(1),
                        remote(2)
                     }
         MAX-ACCESS  read-create
         STATUS      current
         DESCRIPTION
             "Indicates whether a peer is a local peer or a remote peer"
         ::= { ibMplsLdpPeerEntry 8 }

     ibMplsLdpPeerRowStatus OBJECT-TYPE
         SYNTAX      RowStatus
         MAX-ACCESS  read-create
         STATUS      current
         DESCRIPTION
             "An object that allows entries in this table to be created
             and deleted using the RowStatus convention."
         ::= { ibMplsLdpPeerEntry 9 }

     --
     -- The MPLS LDP Peer Configurable ATM Label Range Table
     --

     ibMplsLdpPeerConfAtmLabelRangeTable OBJECT-TYPE
         SYNTAX SEQUENCE OF IbMplsLdpPeerConfAtmLabelRangeEntry
         MAX-ACCESS not-accessible
         STATUS current
         DESCRIPTION
             "The MPLS LDP Peer Configurable ATM Label Range Table.
             The purpose of this table is to provide a mechanism
             for specifying a contiguous range of vpi's with a contiguous
             range of vci's, or a 'label range' for LDP Peers.
             LDP Peers which use ATM must have at least one
             entry in this table."
         ::= { ibMplsLdpPeerObjects 2 }

     ibMplsLdpPeerConfAtmLabelRangeEntry OBJECT-TYPE
         SYNTAX IbMplsLdpPeerConfAtmLabelRangeEntry
         MAX-ACCESS not-accessible
         STATUS current
         DESCRIPTION
             "A row in the LDP Peer Configurable ATM Label Range Table.
             One entry in this table contains information
             on a single range of labels represented by
             the configured Upper and Lower Bounds VPI/VCI pairs.

             NOTE:  The ranges for a specific LDP Peer
             are UNIQUE and non-overlapping.  For example,
             for a specific LDP Peer index, there could
             be one entry having ConfLowerBound vpi/vci == 0/32, and
             ConfUpperBound vpi/vci == 0/100, and a second entry for this
             same interface with ConfLowerBound vpi/vci == 0/101 and
             ConfUpperBound vpi/vci == 0/200.  However, there could not be
             a third entry with ConfLowerBound vpi/vci == 0/200 and
             ConfUpperBound vpi/vci == 0/300 because this label range overlaps
             with the second entry (i.e. both entries now have 0/200).

             A row will not be created unless a unique and non-overlapping
             range is specified.  Thus, row creation implies a one-shot
             row creation of LDP PeerIndex and ConfLowerBound vpi/vci and
             ConfUpperBound vpi/vci.  At least one label range entry
             for a specific LDP Peer MUST include the default VPI/VCI
             values denoted in the LDP Peer Table."
         INDEX { ibMplsLdpLsrIncarnID, ibMplsLdpEntityIfIndex,
                 ibMplsLdpPeerIndex,
                 ibMplsLdpPeerConfAtmLabelRangeLowerBoundVPI,
                 ibMplsLdpPeerConfAtmLabelRangeLowerBoundVCI  }
         ::= { ibMplsLdpPeerConfAtmLabelRangeTable 1 }

     IbMplsLdpPeerConfAtmLabelRangeEntry ::= SEQUENCE {
         ibMplsLdpPeerConfAtmLabelRangeLowerBoundVPI      AtmVpIdentifier,
         ibMplsLdpPeerConfAtmLabelRangeLowerBoundVCI      AtmVcIdentifier,
         ibMplsLdpPeerConfAtmLabelRangeUpperBoundVPI      AtmVpIdentifier,
         ibMplsLdpPeerConfAtmLabelRangeUpperBoundVCI      AtmVcIdentifier
     }

     ibMplsLdpPeerConfAtmLabelRangeLowerBoundVPI OBJECT-TYPE
         SYNTAX AtmVpIdentifier
         MAX-ACCESS not-accessible
         STATUS current
         DESCRIPTION
             "The minimum VPI number configured for this range."
         ::= { ibMplsLdpPeerConfAtmLabelRangeEntry 1 }

     ibMplsLdpPeerConfAtmLabelRangeLowerBoundVCI OBJECT-TYPE
         SYNTAX AtmVcIdentifier
         MAX-ACCESS not-accessible
         STATUS current
         DESCRIPTION
             "The minimum VCI number configured for this range."
         ::= { ibMplsLdpPeerConfAtmLabelRangeEntry 2 }

     ibMplsLdpPeerConfAtmLabelRangeUpperBoundVPI OBJECT-TYPE
         SYNTAX AtmVpIdentifier
         MAX-ACCESS read-only
         STATUS current
         DESCRIPTION
             "The maximum VPI number configured for this range."
         ::= { ibMplsLdpPeerConfAtmLabelRangeEntry 3 }

     ibMplsLdpPeerConfAtmLabelRangeUpperBoundVCI OBJECT-TYPE
         SYNTAX AtmVcIdentifier
         MAX-ACCESS read-only
         STATUS current
         DESCRIPTION
             "The maximum VCI number configured for this range."
        ::= { ibMplsLdpPeerConfAtmLabelRangeEntry 4 }

     --
     -- The MPLS LDP Sessions Table
     --


     ibMplsLdpSessionTable OBJECT-TYPE
         SYNTAX      SEQUENCE OF IbMplsLdpSessionEntry
         MAX-ACCESS  not-accessible
         STATUS      current
         DESCRIPTION
             "A table of Sessions between the LDP Entities and
             LDP Peers."
         ::= { ibMplsLdpSessionObjects 1 }

     ibMplsLdpSessionEntry OBJECT-TYPE
         SYNTAX      IbMplsLdpSessionEntry
         MAX-ACCESS  not-accessible
         STATUS      current
         DESCRIPTION
             "An entry in this table represents information on a
             single session between an LDP Entity and LDP Peer."
         INDEX       { ibMplsLdpLsrIncarnID,
                       ibMplsLdpEntityIfIndex,
                       ibMplsLdpPeerIndex,
                       ibMplsLdpSessionIndex
                     }
         ::= { ibMplsLdpSessionTable 1 }

     IbMplsLdpSessionEntry ::= SEQUENCE {
         ibMplsLdpSessionIndex                          Unsigned32,
         ibMplsLdpSessionID                             MplsLdpIdentifier,
         ibMplsLdpSessionProtocolVersion                INTEGER,
         ibMplsLdpSessionKeepAliveHoldTimeRemaining     TimeInterval,
         ibMplsLdpSessionRole                           INTEGER,
         ibMplsLdpSessionState                          INTEGER,
         ibMplsLdpSessionAtmLabelRangeLowerBoundVPI     AtmVpIdentifier,
         ibMplsLdpSessionAtmLabelRangeLowerBoundVCI     AtmVcIdentifier,
         ibMplsLdpSessionAtmLabelRangeUpperBoundVPI     AtmVpIdentifier,
         ibMplsLdpSessionAtmLabelRangeUpperBoundVCI     AtmVcIdentifier
     }

     ibMplsLdpSessionIndex OBJECT-TYPE
         SYNTAX      Unsigned32 (1..4294967295)
         MAX-ACCESS  not-accessible
         STATUS      current
         DESCRIPTION
             "An unique identifier for this entry such that it
             identifies a specific LDP Session."
         ::= { ibMplsLdpSessionEntry 1 }

     ibMplsLdpSessionID OBJECT-TYPE
         SYNTAX      MplsLdpIdentifier
         MAX-ACCESS  read-only
         STATUS      current
         DESCRIPTION
             "The LDP Session identifier."
         ::= { ibMplsLdpSessionEntry 2 }

     ibMplsLdpSessionProtocolVersion OBJECT-TYPE
              SYNTAX      INTEGER(0..65535)
              MAX-ACCESS  read-only
              STATUS      current
              DESCRIPTION
                  "The version of the LDP Protocol which
                  this session is using."
              ::= { ibMplsLdpSessionEntry 3 }

     ibMplsLdpSessionKeepAliveHoldTimeRemaining OBJECT-TYPE
         SYNTAX      TimeInterval
         MAX-ACCESS  read-only
         STATUS      current
         DESCRIPTION
             "The keep alive hold time remaining for this session."
         ::= { ibMplsLdpSessionEntry 4 }

     ibMplsLdpSessionRole OBJECT-TYPE
         SYNTAX      INTEGER {
                        active(1),
                        passive(2)
                     }
         MAX-ACCESS  read-only
         STATUS      current
         DESCRIPTION
             "An indication of whether the LDP Entity associated with
             this session is acting in an 'active' role or
             a 'passive' role."
         ::= { ibMplsLdpSessionEntry 5 }

     ibMplsLdpSessionState OBJECT-TYPE
         SYNTAX      INTEGER {
                        nonexistent(1),
                        initialized(2),
                        openrec(3),
                        opensent(4),
                        operational(5)
                     }
         MAX-ACCESS  read-only
         STATUS      current
         DESCRIPTION
             "The current state of the session, all of the
             states 1 - 5 are based on the state machine for
             session negotiation behavior."
         ::= { ibMplsLdpSessionEntry 6 }

     ibMplsLdpSessionAtmLabelRangeLowerBoundVPI OBJECT-TYPE
         SYNTAX AtmVpIdentifier
         MAX-ACCESS read-only
         STATUS current
         DESCRIPTION
             "The minimum VPI number for this range."
         ::= { ibMplsLdpSessionEntry 7 }

     ibMplsLdpSessionAtmLabelRangeLowerBoundVCI OBJECT-TYPE
         SYNTAX AtmVcIdentifier
         MAX-ACCESS read-only
         STATUS current
         DESCRIPTION
             "The minimum VCI number for this range."
         ::= { ibMplsLdpSessionEntry 8 }

     ibMplsLdpSessionAtmLabelRangeUpperBoundVPI OBJECT-TYPE
         SYNTAX AtmVpIdentifier
         MAX-ACCESS read-only
         STATUS current
         DESCRIPTION
             "The maximum VPI number for this range."
         ::= { ibMplsLdpSessionEntry 9 }

     ibMplsLdpSessionAtmLabelRangeUpperBoundVCI OBJECT-TYPE
         SYNTAX AtmVcIdentifier
         MAX-ACCESS read-only
         STATUS current
         DESCRIPTION
             "The maximum VCI number for this range."
         ::= { ibMplsLdpSessionEntry 10 }



     --
     -- The MPLS LDP Hello Adjacency Table
     --


     ibMplsLdpHelloAdjacencyTable OBJECT-TYPE
         SYNTAX      SEQUENCE OF IbMplsLdpHelloAdjacencyEntry
         MAX-ACCESS  not-accessible
         STATUS      current
         DESCRIPTION
             "A table of Hello Adjacencies for Sessions."
         ::= { ibMplsLdpHelloAdjacencyObjects 1 }

     ibMplsLdpHelloAdjacencyEntry OBJECT-TYPE
         SYNTAX      IbMplsLdpHelloAdjacencyEntry
         MAX-ACCESS  not-accessible
         STATUS      current
         DESCRIPTION
             "Each row represents a single LDP Hello Adjacency.
             An LDP Session can have one or more Hello adjacencies."
         INDEX       { ibMplsLdpLsrIncarnID,
                       ibMplsLdpEntityIfIndex,
                       ibMplsLdpPeerIndex,
                       ibMplsLdpSessionIndex,
                       ibMplsLdpHelloAdjacencyIndex }
         ::= { ibMplsLdpHelloAdjacencyTable 1 }

     IbMplsLdpHelloAdjacencyEntry ::= SEQUENCE {
         ibMplsLdpHelloAdjacencyIndex                  Unsigned32,
         ibMplsLdpHelloAdjacencyHoldTimeRemaining      TimeInterval
     }

     ibMplsLdpHelloAdjacencyIndex OBJECT-TYPE
         SYNTAX      Unsigned32 (1..4294967295)
         MAX-ACCESS  not-accessible
         STATUS      current
         DESCRIPTION
             "An identifier for the adjacency."
         ::= { ibMplsLdpHelloAdjacencyEntry 1 }

     ibMplsLdpHelloAdjacencyHoldTimeRemaining OBJECT-TYPE
         SYNTAX      TimeInterval
         MAX-ACCESS  read-only
         STATUS      current
         DESCRIPTION
             "The time remaining for this Hello Adjacency."
         ::= { ibMplsLdpHelloAdjacencyEntry 2 }

     --
     -- FSMPLS- CRLSP Table
     --

     ibMplsLdpCrlspTnlTable OBJECT-TYPE
        SYNTAX        SEQUENCE OF IbMplsLdpCrlspTnlEntry
        MAX-ACCESS    not-accessible
        STATUS        current
        DESCRIPTION
            "The ibMplsLdpCrlspTnlTable allows new CRLSP MPLS tunnels
             to be created. The ER hops associated with a CRLSP tunnel
             are to be configured using the ibMplsLdpCrlspErHopTable."
        ::= { ibMplsLdpCrlspTnlObjects 1 }

     ibMplsLdpCrlspTnlEntry OBJECT-TYPE
        SYNTAX        IbMplsLdpCrlspTnlEntry
        MAX-ACCESS    not-accessible
        STATUS        current
        DESCRIPTION
            "An  entry  in this table represents an CRLSP MPLS  tunnel.
             An  entry  can be created by a network administrator."
        INDEX  {  ibMplsLdpLsrIncarnID,  ibMplsLdpCrlspTnlIndex  }
           ::= { ibMplsLdpCrlspTnlTable 1 }

     IbMplsLdpCrlspTnlEntry ::= SEQUENCE {
           ibMplsLdpCrlspTnlIndex                 MplsTunnelIndex,
           ibMplsLdpCrlspTnlName                  DisplayString,
           ibMplsLdpCrlspTnlDirection             INTEGER,
           ibMplsLdpCrlspTnlSignallingProto       INTEGER,
           ibMplsLdpCrlspTnlSetupPrio             INTEGER,
           ibMplsLdpCrlspTnlHoldingPrio           INTEGER,
           ibMplsLdpCrlspTnlPeakDataRate          BitRate,
           ibMplsLdpCrlspTnlPeakBurstSize         BurstSize,
           ibMplsLdpCrlspTnlCommittedDataRate     BitRate,
           ibMplsLdpCrlspTnlCommittedBurstSize    BurstSize,
           ibMplsLdpCrlspTnlExcessBurstSize       BurstSize,
           ibMplsLdpCrlspTnlIsPinned              TruthValue,
           ibMplsLdpCrlspTnlFrequency             INTEGER,
           ibMplsLdpCrlspTnlWeight                INTEGER,
           ibMplsLdpCrlspTnlRowStatus             RowStatus
        }

     ibMplsLdpCrlspTnlIndex OBJECT-TYPE
        SYNTAX        MplsTunnelIndex
        MAX-ACCESS    accessible-for-notify
        STATUS        current
        DESCRIPTION
            "Uniquely identifies this row."
        ::= { ibMplsLdpCrlspTnlEntry 1 }

     ibMplsLdpCrlspTnlName OBJECT-TYPE
        SYNTAX        DisplayString
        MAX-ACCESS    read-create
        STATUS        current
        DESCRIPTION
            "The 'canonical' name assigned to the tunnel that can
             be  used  to refer to it on the 'console' port."
        ::= { ibMplsLdpCrlspTnlEntry 2 }


     ibMplsLdpCrlspTnlDirection OBJECT-TYPE
        SYNTAX        INTEGER { in(1), out(2), inOut(3) }
        MAX-ACCESS    read-create
        STATUS        current
        DESCRIPTION
            "Whether   this  tunnel  is  unidirectional-incoming,
             unidirectional-outgoing, or bidirectional."
        ::= { ibMplsLdpCrlspTnlEntry 3 }


     ibMplsLdpCrlspTnlSignallingProto OBJECT-TYPE
        SYNTAX        INTEGER { none(1), ldp(2), rsvp(3) }
        MAX-ACCESS    read-create
        STATUS        current
        DESCRIPTION
            "The  signaling protocol, if any, that  set  up  this
             tunnel."
        DEFVAL        { none }
        ::= { ibMplsLdpCrlspTnlEntry 4 }

     ibMplsLdpCrlspTnlSetupPrio OBJECT-TYPE
        SYNTAX        INTEGER (0..7)
        MAX-ACCESS    read-create
        STATUS        current
        DESCRIPTION
            "The setup priority of this tunnel."
        REFERENCE
            "Extensions to RSVP for LSP Tunnels, Awduche  et  al,
             Internet  Draft <draft-mpls-rsvp-lsp-tunnel-02.txt>,
             March  1999., Constraint-Based LSP Setup using  LDP,
             Jamoussi,  Internet  Draft  <draft-ietf-mpls-cr-ldp-
             01.txt>, Feb. 1999."
        ::= { ibMplsLdpCrlspTnlEntry 5 }

     ibMplsLdpCrlspTnlHoldingPrio OBJECT-TYPE
        SYNTAX        INTEGER (0..7)
        MAX-ACCESS    read-create
        STATUS        current
        DESCRIPTION
            "The holding priority for this tunnel."
        REFERENCE
            "  Extensions to RSVP for LSP Tunnels, Awduche et al,
             Internet  Draft <draft-mpls-rsvp-lsp-tunnel-02.txt>,
             March  1999., Constraint-Based LSP Setup using  LDP,
             Jamoussi,  Internet  Draft  <draft-ietf-mpls-cr-ldp-
             01.txt>, Feb. 1999."
        ::= { ibMplsLdpCrlspTnlEntry 6 }

     ibMplsLdpCrlspTnlPeakDataRate OBJECT-TYPE
        SYNTAX        BitRate
        UNITS         "bits per second"
        MAX-ACCESS    read-create
        STATUS        current
        DESCRIPTION
            "The peak rate - the maximum rate at which traffic will be sent on the
             CRLSP."
        REFERENCE
            "Section 4.3.1.2, Constraint-Based LSP Setup using LDP, Jamoussi, et.
             al, <draft-ietf-mpls-crldp-02.txt>, August 1999."
        DEFVAL        { 0 }
        ::= { ibMplsLdpCrlspTnlEntry 7 }

     ibMplsLdpCrlspTnlPeakBurstSize OBJECT-TYPE
        SYNTAX        BurstSize
        UNITS         "bytes"
        MAX-ACCESS    read-create
        STATUS        current
        DESCRIPTION
            "The peak burst size - the maximum burst size of the traffic that can
             occur in the established CRLSP."
        REFERENCE
            "Section 4.3, Constraint-Based LSP Setup using LDP, Jamoussi, et.
             al, <draft-ietf-mpls-crldp-02.txt>, August 1999."
        DEFVAL        { 0 }
        ::= { ibMplsLdpCrlspTnlEntry 8 }

     ibMplsLdpCrlspTnlCommittedDataRate OBJECT-TYPE
        SYNTAX        BitRate
        UNITS         "bits per second"
        MAX-ACCESS    read-create
        STATUS        current
        DESCRIPTION
            "The committed rate - the committed rate at which traffic will be sent on the
             CRLSP."
        REFERENCE
            "Section 4.3.1.3, Constraint-Based LSP Setup using LDP, Jamoussi, et.
             al, <draft-ietf-mpls-crldp-02.txt>, August 1999."
        DEFVAL        { 0 }
        ::= { ibMplsLdpCrlspTnlEntry 9 }

     ibMplsLdpCrlspTnlCommittedBurstSize OBJECT-TYPE
        SYNTAX        BurstSize
        UNITS         "bytes"
        MAX-ACCESS    read-create
        STATUS        current
        DESCRIPTION
            "The committed burst size - the committed burst size of the traffic
             that will be handled in the established CRLSP."
        REFERENCE
            "Section 4.3, Constraint-Based LSP Setup using LDP, Jamoussi, et.
             al, <draft-ietf-mpls-crldp-02.txt>, August 1999."
        DEFVAL        { 0 }
        ::= { ibMplsLdpCrlspTnlEntry 10 }

     ibMplsLdpCrlspTnlExcessBurstSize OBJECT-TYPE
        SYNTAX        BurstSize
        UNITS         "bytes"
        MAX-ACCESS    read-create
        STATUS        current
        DESCRIPTION
            "The Excess burst size - the excess burst size limit to be used
             for traffic conditioning at the ingress of the CRLSP."
        REFERENCE
            "Section 4.3.1.4, Constraint-Based LSP Setup using LDP, Jamoussi, et.
             al, <draft-ietf-mpls-crldp-02.txt>, August 1999."
        DEFVAL        { 0 }
        ::= { ibMplsLdpCrlspTnlEntry 11 }

     ibMplsLdpCrlspTnlIsPinned OBJECT-TYPE
        SYNTAX        TruthValue
        MAX-ACCESS    read-create
        STATUS        current
        DESCRIPTION
            "Indicates  whether  the loose-routed  hops  of  this
             tunnel are to be pinned."
        DEFVAL        { false }
        ::= { ibMplsLdpCrlspTnlEntry 12 }

     ibMplsLdpCrlspTnlFrequency OBJECT-TYPE
        SYNTAX        INTEGER (0..2)
        MAX-ACCESS    read-create
        STATUS        current
        DESCRIPTION
            "Indicates the frequency of usage of the established CRLSP."
        REFERENCE
            "Section 4.3.1.1, Constraint-Based LSP Setup using LDP, Jamoussi, et.
             al, <draft-ietf-mpls-crldp-02.txt>, August 1999."
        ::= { ibMplsLdpCrlspTnlEntry 13 }

     ibMplsLdpCrlspTnlWeight OBJECT-TYPE
        SYNTAX        INTEGER (0..255)
        MAX-ACCESS    read-create
        STATUS        current
        DESCRIPTION
            "Indicates the weight that is the established CRLSP."
        REFERENCE
            "Section 4.3, Constraint-Based LSP Setup using LDP, Jamoussi, et.
             al, <draft-ietf-mpls-crldp-02.txt>, August 1999."
        ::= { ibMplsLdpCrlspTnlEntry 14 }

     ibMplsLdpCrlspTnlRowStatus OBJECT-TYPE
        SYNTAX        RowStatus
        MAX-ACCESS    read-create
        STATUS        current
        DESCRIPTION
            "For controlling the state of this row.
             The status can be set to 'active' only when atleast one ERHOP
             is created in the ibMplsLdpErHopTable, associated with this
             tunnel."
        ::= { ibMplsLdpCrlspTnlEntry 15 }

    --
    -- Er-Hop Table
    --

     ibMplsLdpCrlspErHopTable  OBJECT-TYPE
        SYNTAX        SEQUENCE OF IbMplsLdpCrlspErHopEntry
        MAX-ACCESS    not-accessible
        STATUS        current
        DESCRIPTION
            "The ibMplsLdpCrlspErHopTable is used to indicate the hops,
             strict  or  loose,  for an MPLS  CRLSP tunnel  defined  in
             ibMplsLdpCrlspTnlTable.

             There must be atleast one entry in this table for each CRLSP tunnel
             that is supported in the ibMplsLdpCrlspTnlTable.

             The first row in the table  is  the
             first hop after the origination point of the tunnel."
        ::= { ibMplsLdpCrlspTnlObjects 2 }

     ibMplsLdpCrlspErHopEntry  OBJECT-TYPE
        SYNTAX        IbMplsLdpCrlspErHopEntry
        MAX-ACCESS    not-accessible
        STATUS        current
        DESCRIPTION
            "An  entry in this table represents a tunnel hop.  An
             entry  is  created  by a network  administrator  for
             signalled ERLSP set up by LDP or RSVP."
        INDEX  {  ibMplsLdpLsrIncarnID,
                  ibMplsLdpCrlspTnlIndex, ibMplsLdpCrlspErHopIndex  }
           ::= { ibMplsLdpCrlspErHopTable 1 }

     IbMplsLdpCrlspErHopEntry ::= SEQUENCE {
           ibMplsLdpCrlspErHopIndex              INTEGER,
           ibMplsLdpCrlspErHopAddrType           INTEGER,
           ibMplsLdpCrlspErHopIpv4Addr           IpAddress,
           ibMplsLdpCrlspErHopIpv4PrefixLen      INTEGER,
           ibMplsLdpCrlspErHopStrictOrLoose      INTEGER,
           ibMplsLdpCrlspErHopRowStatus          RowStatus
        }

     ibMplsLdpCrlspErHopIndex OBJECT-TYPE
        SYNTAX        INTEGER
        MAX-ACCESS    not-accessible
        STATUS        current
        DESCRIPTION
            "Secondary  index  into  this table  identifying  the
             particular hop."
        ::= { ibMplsLdpCrlspErHopEntry 1 }

     ibMplsLdpCrlspErHopAddrType OBJECT-TYPE
        SYNTAX        INTEGER { ipV4(1) }
        MAX-ACCESS    read-create
        STATUS        current
        DESCRIPTION
            "Address type of this hop."
        DEFVAL        { ipV4 }
        ::= { ibMplsLdpCrlspErHopEntry 2 }

     ibMplsLdpCrlspErHopIpv4Addr OBJECT-TYPE
        SYNTAX        IpAddress
        MAX-ACCESS    read-create
        STATUS        current
        DESCRIPTION
            "If ibMplsLdpCrlspErHopAddrType is ipV4(1), IPv4 address of
             this  hop.  This object is not significant otherwise
             and should return a value of 0."
        ::= { ibMplsLdpCrlspErHopEntry 3 }

     ibMplsLdpCrlspErHopIpv4PrefixLen OBJECT-TYPE
        SYNTAX        INTEGER (1..32)
        MAX-ACCESS    read-create
        STATUS        current
        DESCRIPTION
            "If  ibMplsLdpCrlspErHopAddrType is ipV4(1), prefix  length
             for  this  hop's IPv4 address.  This object  is  not
             significant otherwise and should return a  value  of
             0."
        ::= { ibMplsLdpCrlspErHopEntry 4 }

     ibMplsLdpCrlspErHopStrictOrLoose OBJECT-TYPE
        SYNTAX        INTEGER { strict(1), loose(2) }
        MAX-ACCESS    read-create
        STATUS        current
        DESCRIPTION
            "Whether this is a strict or loose hop."
        ::= { ibMplsLdpCrlspErHopEntry 5 }

     ibMplsLdpCrlspErHopRowStatus OBJECT-TYPE
        SYNTAX        RowStatus
        MAX-ACCESS    read-create
        STATUS        current
        DESCRIPTION
            "For creating, modifying and deleting this row."
        ::= { ibMplsLdpCrlspErHopEntry 6 }

     ---
     --- ibMplsLdpScalarGroup
     ---

     ibMplsLdpCfgInfo    OBJECT-TYPE
      SYNTAX      OCTET STRING (SIZE (1..127))
      MAX-ACCESS  accessible-for-notify
      STATUS      current
      DESCRIPTION
          "The information of MPLS(Multiprotocol Label Switching)
           LDP(Label Distribution Protocol) configuration."
      ::= { ibMplsLdpScalarGroup 1 }

     ibMplsLdpSessInfo    OBJECT-TYPE
      SYNTAX      OCTET STRING (SIZE (1..127))
      MAX-ACCESS  accessible-for-notify
      STATUS      current
      DESCRIPTION
          "The information of MPLS(Multiprotocol Label Switching)
          LDP(Label Distribution Protocol) session."
      ::= { ibMplsLdpScalarGroup 2 }


     ---
     --- Notifications
     ---

     ibMplsLdpNotificationPrefix   OBJECT IDENTIFIER ::=
                                      { ibMplsLdpNotifications 0 }

     ibMplsLdpFailedInitSessionThresholdExceeded NOTIFICATION-TYPE
     OBJECTS     {
      ibMplsLdpLsrIncarnID, ibMplsLdpEntityID,
                        ibMplsLdpEntityFailedInitSessionThreshold
                 }
     STATUS      current
   DESCRIPTION   "This notification is generated whenever the value
             of ibMplsLdpEntityFailedInitSessionThreshold is
             exceeded."
   ::= { ibMplsLdpNotificationPrefix 1 }

--          OBJECTS     { ibMplsLdpLsrIncarnID, ibMplsLdpEntityID,
--                        ibMplsLdpEntityFailedInitSessionThreshold
--                      }
--          STATUS      current
--          DESCRIPTION
--             "This notification is generated whenever the value
--             of ibMplsLdpEntityFailedInitSessionThreshold is
--             exceeded."
--          ::= { ibMplsLdpNotificationPrefix 1 }

     ibMplsLdpCrlspTunnelUp NOTIFICATION-TYPE
     OBJECTS     {
      ibMplsLdpLsrIncarnID, ibMplsLdpEntityID,
                  ibMplsLdpCrlspTnlIndex
                 }
        STATUS      current
        DESCRIPTION
            "This notification is generated by the Ingress LSR of the CRLSP tunnel
             on the receipt of Label mapping message from the downstream LSR for
             the LAbel request sent for the CRLSP tunnel."
        ::= { ibMplsLdpNotificationPrefix 2 }

     ibMplsLdpCrlspTunnelDown NOTIFICATION-TYPE
     OBJECTS     {
    ibMplsLdpLsrIncarnID, ibMplsLdpEntityID,
                  ibMplsLdpCrlspTnlIndex }
        STATUS      current
        DESCRIPTION
            "This notification is generated when a CRLSP Row status is modified
             to destroy the CRLSP tunnel.  - due to pre-emption etc.,"
        ::= { ibMplsLdpNotificationPrefix 3 }

     ibMplsLdpCrlspTunnelSetupFailure NOTIFICATION-TYPE
     OBJECTS     { ibMplsLdpLsrIncarnID, ibMplsLdpEntityID,
                  ibMplsLdpCrlspTnlIndex }
        STATUS      current
        DESCRIPTION
            "This notification is generated by the Ingress LSR of the CRLSP tunnel
             on the receipt of Nak message from the downstream LSR for
             the Label request sent for the CRLSP tunnel. This can occur due to
             improper ER hop values being set, or Traffic resources not available
             etc.,"
        ::=  { ibMplsLdpNotificationPrefix 4 }


     ibMplsLdpIncarnUpEventFailure  NOTIFICATION-TYPE
     OBJECTS     { ibMplsLdpLsrIncarnID}
        STATUS      current
        DESCRIPTION
            "This notification is generated by LDP to notify
             the Incarnation UP Event failure"
        ::= { ibMplsLdpNotificationPrefix 11 }

     ibMplsLdpIncarnDownEventFailure NOTIFICATION-TYPE
     OBJECTS     { ibMplsLdpLsrIncarnID }
        STATUS      current
        DESCRIPTION
            "This notification is generated by LDP to notify
             the Incarnation DOWN Event failure"
        ::= { ibMplsLdpNotificationPrefix 12 }

     ibMplsLdpEntityUpEventFailure NOTIFICATION-TYPE
     OBJECTS     { ibMplsLdpLsrIncarnID, ibMplsLdpEntityID}
        STATUS      current
        DESCRIPTION
            "This notification is generated by LDP to notify
             the ENTITY UP Event failure"
        ::= { ibMplsLdpNotificationPrefix 13 }


     ibMplsLdpEntityDownEventFailure NOTIFICATION-TYPE
     OBJECTS     { ibMplsLdpLsrIncarnID, ibMplsLdpEntityID }
        STATUS      current
        DESCRIPTION
            "This notification is generated by LDP to notify
             the ENTITY  DOWN Event failure"
        ::= { ibMplsLdpNotificationPrefix 14 }
        ibMplsLdpSessionUpEventFailure NOTIFICATION-TYPE
     OBJECTS     { ibMplsLdpSessionID, ibMplsLdpSessionState }
        STATUS      current
        DESCRIPTION
            "Generation of this trap occurs when the
            value of 'ibMplsLdpSessionState' enters
             the 'operational(5)' state."
        ::= { ibMplsLdpNotificationPrefix 15 }

     ibMplsLdpSessionDownEventFailure NOTIFICATION-TYPE
     OBJECTS     { ibMplsLdpSessionID, ibMplsLdpSessionState }
        STATUS      current
        DESCRIPTION
            "Generation of this trap occurs when the
            value of 'ibMplsLdpSessionState' leaves
            the 'operational(5)' state."
        ::= { ibMplsLdpNotificationPrefix 16 }

     ibMplsLdpMulLinkCfgInc NOTIFICATION-TYPE
     OBJECTS     { ibMplsLdpCfgInfo, ibMplsLdpSessInfo }
        STATUS      current
        DESCRIPTION
            "This notification is generated when the
            multi-link configurations were inconsistent"
        ::= { ibMplsLdpNotificationPrefix 17 }

     ibMplsLdpMulLinkCfgIncClear NOTIFICATION-TYPE
     OBJECTS     { ibMplsLdpCfgInfo, ibMplsLdpSessInfo }
        STATUS      current
        DESCRIPTION
            "This notification is generated when the
            multi-link configurations changed to consistent"
        ::= { ibMplsLdpNotificationPrefix 18 }

-- End of notifications.
END
