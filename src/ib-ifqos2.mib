-- ============================================================================
-- Copyright (C) 2023 Intelbras S.A. All rights reserved.
--
-- Description: Interface QoS Management Information Base.
-- Reference: RFC 3291
-- Version: 2.0
-- History:
-- V1.0 created by tangshun.
-- V1.1 2006/02/24 modified by changhuifeng
--  Add  object ibIfQoSWFQType in ibIfQoSWFQTable.
--  Add ibIfQoSL3PlusObjects and ibIfQoSPortBindingTable.
--  Modify property of ibIfQoSPortWredPreID to "not-accessible".
--  Add the  enumeration ipall to ibIfQoSPQClassRuleType in ibIfQoSPQClassRuleTable.
--  Modify some text errors in this file.
-- V1.2 2006/03/29 modified by xialei
--  Modify the ipv4acl value in description of ibIfQoSPQClassRuleValue and ibIfQoSCQClassRuleValue
--  Add the enumeration mpls to ibIfQoSPQClassRuleType in ibIfQoSPQClassRuleTable.
--  Add the enumeration ipall, mpls to ibIfQoSCQClassRuleType in ibIfQoSCQClassRuleTable.
-- V1.3 2006/05/24 add by cuichuanjin
--  Add ibIfQoSCarlTable
-- V1.4 2007/11/12 modified by mouxuanli
--  Modify the description of the object ibIfQoSPassPackets.
--  Add 18 objects in ibIfQoSHardwareQueueRunInfoTable.
--  Add ibIfQoSHQueueTcpRunInfoTable.
-- V1.5 2008/9/25 modified by yueting
--  Add ibQoSIfTraStaConfigInfoTable.
--  Add ibQoSIfTraStaRunInfoTable.
-- V1.6 2011/12/14 modified by mouxuanli
--  Add the enumeration byteCountWrr, byteCountWfq to ibIfQoSQSMode in ibIfQoSQSModeTable.
--  Add ibIfQoSQSMinBandwidth in ibIfQoSQSWeightTable.
--  Add ibIfQoSLRPir in ibIfQoSLRConfigTable.
-- V1.7 2012/04/28 modified by mouxuanli
--  Add the enumeration ipPrecedence, dot11e, auto to ibIfQoSPortPriorityTrustTrustType.
--  Add the enumeration overcast to ibIfQoSPortPriorityTrustOvercastType.
--  Add ibIfQoSPrePriMapTable.
-- V1.8 2013/10/25 modified by mouxuanli
--  Add the enumeration gmb to ibIfQoSQSMode.
--  Add ibIfQoSQSMinBandwidthPercent in ibIfQoSQSWeightTable.
--  Add ibIfQoSLRUnit in ibIfQoSLRConfigTable.
--  Add ibQoSGlobalPriorityObject.
-- V1.9 2014/11/25 modified by zhaixiaoxiang & xunzhi
--  Modify the name of CarAction to IbIfCarAction.
--  Add the enumeration remarkLocalPreContinue, remarkLocalPrePass, remarkDropPreContinue
--  and remarkDropPrePass to IbIfCarAction and modify the related descriptions.
--  Add the enumeration hierarchy to ibIfQoSAggregativeCarType.
--  Add ibIfQoSTricolorCarUnitType in ibIfQoSTricolorCarConfigTable.
--  Add ibIfQoSGTSPir and ibIfQoSGTSUnitType in ibIfQoSGTSConfigTable.
--  Add ibIfQoSProcessingStatus node.
-- V1.10 2016/10/25 modified by gaomengfei
--  Add the enumeration group3 and group4 to ibIfQoSQueueGroupType
--  2017/05/20 modified by gaomengfei
--  Add the ibIfQoSQueueName in ibIfQoSHardwareQueueRunInfoEntry
--  Add ibIfQoSHardwareQueueTotalRunInfoTable
--  2018/02/28 modified by hulifang
--  Add ibIfQoSCoppFlowStatTable
-- V1.11 2018/12/12 modified by meixixue
--  2018/12/12 modified by meixixue
--  Add the ibIfQoSDropPPS and ibIfQoSDropBPS in ibIfQoSHardwareQueueRunInfoEntry
-- V1.12 2019/06/20 modified by wangqian
--  2019/06/20 modified by wangqian
--  Add the ibIfQoSPeakPassPPS and ibIfQoSPeakPassBPS in ibIfQoSHardwareQueueRunInfoEntry
-- V1.13 2021/10/06 modified by gaomengfei
--  Add ibIfQoS8QueueResouceOverAlarm
--  Add ibIfQoS8QueueResouceOverRecover
--  Add ibIfQoS8QueueResoucePreAlarm
--  Add ibIfQoS8QueueResoucePreRecover
--  Add ibIfQoSBufferOverAlarm
--  Add ibIfQoSBufferOverRecover
--  Add ibIfQoSModeChannelOverPortShapAlarm
--  Add ibIfQoSModeChannelOverPortShapRecover
--  Add ibIfQoSExclusiveBandApplyFailAlarm
--  Add ibIfQoSExclusiveBandApplyFailRecover
--  Add ibIfQoSExclusiveBandOverAlarm
--  Add ibIfQoSExclusiveBandOverRecover
-- V1.14 2022/06/09 modified by lizhaocheng
--  Add ibIfQoSLRDiscardAlarm
--  Add ibIfQoSLRDiscardAlarmRecover
--  Add ibIfQoSCarDiscardAlarm
--  Add ibIfQoSCarDiscardAlarmRecover
-- V1.15 2022/08/05 modified by lizhaocheng
--  Add ibIfQoSCoppDropPktAlarm
--  Add ibIfQoSCoppDropPktAlarmRecover
--  Add ibIfQoSQueExcpAlarm
--  Add ibIfQoSQueExcpAlarmRecover
--  Add ibIfQoSBoardL3AclResLack
--  Add ibIfQoSAclResAlarm
--  Add ibIfQoSAclResAlarmRecover
--  Add ibIfQoSAclMemFullAlarm
--  Add ibIfQoSAclMemFullAlarmRecover
-- V2.0 2022/11/18 modified by zhangxiaowei
--  Add ibIfQoSBufferAlarm
--  Add ibIfQoSBufferAlarmRecover
--  Add ibIfQoSQueBufferOverrunAlarm
--  Add ibIfQoSQueBufferOverrunRecover
--  Add ibIfQoSFCoEPriorityAlarm
--  Add ibIfQoSFCoEPriorityRecover
--  Add ibIfQoSRcyPortPktsDropAlarm
--  Add ibIfQoSRcyPortPktsDropRecover
--  Add ibIfQoSStormSuppressAlarm
--  Add ibIfQoSStormSuppressRecover
--  Add ibIfQoSUniPktsDiscardAlarm
--  Add ibIfQoSUniPktsDiscardRecover
--  Add ibIfQoSIngressDiscardAlarm
--  Add ibIfQoSIngressDiscardRecover
-- ============================================================================
IB-IFQOS2-MIB DEFINITIONS ::= BEGIN

        IMPORTS
            ibCommon
                FROM IB-OID-MIB
            OBJECT-TYPE, MODULE-IDENTITY, NOTIFICATION-TYPE, Integer32, Counter64, Unsigned32, IpAddress
                FROM SNMPv2-SMI
            ifIndex
                FROM IF-MIB
            InetAddressIPv6, InetAddressPrefixLength
                FROM INET-ADDRESS-MIB
            RowStatus, TruthValue, TEXTUAL-CONVENTION
                FROM SNMPv2-TC;
--
-- Nodes definitions
--

        ibIfQos2 MODULE-IDENTITY
            LAST-UPDATED "202211180000Z"
            ORGANIZATION
                "Intelbras S.A. Industria de Telecomunicacao Eletronica Brasileria."
            CONTACT-INFO
                ""
            DESCRIPTION
                "The MIB contains objects to manage configuration and
                 monitor running state for Interface Based QoS feature.
                "
            REVISION "202211180000Z"        --November 18, 2022 at 00:00 GMT
            DESCRIPTION
                "Add ibIfQoSBufferAlarm.
                 Add ibIfQoSBufferAlarmRecover.
                 Add ibIfQoSQueBufferOverrunAlarm.
                 Add ibIfQoSQueBufferOverrunRecover.
                 Add ibIfQoSFCoEPriorityAlarm.
                 Add ibIfQoSFCoEPriorityRecover.
                 Add ibIfQoSRcyPortPktsDropAlarm.
                 Add ibIfQoSRcyPortPktsDropRecover.
                 Add ibIfQoSStormSuppressAlarm.
                 Add ibIfQoSStormSuppressRecover.
                 Add ibIfQoSUniPktsDiscardAlarm.
                 Add ibIfQoSUniPktsDiscardRecover.
                 Add ibIfQoSIngressDiscardAlarm.
                 Add ibIfQoSIngressDiscardRecover."
            REVISION "202208050000Z"        --August 5, 2022 at 00:00 GMT
            DESCRIPTION
                "Add ibIfQoSCoppDropPktAlarm.
                 Add ibIfQoSCoppDropPktAlarmRecover.
                 Add ibIfQoSQueExcpAlarm.
                 Add ibIfQoSQueExcpAlarmRecover.
                 Add ibIfQoSBoardL3AclResLack.
                 Add ibIfQoSAclResAlarm.
                 Add ibIfQoSAclResAlarmRecover.
                 Add ibIfQoSAclMemFullAlarm.
                 Add ibIfQoSAclMemFullAlarmRecover."
            REVISION "202206090000Z"        --June 9, 2022 at 00:00 GMT
            DESCRIPTION
                "Add ibIfQoSLRDiscardAlarm.
                 Add ibIfQoSLRDiscardAlarmRecover.
                 Add ibIfQoSCarDiscardAlarm.
                 Add ibIfQoSCarDiscardAlarmRecover."
            REVISION "202110060000Z"        --October 06, 2021 at 00:00 GMT
            DESCRIPTION
                "Add the ibIfQoSPeakPassPPS and ibIfQoSPeakPassBPS in ibIfQoSHardwareQueueRunInfoEntry."
            REVISION "201906200000Z"        --June 20, 2019 at 00:00 GMT
            DESCRIPTION
                "Add the ibIfQoSDropPPS and ibIfQoSDropBPS in ibIfQoSHardwareQueueRunInfoEntry."
            REVISION "201812120000Z"        --December 12, 2018 at 00:00 GMT
            DESCRIPTION
                "Interface QoS management information base."
            REVISION "201802280000Z"        --February 28, 2018 at 00:00 GMT
            DESCRIPTION
                "Add ibIfQoSCoppFlowStatTable."
            REVISION "201705200000Z"        --May 20, 2017 at 00:00 GMT
            DESCRIPTION
                "Add the ibIfQoSQueueName in ibIfQoSHardwareQueueRunInfoEntry and
                add ibIfQoSHardwareQueueTotalRunInfoTable."
            REVISION "201610250000Z"        --October 25, 2016 at 00:00 GMT
            DESCRIPTION
                "Add the enumeration group3 and group4 to ibIfQoSQueueGroupType."
            REVISION "201411250000Z"        --November 25, 2014 at 00:00 GMT
            DESCRIPTION
                "Add the unit type node in ibIfQoSTricolorCarConfigTable and
                ibIfQoSGTSConfigTable, and add object ibIfQoSProcessingStatus."
            REVISION "201311280000Z"        --November 28, 2013 at 00:00 GMT
            DESCRIPTION
                "Interface QoS management information base."
            ::= { ibQos2 1 }

        ibQos2     OBJECT IDENTIFIER ::= { ibCommon 65 }

-- IfCar Action
        IbIfCarAction ::= TEXTUAL-CONVENTION
            STATUS current
            DESCRIPTION
                "The actions taken when packets conforming or exceeding the configured CIR."
            SYNTAX  INTEGER
            {
                invalid(0),
                pass(1),
                continue(2),
                discard(3),
                remark(4),
                remark-ip-continue(5),
                remark-ip-pass(6),
                remark-mplsexp-continue(7),
                remark-mplsexp-pass(8),
                remark-dscp-continue(9),
                remark-dscp-pass(10),
                remark-dot1p-continue(11),
                remark-dot1p-pass(12),
                remark-atm-clp-continue(13),
                remark-atm-clp-pass(14),
                remark-fr-de-continue(15),
                remark-fr-de-pass(16),
                remarkLocalPreContinue(17),
                remarkLocalPrePass(18),
                remarkDropPreContinue(19),
                remarkDropPrePass(20)
            }

--
-- priority queue
--
        PriorityQueue ::= TEXTUAL-CONVENTION
            STATUS current
            DESCRIPTION
                "The type of priority queue."
            SYNTAX INTEGER
            {
                top(1),
                middle(2),
                normal(3),
                bottom(4)
            }
--
-- direction
--
        Direction ::= TEXTUAL-CONVENTION
            STATUS current
            DESCRIPTION
                "Inbound or outbound."
            SYNTAX INTEGER
            {
                inbound(1),
                outbound(2)
            }
--
-- node of ibIfQoSHardwareQueueObjects
--
        ibIfQoSHardwareQueueObjects OBJECT IDENTIFIER ::= { ibIfQos2 1 }
--
-- nodes of ibIfQoSHardwareQueueConfigGroup
--
        ibIfQoSHardwareQueueConfigGroup OBJECT IDENTIFIER ::= { ibIfQoSHardwareQueueObjects 1 }

        ibIfQoSQSModeTable OBJECT-TYPE
            SYNTAX SEQUENCE OF IbIfQoSQSModeEntry
            MAX-ACCESS not-accessible
            STATUS current
            DESCRIPTION
                "A table of queue schedule mode information."
            ::= { ibIfQoSHardwareQueueConfigGroup 1 }

        ibIfQoSQSModeEntry OBJECT-TYPE
            SYNTAX IbIfQoSQSModeEntry
            MAX-ACCESS not-accessible
            STATUS current
            DESCRIPTION
                "Queue schedule mode information entry."
            INDEX { ifIndex }
            ::= { ibIfQoSQSModeTable 1 }

        IbIfQoSQSModeEntry ::=
            SEQUENCE
            {
                ibIfQoSQSMode
                    INTEGER
            }

        ibIfQoSQSMode OBJECT-TYPE
            SYNTAX INTEGER
            {
                sp(1),
                sp0(2),
                sp1(3),
                sp2(4),
                wrr(5),
                ibfq(6),
                wrr-sp(7),
                byteCountWrr(8),
                byteCountWfq(9),
                gmb(10)
            }
            MAX-ACCESS read-write
            STATUS current
            DESCRIPTION
                "The mode of schedule."
            ::= { ibIfQoSQSModeEntry 1 }

--
-- notes of ibIfQoSQSWeightTable
--
        ibIfQoSQSWeightTable OBJECT-TYPE
            SYNTAX SEQUENCE OF IbIfQoSQSWeightEntry
            MAX-ACCESS not-accessible
            STATUS current
            DESCRIPTION
                "A table of queue schedule weight configuration information."
            ::= { ibIfQoSHardwareQueueConfigGroup 2 }

        ibIfQoSQSWeightEntry OBJECT-TYPE
            SYNTAX IbIfQoSQSWeightEntry
            MAX-ACCESS not-accessible
            STATUS current
            DESCRIPTION
                "Queue schedule weight configuration information entry."
            INDEX { ifIndex, ibIfQoSQueueID }
            ::= { ibIfQoSQSWeightTable 1 }

        IbIfQoSQSWeightEntry ::=
            SEQUENCE
            {
                ibIfQoSQueueID
                    Integer32,
                ibIfQoSQueueGroupType
                    INTEGER,
                ibIfQoSQSType
                    INTEGER,
                ibIfQoSQSValue
                    Integer32,
                ibIfQoSQSMaxDelay
                    Integer32,
                ibIfQoSQSMinBandwidth
                    Integer32,
                ibIfQoSQSMinBandwidthPercent
                    Unsigned32
            }

        ibIfQoSQueueID OBJECT-TYPE
            SYNTAX Integer32
            MAX-ACCESS not-accessible
            STATUS current
            DESCRIPTION
                "Queue ID"
            ::= { ibIfQoSQSWeightEntry 1 }

        ibIfQoSQueueGroupType OBJECT-TYPE
            SYNTAX INTEGER
            {
                group0(1),
                group1(2),
                group2(3),
                group3(4),
                group4(5)
            }
            MAX-ACCESS read-write
            STATUS current
            DESCRIPTION
                "Group type of WRR and WFQ."
            ::= { ibIfQoSQSWeightEntry 2 }

        ibIfQoSQSType OBJECT-TYPE
            SYNTAX INTEGER
            {
                weight(1),
                byte-count(2)
            }
            MAX-ACCESS read-write
            STATUS current
            DESCRIPTION
                "Schedule type."
            ::= { ibIfQoSQSWeightEntry 3 }

        ibIfQoSQSValue OBJECT-TYPE
            SYNTAX Integer32
            MAX-ACCESS read-write
            STATUS current
            DESCRIPTION
                "Schedule value."
            ::= { ibIfQoSQSWeightEntry 4 }

        ibIfQoSQSMaxDelay OBJECT-TYPE
            SYNTAX Integer32
            MAX-ACCESS read-write
            STATUS current
            DESCRIPTION
                "Max delay."
            DEFVAL { 9 }
            ::= { ibIfQoSQSWeightEntry 5 }

        ibIfQoSQSMinBandwidth OBJECT-TYPE
            SYNTAX Integer32
            MAX-ACCESS read-write
            STATUS current
            DESCRIPTION
                "Min bandwidth.  Unit: kbps."
            ::= { ibIfQoSQSWeightEntry 6 }

        ibIfQoSQSMinBandwidthPercent OBJECT-TYPE
            SYNTAX Unsigned32  (0..100 | 255)
            MAX-ACCESS read-write
            STATUS current
            DESCRIPTION
                "Percent of min bandwidth.  Unit: %.
                 The value is 255 when the schedule mode of the queue is strict queuing.
                "
            ::= { ibIfQoSQSWeightEntry 7 }

--
-- nodes of ibIfQoSHardwareQueueRunInfoGroup
--
        ibIfQoSHardwareQueueRunInfoGroup OBJECT IDENTIFIER ::= { ibIfQoSHardwareQueueObjects 2 }

        ibIfQoSHardwareQueueRunInfoTable OBJECT-TYPE
            SYNTAX SEQUENCE OF IbIfQoSHardwareQueueRunInfoEntry
            MAX-ACCESS not-accessible
            STATUS current
            DESCRIPTION
                "A table of queue statistic information."
            ::= { ibIfQoSHardwareQueueRunInfoGroup 1 }

        ibIfQoSHardwareQueueRunInfoEntry OBJECT-TYPE
            SYNTAX IbIfQoSHardwareQueueRunInfoEntry
            MAX-ACCESS not-accessible
            STATUS current
            DESCRIPTION
                "Queue statistic information entry."
            INDEX { ifIndex, ibIfQoSQueueID }
            ::= { ibIfQoSHardwareQueueRunInfoTable 1 }

        IbIfQoSHardwareQueueRunInfoEntry ::=
            SEQUENCE
            {
                ibIfQoSPassPackets
                    Counter64,
                ibIfQoSDropPackets
                    Counter64,
                ibIfQoSPassBytes
                    Counter64,
                ibIfQoSPassPPS
                    Unsigned32,
                ibIfQoSPassBPS
                    Unsigned32,
                ibIfQoSDropBytes
                    Counter64,
                ibIfQoSQueueLengthInPkts
                    Unsigned32,
                ibIfQoSQueueLengthInBytes
                    Unsigned32,
                ibIfQoSCurQueuePkts
                    Unsigned32,
                ibIfQoSCurQueueBytes
                    Unsigned32,
                ibIfQoSCurQueuePPS
                    Unsigned32,
                ibIfQoSCurQueueBPS
                    Unsigned32,
                ibIfQoSTailDropPkts
                    Counter64,
                ibIfQoSTailDropBytes
                    Counter64,
                ibIfQoSTailDropPPS
                    Unsigned32,
                ibIfQoSTailDropBPS
                    Unsigned32,
                ibIfQoSWredDropPkts
                    Counter64,
                ibIfQoSWredDropBytes
                    Counter64,
                ibIfQoSWredDropPPS
                    Unsigned32,
                ibIfQoSWredDropBPS
                    Unsigned32,
                ibIfQoSQueueName
                    OCTET STRING,
                ibIfQoSDropPPS
                    Unsigned32,
                ibIfQoSDropBPS
                    Unsigned32,
                ibIfQoSPeakPassPPS
                    Unsigned32,
                ibIfQoSPeakPassBPS
                    Unsigned32
            }

        ibIfQoSPassPackets OBJECT-TYPE
            SYNTAX Counter64
            MAX-ACCESS read-only
            STATUS current
            DESCRIPTION
                "The number of forwarded packets."
            ::= { ibIfQoSHardwareQueueRunInfoEntry 1 }

        ibIfQoSDropPackets OBJECT-TYPE
            SYNTAX Counter64
            MAX-ACCESS read-only
            STATUS current
            DESCRIPTION
                "The number of dropped packets."
            ::= { ibIfQoSHardwareQueueRunInfoEntry 2 }

        ibIfQoSPassBytes OBJECT-TYPE
            SYNTAX Counter64
            MAX-ACCESS read-only
            STATUS current
            DESCRIPTION
                "The bytes of forwarded packets."
            ::= { ibIfQoSHardwareQueueRunInfoEntry 3 }

        ibIfQoSPassPPS OBJECT-TYPE
            SYNTAX Unsigned32
            MAX-ACCESS read-only
            STATUS current
            DESCRIPTION
                "The PPS of forwarded packets.  PPS: packets per second."
            ::= { ibIfQoSHardwareQueueRunInfoEntry 4 }

        ibIfQoSPassBPS OBJECT-TYPE
            SYNTAX Unsigned32
            MAX-ACCESS read-only
            STATUS current
            DESCRIPTION
                "The BPS of forwarded packets.  BPS: bytes per second."
            ::= { ibIfQoSHardwareQueueRunInfoEntry 5 }

        ibIfQoSDropBytes OBJECT-TYPE
            SYNTAX Counter64
            MAX-ACCESS read-only
            STATUS current
            DESCRIPTION
                "The bytes of dropped packets."
            ::= { ibIfQoSHardwareQueueRunInfoEntry 6 }

        ibIfQoSQueueLengthInPkts OBJECT-TYPE
            SYNTAX Unsigned32
            MAX-ACCESS read-only
            STATUS current
            DESCRIPTION
                "The max number of packets which the queue can hold."
            ::= { ibIfQoSHardwareQueueRunInfoEntry 7 }

        ibIfQoSQueueLengthInBytes OBJECT-TYPE
            SYNTAX Unsigned32
            MAX-ACCESS read-only
            STATUS current
            DESCRIPTION
                "The max bytes of packets which the queue can hold."
            ::= { ibIfQoSHardwareQueueRunInfoEntry 8 }

        ibIfQoSCurQueuePkts OBJECT-TYPE
            SYNTAX Unsigned32
            MAX-ACCESS read-only
            STATUS current
            DESCRIPTION
                "The number of packets in the current queue."
            ::= { ibIfQoSHardwareQueueRunInfoEntry 9 }

        ibIfQoSCurQueueBytes OBJECT-TYPE
            SYNTAX Unsigned32
            MAX-ACCESS read-only
            STATUS current
            DESCRIPTION
                "The bytes of packets in the current queue."
            ::= { ibIfQoSHardwareQueueRunInfoEntry 10 }

        ibIfQoSCurQueuePPS OBJECT-TYPE
            SYNTAX Unsigned32
            MAX-ACCESS read-only
            STATUS current
            DESCRIPTION
                "The PPS of packets in the current queue."
            ::= { ibIfQoSHardwareQueueRunInfoEntry 11 }

        ibIfQoSCurQueueBPS OBJECT-TYPE
            SYNTAX Unsigned32
            MAX-ACCESS read-only
            STATUS current
            DESCRIPTION
                "The BPS of packets in the current queue."
            ::= { ibIfQoSHardwareQueueRunInfoEntry 12 }

        ibIfQoSTailDropPkts OBJECT-TYPE
            SYNTAX Counter64
            MAX-ACCESS read-only
            STATUS current
            DESCRIPTION
                "The number of packets dropped by tail dropping."
            ::= { ibIfQoSHardwareQueueRunInfoEntry 13 }

        ibIfQoSTailDropBytes OBJECT-TYPE
            SYNTAX Counter64
            MAX-ACCESS read-only
            STATUS current
            DESCRIPTION
                "The bytes of packets dropped by tail dropping."
            ::= { ibIfQoSHardwareQueueRunInfoEntry 14 }

        ibIfQoSTailDropPPS OBJECT-TYPE
            SYNTAX Unsigned32
            MAX-ACCESS read-only
            STATUS current
            DESCRIPTION
                "The PPS of packets dropped by tail dropping."
            ::= { ibIfQoSHardwareQueueRunInfoEntry 15 }

        ibIfQoSTailDropBPS OBJECT-TYPE
            SYNTAX Unsigned32
            MAX-ACCESS read-only
            STATUS current
            DESCRIPTION
                "The BPS of packets dropped by tail dropping."
            ::= { ibIfQoSHardwareQueueRunInfoEntry 16 }

        ibIfQoSWredDropPkts OBJECT-TYPE
            SYNTAX Counter64
            MAX-ACCESS read-only
            STATUS current
            DESCRIPTION
                "The number of packets dropped by WRED."
            ::= { ibIfQoSHardwareQueueRunInfoEntry 17 }

        ibIfQoSWredDropBytes OBJECT-TYPE
            SYNTAX Counter64
            MAX-ACCESS read-only
            STATUS current
            DESCRIPTION
                "The bytes of packets dropped by WRED."
            ::= { ibIfQoSHardwareQueueRunInfoEntry 18 }

        ibIfQoSWredDropPPS OBJECT-TYPE
            SYNTAX Unsigned32
            MAX-ACCESS read-only
            STATUS current
            DESCRIPTION
                "The PPS of packets dropped by WRED."
            ::= { ibIfQoSHardwareQueueRunInfoEntry 19 }

        ibIfQoSWredDropBPS OBJECT-TYPE
            SYNTAX Unsigned32
            MAX-ACCESS read-only
            STATUS current
            DESCRIPTION
                "The BPS of packets dropped by WRED."
            ::= { ibIfQoSHardwareQueueRunInfoEntry 20 }

        ibIfQoSQueueName OBJECT-TYPE
            SYNTAX OCTET STRING (SIZE(2..3))
            MAX-ACCESS read-only
            STATUS current
            DESCRIPTION
                "The Name of Queue."
            ::= { ibIfQoSHardwareQueueRunInfoEntry 21 }

        ibIfQoSDropPPS OBJECT-TYPE
            SYNTAX Unsigned32
            MAX-ACCESS read-only
            STATUS current
            DESCRIPTION
                "The PPS of dropped packets.  PPS: packets per second."
            ::= { ibIfQoSHardwareQueueRunInfoEntry 22 }

        ibIfQoSDropBPS OBJECT-TYPE
            SYNTAX Unsigned32
            MAX-ACCESS read-only
            STATUS current
            DESCRIPTION
                "The BPS of dropped packets.  BPS: bytes per second."
            ::= { ibIfQoSHardwareQueueRunInfoEntry 23 }

        ibIfQoSPeakPassPPS OBJECT-TYPE
            SYNTAX Unsigned32
            MAX-ACCESS read-only
            STATUS current
            DESCRIPTION
                "The max rate of forwarded packets in bytes per second (pps)
                 during the period from the time when the reset command was executed
                 to the current time."
            ::= { ibIfQoSHardwareQueueRunInfoEntry 24 }

        ibIfQoSPeakPassBPS OBJECT-TYPE
            SYNTAX Unsigned32
            MAX-ACCESS read-only
            STATUS current
            DESCRIPTION
                "The max rate of forwarded packets in bytes per second (Bps)
                 during the period from the time when the reset command was executed
                 to the current time."
            ::= { ibIfQoSHardwareQueueRunInfoEntry 25 }

--
-- nodes of ibIfQoSHQueueTcpRunInfoTable
--

        ibIfQoSHQueueTcpRunInfoTable OBJECT-TYPE
            SYNTAX SEQUENCE OF IbIfQoSHQueueTcpRunInfoEntry
            MAX-ACCESS not-accessible
            STATUS current
            DESCRIPTION
                "A table of queue statistic information
                 about TCP and non-TCP packets."
            ::= { ibIfQoSHardwareQueueRunInfoGroup 2 }

        ibIfQoSHQueueTcpRunInfoEntry OBJECT-TYPE
            SYNTAX IbIfQoSHQueueTcpRunInfoEntry
            MAX-ACCESS not-accessible
            STATUS current
            DESCRIPTION
                "Queue statistic information entry
                 about TCP and non-TCP packets."
            INDEX { ifIndex, ibIfQoSQueueID }
            ::= { ibIfQoSHQueueTcpRunInfoTable 1 }

        IbIfQoSHQueueTcpRunInfoEntry ::=
            SEQUENCE
            {
                ibIfQoSWredDropLPreNTcpPkts
                    Counter64,
                ibIfQoSWredDropLPreNTcpBytes
                    Counter64,
                ibIfQoSWredDropLPreNTcpPPS
                    Unsigned32,
                ibIfQoSWredDropLPreNTcpBPS
                    Unsigned32,
                ibIfQoSWredDropLPreTcpPkts
                    Counter64,
                ibIfQoSWredDropLPreTcpBytes
                    Counter64,
                ibIfQoSWredDropLPreTcpPPS
                    Unsigned32,
                ibIfQoSWredDropLPreTcpBPS
                    Unsigned32,
                ibIfQoSWredDropHPreNTcpPkts
                    Counter64,
                ibIfQoSWredDropHPreNTcpBytes
                    Counter64,
                ibIfQoSWredDropHPreNTcpPPS
                    Unsigned32,
                ibIfQoSWredDropHPreNTcpBPS
                    Unsigned32,
                ibIfQoSWredDropHPreTcpPkts
                    Counter64,
                ibIfQoSWredDropHPreTcpBytes
                    Counter64,
                ibIfQoSWredDropHPreTcpPPS
                    Unsigned32,
                ibIfQoSWredDropHPreTcpBPS
                    Unsigned32
            }

        ibIfQoSWredDropLPreNTcpPkts OBJECT-TYPE
            SYNTAX Counter64
            MAX-ACCESS read-only
            STATUS current
            DESCRIPTION
                "The number of low-precedence non-TCP packets dropped by WRED."
            ::= { ibIfQoSHQueueTcpRunInfoEntry 1 }

        ibIfQoSWredDropLPreNTcpBytes OBJECT-TYPE
            SYNTAX Counter64
            MAX-ACCESS read-only
            STATUS current
            DESCRIPTION
                "The bytes of low-precedence non-TCP packets dropped by WRED."
            ::= { ibIfQoSHQueueTcpRunInfoEntry 2 }

        ibIfQoSWredDropLPreNTcpPPS OBJECT-TYPE
            SYNTAX Unsigned32
            MAX-ACCESS read-only
            STATUS current
            DESCRIPTION
                "The PPS of low-precedence non-TCP packets dropped by WRED.
                 PPS: packets per second."
            ::= { ibIfQoSHQueueTcpRunInfoEntry 3 }

        ibIfQoSWredDropLPreNTcpBPS OBJECT-TYPE
            SYNTAX Unsigned32
            MAX-ACCESS read-only
            STATUS current
            DESCRIPTION
                "The BPS of low-precedence non-TCP packets dropped by WRED.
                 BPS: bytes per second."
            ::= { ibIfQoSHQueueTcpRunInfoEntry 4 }

        ibIfQoSWredDropLPreTcpPkts OBJECT-TYPE
            SYNTAX Counter64
            MAX-ACCESS read-only
            STATUS current
            DESCRIPTION
                "The number of low-precedence TCP packets dropped by WRED."
            ::= { ibIfQoSHQueueTcpRunInfoEntry 5 }

        ibIfQoSWredDropLPreTcpBytes OBJECT-TYPE
            SYNTAX Counter64
            MAX-ACCESS read-only
            STATUS current
            DESCRIPTION
                "The bytes of low-precedence TCP packets dropped by WRED."
            ::= { ibIfQoSHQueueTcpRunInfoEntry 6 }

        ibIfQoSWredDropLPreTcpPPS OBJECT-TYPE
            SYNTAX Unsigned32
            MAX-ACCESS read-only
            STATUS current
            DESCRIPTION
                "The PPS of low-precedence TCP packets dropped by WRED."
            ::= { ibIfQoSHQueueTcpRunInfoEntry 7 }

        ibIfQoSWredDropLPreTcpBPS OBJECT-TYPE
            SYNTAX Unsigned32
            MAX-ACCESS read-only
            STATUS current
            DESCRIPTION
                "The BPS of low-precedence TCP packets dropped by WRED."
            ::= { ibIfQoSHQueueTcpRunInfoEntry 8 }

        ibIfQoSWredDropHPreNTcpPkts OBJECT-TYPE
            SYNTAX Counter64
            MAX-ACCESS read-only
            STATUS current
            DESCRIPTION
                "The number of high-precedence non-TCP packets dropped by WRED."
            ::= { ibIfQoSHQueueTcpRunInfoEntry 9 }

        ibIfQoSWredDropHPreNTcpBytes OBJECT-TYPE
            SYNTAX Counter64
            MAX-ACCESS read-only
            STATUS current
            DESCRIPTION
                "The bytes of high-precedence non-TCP packets dropped by WRED."
            ::= { ibIfQoSHQueueTcpRunInfoEntry 10 }

        ibIfQoSWredDropHPreNTcpPPS OBJECT-TYPE
            SYNTAX Unsigned32
            MAX-ACCESS read-only
            STATUS current
            DESCRIPTION
                "The PPS of high-precedence non-TCP packets dropped by WRED."
            ::= { ibIfQoSHQueueTcpRunInfoEntry 11 }

        ibIfQoSWredDropHPreNTcpBPS OBJECT-TYPE
            SYNTAX Unsigned32
            MAX-ACCESS read-only
            STATUS current
            DESCRIPTION
                "The BPS of high-precedence non-TCP packets dropped by WRED."
            ::= { ibIfQoSHQueueTcpRunInfoEntry 12 }

        ibIfQoSWredDropHPreTcpPkts OBJECT-TYPE
            SYNTAX Counter64
            MAX-ACCESS read-only
            STATUS current
            DESCRIPTION
                "The number of high-precedence TCP packets dropped by WRED."
            ::= { ibIfQoSHQueueTcpRunInfoEntry 13 }

        ibIfQoSWredDropHPreTcpBytes OBJECT-TYPE
            SYNTAX Counter64
            MAX-ACCESS read-only
            STATUS current
            DESCRIPTION
                "The bytes of high-precedence TCP packets dropped by WRED."
            ::= { ibIfQoSHQueueTcpRunInfoEntry 14 }

        ibIfQoSWredDropHPreTcpPPS OBJECT-TYPE
            SYNTAX Unsigned32
            MAX-ACCESS read-only
            STATUS current
            DESCRIPTION
                "The PPS of high-precedence TCP packets dropped by WRED."
            ::= { ibIfQoSHQueueTcpRunInfoEntry 15 }

        ibIfQoSWredDropHPreTcpBPS OBJECT-TYPE
            SYNTAX Unsigned32
            MAX-ACCESS read-only
            STATUS current
            DESCRIPTION
                "The BPS of high-precedence TCP packets dropped by WRED."
            ::= { ibIfQoSHQueueTcpRunInfoEntry 16 }

--
-- nodes of ibIfQoSHardwareQueueTotalRunInfoTable
--

        ibIfQoSHardwareQueueTotalRunInfoTable OBJECT-TYPE
            SYNTAX SEQUENCE OF IbIfQoSHardwareQueueTotalRunInfoEntry
            MAX-ACCESS not-accessible
            STATUS current
            DESCRIPTION
                "A table of queue statistic total information."
            ::= { ibIfQoSHardwareQueueRunInfoGroup 3 }

        ibIfQoSHardwareQueueTotalRunInfoEntry OBJECT-TYPE
            SYNTAX IbIfQoSHardwareQueueTotalRunInfoEntry
            MAX-ACCESS not-accessible
            STATUS current
            DESCRIPTION
                "Queue statistic information entry."
            INDEX { ifIndex }
            ::= { ibIfQoSHardwareQueueTotalRunInfoTable 1 }

        IbIfQoSHardwareQueueTotalRunInfoEntry ::=
            SEQUENCE
            {
                ibIfQoSQueueLength
                    Unsigned32,
                ibIfQoSPeakQueueBytes
                    Unsigned32
            }

        ibIfQoSQueueLength OBJECT-TYPE
            SYNTAX Unsigned32
            MAX-ACCESS read-only
            STATUS current
            DESCRIPTION
                "The length of queues."
            ::= { ibIfQoSHardwareQueueTotalRunInfoEntry 1 }

        ibIfQoSPeakQueueBytes OBJECT-TYPE
            SYNTAX Unsigned32
            MAX-ACCESS read-only
            STATUS current
            DESCRIPTION
                "The max bytes of packets in the current queues in the last 10 seconds."
            ::= { ibIfQoSHardwareQueueTotalRunInfoEntry 2 }

--
-- nodes of ibIfQoSSoftwareQueueObjects
--
        ibIfQoSSoftwareQueueObjects OBJECT IDENTIFIER ::= { ibIfQos2 2 }

--
-- nodes of ibIfQoSFIFOObject
--
        ibIfQoSFIFOObject OBJECT IDENTIFIER ::= { ibIfQoSSoftwareQueueObjects 1 }

        ibIfQoSFIFOConfigTable OBJECT-TYPE
            SYNTAX SEQUENCE OF IbIfQoSFIFOConfigEntry
            MAX-ACCESS not-accessible
            STATUS current
            DESCRIPTION
                "A table of FIFO queue information."
            ::= { ibIfQoSFIFOObject 1 }

        ibIfQoSFIFOConfigEntry OBJECT-TYPE
            SYNTAX IbIfQoSFIFOConfigEntry
            MAX-ACCESS not-accessible
            STATUS current
            DESCRIPTION
                "FIFO queue information entry."
            INDEX { ifIndex }
            ::= { ibIfQoSFIFOConfigTable 1 }

        IbIfQoSFIFOConfigEntry ::=
            SEQUENCE
            {
                ibIfQoSFIFOMaxQueueLen
                    Integer32
            }

        ibIfQoSFIFOMaxQueueLen OBJECT-TYPE
            SYNTAX Integer32
            MAX-ACCESS read-write
            STATUS current
            DESCRIPTION
                "The maximum length of FIFO queue."
            ::= { ibIfQoSFIFOConfigEntry 1 }

--
-- nodes of ibIfQoSFifoRunfoTable
--

        ibIfQoSFIFORunInfoTable OBJECT-TYPE
            SYNTAX SEQUENCE OF IbIfQoSFIFORunInfoEntry
            MAX-ACCESS not-accessible
            STATUS current
            DESCRIPTION
                "A table of FIFO queue statistic information."
            ::= { ibIfQoSFIFOObject 2 }

        ibIfQoSFIFORunInfoEntry OBJECT-TYPE
            SYNTAX IbIfQoSFIFORunInfoEntry
            MAX-ACCESS not-accessible
            STATUS current
            DESCRIPTION
                "FIFO queue statistic information entry."
            INDEX { ifIndex }
            ::= { ibIfQoSFIFORunInfoTable 1 }

        IbIfQoSFIFORunInfoEntry ::=
            SEQUENCE
            {
                ibIfQoSFIFOSize
                    Integer32,
                ibIfQoSFIFODiscardPackets
                    Counter64
            }

        ibIfQoSFIFOSize OBJECT-TYPE
            SYNTAX Integer32
            MAX-ACCESS read-only
            STATUS current
            DESCRIPTION
                "The number of packet in FIFO queue."
            ::= { ibIfQoSFIFORunInfoEntry 1 }

        ibIfQoSFIFODiscardPackets OBJECT-TYPE
            SYNTAX Counter64
            MAX-ACCESS read-only
            STATUS current
            DESCRIPTION
                "The number of discard packet."
            ::= { ibIfQoSFIFORunInfoEntry 2 }

--
-- nodes of
--
        ibIfQoSPQObject OBJECT IDENTIFIER ::= { ibIfQoSSoftwareQueueObjects 2 }

        ibIfQoSPQConfigGroup OBJECT IDENTIFIER ::= { ibIfQoSPQObject 1 }

        ibIfQoSPQDefaultTable OBJECT-TYPE
            SYNTAX SEQUENCE OF IbIfQoSPQDefaultEntry
            MAX-ACCESS not-accessible
            STATUS current
            DESCRIPTION
                "A table of priority queue default configuration information."
            ::= { ibIfQoSPQConfigGroup 1 }

        ibIfQoSPQDefaultEntry OBJECT-TYPE
            SYNTAX IbIfQoSPQDefaultEntry
            MAX-ACCESS not-accessible
            STATUS current
            DESCRIPTION
                "Priority queue default configuration information entry."
            INDEX { ibIfQoSPQListNumber }
            ::= { ibIfQoSPQDefaultTable 1 }

        IbIfQoSPQDefaultEntry ::=
            SEQUENCE
            {
                ibIfQoSPQListNumber
                    Integer32,
                ibIfQoSPQDefaultQueueType
                    PriorityQueue
            }

        ibIfQoSPQListNumber OBJECT-TYPE
            SYNTAX Integer32 (1..16)
            MAX-ACCESS not-accessible
            STATUS current
            DESCRIPTION
                "Priority queue list number."
            ::= { ibIfQoSPQDefaultEntry 1 }

        ibIfQoSPQDefaultQueueType OBJECT-TYPE
            SYNTAX PriorityQueue
            MAX-ACCESS read-write
            STATUS current
            DESCRIPTION
                "Specify priority queue that packets put into by default."
            ::= { ibIfQoSPQDefaultEntry 2 }
--
-- nods of ibIfQoSPQQueueLengthTable
--
        ibIfQoSPQQueueLengthTable OBJECT-TYPE
            SYNTAX SEQUENCE OF IbIfQoSPQQueueLengthEntry
            MAX-ACCESS not-accessible
            STATUS current
            DESCRIPTION
                "A table of queue length of priority queue configuration information."
            ::= { ibIfQoSPQConfigGroup 2 }

        ibIfQoSPQQueueLengthEntry OBJECT-TYPE
            SYNTAX IbIfQoSPQQueueLengthEntry
            MAX-ACCESS not-accessible
            STATUS current
            DESCRIPTION
                "Queue length of priority queue configuration information entry."
            INDEX { ibIfQoSPQListNumber, ibIfQoSPQQueueLengthType }
            ::= { ibIfQoSPQQueueLengthTable 1 }

        IbIfQoSPQQueueLengthEntry ::=
            SEQUENCE
            {
                ibIfQoSPQQueueLengthType
                    PriorityQueue,
                ibIfQoSPQQueueLengthValue
                    Integer32
            }

        ibIfQoSPQQueueLengthType OBJECT-TYPE
            SYNTAX PriorityQueue
            MAX-ACCESS not-accessible
            STATUS current
            DESCRIPTION
                "Type of priority queue."
            ::= { ibIfQoSPQQueueLengthEntry 1 }

        ibIfQoSPQQueueLengthValue OBJECT-TYPE
            SYNTAX Integer32 (1..1024)
            MAX-ACCESS read-write
            STATUS current
            DESCRIPTION
                "The size of priority queue."
            ::= { ibIfQoSPQQueueLengthEntry 2 }

--
-- nodes of ibIfQoSPQClassRuleTable
--
        ibIfQoSPQClassRuleTable OBJECT-TYPE
            SYNTAX SEQUENCE OF IbIfQoSPQClassRuleEntry
            MAX-ACCESS not-accessible
            STATUS current
            DESCRIPTION
                "A table of class rule of priority queue information."
            ::= { ibIfQoSPQConfigGroup 3 }

        ibIfQoSPQClassRuleEntry OBJECT-TYPE
            SYNTAX IbIfQoSPQClassRuleEntry
            MAX-ACCESS not-accessible
            STATUS current
            DESCRIPTION
                "A table of class rule of priority queue information."
            INDEX { ibIfQoSPQListNumber,
                    ibIfQoSPQClassRuleType,
                    ibIfQoSPQClassRuleValue }
            ::= { ibIfQoSPQClassRuleTable 1 }

        IbIfQoSPQClassRuleEntry ::=
            SEQUENCE
            {
                ibIfQoSPQClassRuleType
                    INTEGER,
                ibIfQoSPQClassRuleValue
                    Integer32,
                ibIfQoSPQClassRuleQueueType
                    PriorityQueue,
                ibIfQoSPQClassRowStatus
                    RowStatus
            }

        ibIfQoSPQClassRuleType OBJECT-TYPE
            SYNTAX INTEGER
            {
                interface(1),
                ipv4acl(2),
                ipv6acl(3),
                fragments(4),
                greater-than(5),
                less-than(6),
                tcp(7),
                udp(8),
                ipall(9),
                mpls(10)
            }
            MAX-ACCESS not-accessible
            STATUS current
            DESCRIPTION
                "Type of class rule.
                'ipall' means all ip packets."
            ::= { ibIfQoSPQClassRuleEntry 1 }

        ibIfQoSPQClassRuleValue OBJECT-TYPE
            SYNTAX Integer32
            MAX-ACCESS not-accessible
            STATUS current
            DESCRIPTION
                "Value of class rule.
                 interface : ifIndex
                 ipv4acl : 2000..3999
                 ipv6acl : 2000..3999, 10000..42767
                 greater-than : 0..65535
                 less-than : 0..65535
                 tcp : 0..65535
                 udp : 0..65535
                 mpls(exp-mask) : 1..255
                 other types: 0
                "
            ::= { ibIfQoSPQClassRuleEntry 2 }

        ibIfQoSPQClassRuleQueueType OBJECT-TYPE
            SYNTAX PriorityQueue
            MAX-ACCESS read-create
            STATUS current
            DESCRIPTION
                "Specify the queue for matched packets."
            ::= { ibIfQoSPQClassRuleEntry 3 }

        ibIfQoSPQClassRowStatus OBJECT-TYPE
            SYNTAX RowStatus
            MAX-ACCESS read-create
            STATUS current
            DESCRIPTION
                "RowStatus."
            ::= { ibIfQoSPQClassRuleEntry 4 }
--
-- nodes of ibIfQoSPQApplyTable
--
        ibIfQoSPQApplyTable OBJECT-TYPE
            SYNTAX SEQUENCE OF IbIfQoSPQApplyEntry
            MAX-ACCESS not-accessible
            STATUS current
            DESCRIPTION
                "A table of priority queue instance."
            ::= { ibIfQoSPQConfigGroup 4 }

        ibIfQoSPQApplyEntry OBJECT-TYPE
            SYNTAX IbIfQoSPQApplyEntry
            MAX-ACCESS not-accessible
            STATUS current
            DESCRIPTION
                "Priority queue instance information."
            INDEX { ifIndex }
            ::= { ibIfQoSPQApplyTable 1 }

        IbIfQoSPQApplyEntry ::=
            SEQUENCE
            {
                ibIfQoSPQApplyListNumber
                    Integer32,
                ibIfQoSPQApplyRowStatus
                    RowStatus
            }

        ibIfQoSPQApplyListNumber OBJECT-TYPE
            SYNTAX Integer32 (1..16)
            MAX-ACCESS read-create
            STATUS current
            DESCRIPTION
                "Priority queue list number."
            ::= { ibIfQoSPQApplyEntry 1 }

        ibIfQoSPQApplyRowStatus OBJECT-TYPE
            SYNTAX RowStatus
            MAX-ACCESS read-create
            STATUS current
            DESCRIPTION
                "RowStatus."
            ::= { ibIfQoSPQApplyEntry 2 }

--
-- Nodes of ibIfQoSPQRunInfoGroup
--
        ibIfQoSPQRunInfoGroup OBJECT IDENTIFIER ::= { ibIfQoSPQObject 2 }
--
-- nodes of ibIfQoSPQRunInfoTable
--
        ibIfQoSPQRunInfoTable OBJECT-TYPE
            SYNTAX SEQUENCE OF IbIfQoSPQRunInfoEntry
            MAX-ACCESS not-accessible
            STATUS current
            DESCRIPTION
                "A table of priority queue statistic information."
            ::= { ibIfQoSPQRunInfoGroup 1 }

        ibIfQoSPQRunInfoEntry OBJECT-TYPE
            SYNTAX IbIfQoSPQRunInfoEntry
            MAX-ACCESS not-accessible
            STATUS current
            DESCRIPTION
                "Priority queue statistic information entry."
            INDEX { ifIndex, ibIfQoSPQType }
            ::= { ibIfQoSPQRunInfoTable 1 }

        IbIfQoSPQRunInfoEntry ::=
            SEQUENCE
            {
                ibIfQoSPQType
                    PriorityQueue,
                ibIfQoSPQSize
                    Integer32,
                ibIfQoSPQLength
                    Integer32,
                ibIfQoSPQDiscardPackets
                    Counter64
            }

        ibIfQoSPQType OBJECT-TYPE
            SYNTAX PriorityQueue
            MAX-ACCESS not-accessible
            STATUS current
            DESCRIPTION
                "The type of priority queue."
            ::= { ibIfQoSPQRunInfoEntry 1 }

        ibIfQoSPQSize OBJECT-TYPE
            SYNTAX Integer32
            MAX-ACCESS read-only
            STATUS current
            DESCRIPTION
                "The number of packets in the priority queue."
            ::= { ibIfQoSPQRunInfoEntry 2 }

        ibIfQoSPQLength OBJECT-TYPE
            SYNTAX Integer32
            MAX-ACCESS read-only
            STATUS current
            DESCRIPTION
                "The maximum length of priority queue."
            ::= { ibIfQoSPQRunInfoEntry 3 }

        ibIfQoSPQDiscardPackets    OBJECT-TYPE
            SYNTAX Counter64
            MAX-ACCESS read-only
            STATUS current
            DESCRIPTION
                "The packet number of priority queue discard."
            ::= { ibIfQoSPQRunInfoEntry 4 }
--
-- nodes of ibIfQoSCQObject

        ibIfQoSCQObject OBJECT IDENTIFIER ::= { ibIfQoSSoftwareQueueObjects 3 }

        ibIfQoSCQConfigGroup OBJECT IDENTIFIER ::= { ibIfQoSCQObject 1 }

--
-- nodes of ibIfQoSCQDefaultTable
--
        ibIfQoSCQDefaultTable OBJECT-TYPE
            SYNTAX SEQUENCE OF IbIfQoSCQDefaultEntry
            MAX-ACCESS not-accessible
            STATUS current
            DESCRIPTION
                "A table of custom queue default configuration information."
            ::= { ibIfQoSCQConfigGroup 1 }

        ibIfQoSCQDefaultEntry OBJECT-TYPE
            SYNTAX IbIfQoSCQDefaultEntry
            MAX-ACCESS not-accessible
            STATUS current
            DESCRIPTION
                "Custom queue default configuration information entry."
            INDEX { ibIfQoSCQListNumber }
            ::= { ibIfQoSCQDefaultTable 1 }

        IbIfQoSCQDefaultEntry ::=
            SEQUENCE
            {
                ibIfQoSCQListNumber
                    Integer32,
                ibIfQoSCQDefaultQueueID
                    Integer32
            }

        ibIfQoSCQListNumber OBJECT-TYPE
            SYNTAX Integer32 (1..16)
            MAX-ACCESS not-accessible
            STATUS current
            DESCRIPTION
                "Custom queue list number."
            ::= { ibIfQoSCQDefaultEntry 1 }

        ibIfQoSCQDefaultQueueID OBJECT-TYPE
            SYNTAX Integer32 (0..16)
            MAX-ACCESS read-write
            STATUS current
            DESCRIPTION
                "Default queue ID."
            DEFVAL { 1 }
            ::= { ibIfQoSCQDefaultEntry 2 }
--
-- nods of ibIfQoSCQQueueLengthTable
--
        ibIfQoSCQQueueLengthTable OBJECT-TYPE
            SYNTAX SEQUENCE OF IbIfQoSCQQueueLengthEntry
            MAX-ACCESS not-accessible
            STATUS current
            DESCRIPTION
                "A table of queue length of custom queue configuration information."
            ::= { ibIfQoSCQConfigGroup 2 }

        ibIfQoSCQQueueLengthEntry OBJECT-TYPE
            SYNTAX IbIfQoSCQQueueLengthEntry
            MAX-ACCESS not-accessible
            STATUS current
            DESCRIPTION
                "Queue length of custom queue configuration information entry."
            INDEX { ibIfQoSCQListNumber, ibIfQoSCQQueueID }
            ::= { ibIfQoSCQQueueLengthTable 1 }

        IbIfQoSCQQueueLengthEntry ::=
            SEQUENCE
            {
                ibIfQoSCQQueueID
                    Integer32,
                ibIfQoSCQQueueLength
                    Integer32,
                ibIfQoSCQQueueServing
                    Integer32
            }

        ibIfQoSCQQueueID OBJECT-TYPE
            SYNTAX Integer32 (1..16)
            MAX-ACCESS not-accessible
            STATUS current
            DESCRIPTION
                "Custom queue index."
            ::= { ibIfQoSCQQueueLengthEntry 1 }

        ibIfQoSCQQueueLength OBJECT-TYPE
            SYNTAX Integer32 (1..1024)
            MAX-ACCESS read-write
            STATUS current
            DESCRIPTION
                "The size of custom queue."
            DEFVAL { 20 }
            ::= { ibIfQoSCQQueueLengthEntry 2 }

        ibIfQoSCQQueueServing OBJECT-TYPE
            SYNTAX Integer32
            MAX-ACCESS read-write
            STATUS current
            DESCRIPTION
                "The maximum bytes that the specified queue can transmit in each turn."
            DEFVAL { 1500 }
            ::= { ibIfQoSCQQueueLengthEntry 3 }

--
-- nodes of ibIfQoSCQClassRuleTable
--
        ibIfQoSCQClassRuleTable OBJECT-TYPE
            SYNTAX SEQUENCE OF IbIfQoSCQClassRuleEntry
            MAX-ACCESS not-accessible
            STATUS current
            DESCRIPTION
                "A table of class rule of custom queue information."
            ::= { ibIfQoSCQConfigGroup 3 }

        ibIfQoSCQClassRuleEntry OBJECT-TYPE
            SYNTAX IbIfQoSCQClassRuleEntry
            MAX-ACCESS not-accessible
            STATUS current
            DESCRIPTION
                "A table of class rule of custom queue information."
            INDEX { ibIfQoSCQListNumber,
                    ibIfQoSCQClassRuleType,
                    ibIfQoSCQClassRuleValue }
            ::= { ibIfQoSCQClassRuleTable 1 }

        IbIfQoSCQClassRuleEntry ::=
            SEQUENCE
            {
                ibIfQoSCQClassRuleType
                    INTEGER,
                ibIfQoSCQClassRuleValue
                    Integer32,
                ibIfQoSCQClassRuleQueueID
                    Integer32,
                ibIfQoSCQClassRowStatus
                    RowStatus
            }

        ibIfQoSCQClassRuleType OBJECT-TYPE
            SYNTAX INTEGER
            {
                interface(1),
                ipv4acl(2),
                ipv6acl(3),
                fragments(4),
                greater-than(5),
                less-than(6),
                tcp(7),
                udp(8),
                ipall(9),
                mpls(10)
            }
            MAX-ACCESS not-accessible
            STATUS current
            DESCRIPTION
                "Type of class rule.
                'ipall' means all ip packets."
            ::= { ibIfQoSCQClassRuleEntry 1 }

        ibIfQoSCQClassRuleValue OBJECT-TYPE
            SYNTAX Integer32
            MAX-ACCESS not-accessible
            STATUS current
            DESCRIPTION
                "Value of class rule.
                 interface : ifIndex
                 ipv4acl : 2000..3999
                 ipv6acl : 2000..42767
                 greater-than : 0..65535
                 less-than : 0..65535
                 tcp : 0..65535
                 udp : 0..65535
                 mpls(exp-mask) : 1..255
                 other types: 0.
                "
            ::= { ibIfQoSCQClassRuleEntry 2 }

        ibIfQoSCQClassRuleQueueID OBJECT-TYPE
            SYNTAX Integer32( 1..16)
            MAX-ACCESS read-create
            STATUS current
            DESCRIPTION
                "Specify the queue for matched packets."
            ::= { ibIfQoSCQClassRuleEntry 3 }

        ibIfQoSCQClassRowStatus OBJECT-TYPE
            SYNTAX RowStatus
            MAX-ACCESS read-create
            STATUS current
            DESCRIPTION
                "RowStatus."
            ::= { ibIfQoSCQClassRuleEntry 4 }
--
-- nodes of ibIfQoSCQApplyTable
--

        ibIfQoSCQApplyTable OBJECT-TYPE
            SYNTAX SEQUENCE OF IbIfQoSCQApplyEntry
            MAX-ACCESS not-accessible
            STATUS current
            DESCRIPTION
                "A table of custom queue instance."
            ::= { ibIfQoSCQConfigGroup 4 }

        ibIfQoSCQApplyEntry OBJECT-TYPE
            SYNTAX IbIfQoSCQApplyEntry
            MAX-ACCESS not-accessible
            STATUS current
            DESCRIPTION
                "Custom queue instance information."
            INDEX { ifIndex }
            ::= { ibIfQoSCQApplyTable 1 }

        IbIfQoSCQApplyEntry ::=
            SEQUENCE
            {
                ibIfQoSCQApplyListNumber
                    Integer32,
                ibIfQoSCQApplyRowStatus
                    RowStatus
            }

        ibIfQoSCQApplyListNumber OBJECT-TYPE
            SYNTAX Integer32 (1..16)
            MAX-ACCESS read-create
            STATUS current
            DESCRIPTION
                "Custom queue list number."
            ::= { ibIfQoSCQApplyEntry 1 }

        ibIfQoSCQApplyRowStatus OBJECT-TYPE
            SYNTAX RowStatus
            MAX-ACCESS read-create
            STATUS current
            DESCRIPTION
                "RowStatus."
            ::= { ibIfQoSCQApplyEntry 2 }
--
-- Nodes of ibIfQoSCQRunInfoGroup
--
        ibIfQoSCQRunInfoGroup OBJECT IDENTIFIER ::= { ibIfQoSCQObject 2 }

        ibIfQoSCQRunInfoTable OBJECT-TYPE
            SYNTAX SEQUENCE OF IbIfQoSCQRunInfoEntry
            MAX-ACCESS not-accessible
            STATUS current
            DESCRIPTION
                "A table of custom queue statistic information."
            ::= { ibIfQoSCQRunInfoGroup 1 }

        ibIfQoSCQRunInfoEntry OBJECT-TYPE
            SYNTAX IbIfQoSCQRunInfoEntry
            MAX-ACCESS not-accessible
            STATUS current
            DESCRIPTION
                "Custom queue statistic information entry."
            INDEX { ifIndex,
                    ibIfQoSCQQueueID }
            ::= { ibIfQoSCQRunInfoTable 1 }

        IbIfQoSCQRunInfoEntry    ::=
            SEQUENCE
            {
                ibIfQoSCQRunInfoSize
                    Integer32,
                ibIfQoSCQRunInfoLength
                    Integer32,
                ibIfQoSCQRunInfoDiscardPackets
                    Counter64
            }

        ibIfQoSCQRunInfoSize OBJECT-TYPE
            SYNTAX Integer32
            MAX-ACCESS read-only
            STATUS current
            DESCRIPTION
                "The number of packets in the custom queue."
            ::= { ibIfQoSCQRunInfoEntry 1 }

        ibIfQoSCQRunInfoLength OBJECT-TYPE
            SYNTAX Integer32
            MAX-ACCESS read-only
            STATUS current
            DESCRIPTION
                "The maximum length of custom queue."
            ::= { ibIfQoSCQRunInfoEntry 2 }

        ibIfQoSCQRunInfoDiscardPackets    OBJECT-TYPE
            SYNTAX Counter64
            MAX-ACCESS read-only
            STATUS current
            DESCRIPTION
                "The packet number of custom queue discard."
            ::= { ibIfQoSCQRunInfoEntry 3 }
--
-- nodes of ibIfQoSWFQObject
--
        ibIfQoSWFQObject OBJECT IDENTIFIER ::= { ibIfQoSSoftwareQueueObjects 4 }

        ibIfQoSWFQConfigGroup OBJECT IDENTIFIER ::= { ibIfQoSWFQObject 1 }

        ibIfQoSWFQTable OBJECT-TYPE
            SYNTAX SEQUENCE OF IbIfQoSWFQEntry
            MAX-ACCESS not-accessible
            STATUS current
            DESCRIPTION
                "A table of weighted fair queue information."
            ::= { ibIfQoSWFQConfigGroup 1 }

        ibIfQoSWFQEntry OBJECT-TYPE
            SYNTAX IbIfQoSWFQEntry
            MAX-ACCESS not-accessible
            STATUS current
            DESCRIPTION
                "Weighted fair queue information entry."
            INDEX { ifIndex }
            ::= { ibIfQoSWFQTable 1 }

        IbIfQoSWFQEntry ::=
            SEQUENCE
            {
                ibIfQoSWFQQueueLength
                    Integer32,
                ibIfQoSWFQQueueNumber
                    INTEGER,
                ibIfQoSWFQRowStatus
                    RowStatus,
                ibIfQoSWFQType
                    INTEGER
            }

        ibIfQoSWFQQueueLength OBJECT-TYPE
            SYNTAX Integer32 (1..1024)
            MAX-ACCESS read-create
            STATUS current
            DESCRIPTION
                "The length of weighted fair queue."
            DEFVAL { 64 }
            ::= { ibIfQoSWFQEntry 1 }

        ibIfQoSWFQQueueNumber OBJECT-TYPE
            SYNTAX INTEGER
            {
                size16(1),
                size32(2),
                size64(3),
                size128(4),
                size256(5),
                size512(6),
                size1024(7),
                size2048(8),
                size4096(9)
            }
            MAX-ACCESS read-create
            STATUS current
            DESCRIPTION
                "The number of weighted fair queue."
            DEFVAL { 5 }
            ::= { ibIfQoSWFQEntry 2 }

        ibIfQoSWFQRowStatus  OBJECT-TYPE
            SYNTAX RowStatus
            MAX-ACCESS read-create
            STATUS current
            DESCRIPTION
                "RowStatus."
            ::= { ibIfQoSWFQEntry 3 }

        ibIfQoSWFQType OBJECT-TYPE
            SYNTAX INTEGER
            {
                ip-precedence(1),
                dscp(2)
            }
            MAX-ACCESS read-create
            STATUS current
            DESCRIPTION
                "The type of weighted fair queue."
            DEFVAL { 1 }
            ::= { ibIfQoSWFQEntry 4 }
--
-- nodes of ibIfQoSWFQRunInfoGroup
--
        ibIfQoSWFQRunInfoGroup OBJECT IDENTIFIER ::= { ibIfQoSWFQObject 2 }

        ibIfQoSWFQRunInfoTable OBJECT-TYPE
            SYNTAX SEQUENCE OF IbIfQoSWFQRunInfoEntry
            MAX-ACCESS not-accessible
            STATUS current
            DESCRIPTION
                "A table of weighted fair queue statistic information."
            ::= { ibIfQoSWFQRunInfoGroup 1 }

        ibIfQoSWFQRunInfoEntry OBJECT-TYPE
            SYNTAX IbIfQoSWFQRunInfoEntry
            MAX-ACCESS not-accessible
            STATUS current
            DESCRIPTION
                "Weighted fair queue statistic information entry."
            INDEX { ifIndex }
            ::= { ibIfQoSWFQRunInfoTable 1 }

        IbIfQoSWFQRunInfoEntry ::=
            SEQUENCE
            {
                ibIfQoSWFQSize
                    Integer32,
                ibIfQoSWFQLength
                    Integer32,
                ibIfQoSWFQDiscardPackets
                    Counter64,
                ibIfQoSWFQHashedActiveQueues
                    Integer32,
                ibIfQoSWFQHashedMaxActiveQueues
                    Integer32,
                ibIfQosWFQhashedTotalQueues
                    Integer32
            }

        ibIfQoSWFQSize OBJECT-TYPE
            SYNTAX Integer32
            MAX-ACCESS read-only
            STATUS current
            DESCRIPTION
                "The number of packets in all the queues"
            ::= { ibIfQoSWFQRunInfoEntry 1 }

        ibIfQoSWFQLength OBJECT-TYPE
            SYNTAX Integer32
            MAX-ACCESS read-only
            STATUS current
            DESCRIPTION
                "The length of weighted fair queue."
            ::= { ibIfQoSWFQRunInfoEntry 2 }

        ibIfQoSWFQDiscardPackets OBJECT-TYPE
            SYNTAX Counter64
            MAX-ACCESS read-only
            STATUS current
            DESCRIPTION
                "The number of discarded packets in all the queues."
            ::= { ibIfQoSWFQRunInfoEntry 3 }

        ibIfQoSWFQHashedActiveQueues OBJECT-TYPE
            SYNTAX Integer32
            MAX-ACCESS read-only
            STATUS current
            DESCRIPTION
                "The number of active queues."
            ::= { ibIfQoSWFQRunInfoEntry 4 }

        ibIfQoSWFQHashedMaxActiveQueues OBJECT-TYPE
            SYNTAX Integer32
            MAX-ACCESS read-only
            STATUS current
            DESCRIPTION
                "The number of maximum active queues."
            ::= { ibIfQoSWFQRunInfoEntry 5 }

        ibIfQosWFQhashedTotalQueues   OBJECT-TYPE
            SYNTAX Integer32
            MAX-ACCESS read-only
            STATUS current
            DESCRIPTION
                "The number of queues."
            ::= { ibIfQoSWFQRunInfoEntry 6 }
--
-- nodes of ibIfQoSBandwidthGroup
--
        ibIfQoSBandwidthGroup OBJECT IDENTIFIER ::= { ibIfQoSSoftwareQueueObjects 5 }

        ibIfQoSBandwidthTable OBJECT-TYPE
            SYNTAX SEQUENCE OF IbIfQoSBandwidthEntry
            MAX-ACCESS not-accessible
            STATUS current
            DESCRIPTION
                "A table of bandwidth of interface information."
            ::= { ibIfQoSBandwidthGroup 1 }

        ibIfQoSBandwidthEntry OBJECT-TYPE
            SYNTAX IbIfQoSBandwidthEntry
            MAX-ACCESS not-accessible
            STATUS current
            DESCRIPTION
                "Bandwidth information entry."
            INDEX { ifIndex }
            ::= { ibIfQoSBandwidthTable 1 }

        IbIfQoSBandwidthEntry ::=
            SEQUENCE
            {
                ibIfQoSMaxBandwidth
                    Integer32,
                ibIfQoSReservedBandwidthPct
                    Integer32,
                ibIfQoSBandwidthRowStatus
                    RowStatus
            }

        ibIfQoSMaxBandwidth OBJECT-TYPE
            SYNTAX Integer32
            MAX-ACCESS read-create
            STATUS current
            DESCRIPTION
                "The maximum bandwidth of interface.  Unit : Kbps"
            ::= { ibIfQoSBandwidthEntry 1 }

        ibIfQoSReservedBandwidthPct OBJECT-TYPE
            SYNTAX Integer32 (1..100)
            MAX-ACCESS read-create
            STATUS current
            DESCRIPTION
                "Max reserved bandwidth of the interface for QoS."
            DEFVAL { 75 }
            ::= { ibIfQoSBandwidthEntry 2 }

        ibIfQoSBandwidthRowStatus OBJECT-TYPE
            SYNTAX RowStatus
            MAX-ACCESS read-create
            STATUS current
            DESCRIPTION
                "RowStatus."
            ::= { ibIfQoSBandwidthEntry 3 }
--
-- nodes of ibIfQoSQmtokenGroup
--
        ibIfQoSQmtokenGroup OBJECT IDENTIFIER ::= { ibIfQoSSoftwareQueueObjects 6 }

        ibIfQoSQmtokenTable OBJECT-TYPE
            SYNTAX SEQUENCE OF IbIfQoSQmtokenEntry
            MAX-ACCESS not-accessible
            STATUS current
            DESCRIPTION
                "A table of qmtoken information."
            ::= { ibIfQoSQmtokenGroup 1 }

        ibIfQoSQmtokenEntry OBJECT-TYPE
            SYNTAX IbIfQoSQmtokenEntry
            MAX-ACCESS not-accessible
            STATUS current
            DESCRIPTION
                "Qmtoken information entry."
            INDEX { ifIndex }
            ::= { ibIfQoSQmtokenTable 1 }

        IbIfQoSQmtokenEntry ::=
            SEQUENCE
            {
                ibIfQoSQmtokenNumber
                    Integer32,
                ibIfQoSQmtokenRosStatus
                    RowStatus
            }

        ibIfQoSQmtokenNumber OBJECT-TYPE
            SYNTAX Integer32 (1..50)
            MAX-ACCESS read-create
            STATUS current
            DESCRIPTION
                "The number of tokens."
            ::= { ibIfQoSQmtokenEntry 1 }

        ibIfQoSQmtokenRosStatus OBJECT-TYPE
            SYNTAX RowStatus
            MAX-ACCESS read-create
            STATUS current
            DESCRIPTION
                "RowStatus"
            ::= { ibIfQoSQmtokenEntry 2 }

--
-- nodes of ibIfQoSRTPQObject
--
        ibIfQoSRTPQObject OBJECT IDENTIFIER ::= { ibIfQoSSoftwareQueueObjects 7 }

        ibIfQoSRTPQConfigGroup OBJECT IDENTIFIER ::= { ibIfQoSRTPQObject 1 }

        ibIfQoSRTPQConfigTable OBJECT-TYPE
            SYNTAX SEQUENCE OF IbIfQoSRTPQConfigEntry
            MAX-ACCESS not-accessible
            STATUS current
            DESCRIPTION
                "A table of Real-time protocol queue information."
            ::= { ibIfQoSRTPQConfigGroup 1 }

        ibIfQoSRTPQConfigEntry OBJECT-TYPE
            SYNTAX IbIfQoSRTPQConfigEntry
            MAX-ACCESS not-accessible
            STATUS current
            DESCRIPTION
                "The information of Real-time protocol queue entry."
            INDEX { ifIndex }
            ::= { ibIfQoSRTPQConfigTable 1 }

        IbIfQoSRTPQConfigEntry ::=
            SEQUENCE
            {
                ibIfQoSRTPQStartPort
                    Integer32,
                ibIfQoSRTPQEndPort
                    Integer32,
                ibIfQoSRTPQReservedBandwidth
                    Integer32,
                ibIfQoSRTPQCbs
                    Unsigned32,
                ibIfQoSRTPQRowStatus
                    RowStatus
            }

        ibIfQoSRTPQStartPort OBJECT-TYPE
            SYNTAX Integer32 (2000..65535)
            MAX-ACCESS read-create
            STATUS current
            DESCRIPTION
                "Minimum threshold of UDP destination port."
            ::= { ibIfQoSRTPQConfigEntry 1 }

        ibIfQoSRTPQEndPort OBJECT-TYPE
            SYNTAX Integer32 (2000..65535)
            MAX-ACCESS read-create
            STATUS current
            DESCRIPTION
                "Maximum threshold of UDP destination port."
            ::= { ibIfQoSRTPQConfigEntry 2 }

        ibIfQoSRTPQReservedBandwidth OBJECT-TYPE
            SYNTAX Integer32
            MAX-ACCESS read-create
            STATUS current
            DESCRIPTION
                "Maximum bandwidth.  unit : kbps"
            ::= { ibIfQoSRTPQConfigEntry 3 }

        ibIfQoSRTPQCbs OBJECT-TYPE
            SYNTAX Unsigned32
            MAX-ACCESS read-create
            STATUS current
            DESCRIPTION
                "Committed Burst Size. Unit: byte"
            ::= { ibIfQoSRTPQConfigEntry 4 }

        ibIfQoSRTPQRowStatus OBJECT-TYPE
            SYNTAX RowStatus
            MAX-ACCESS read-create
            STATUS current
            DESCRIPTION
                "RowStatus."
            ::= { ibIfQoSRTPQConfigEntry 5 }
--
-- nodes of ibIfQoSRTPQRunInfoGroup
--
        ibIfQoSRTPQRunInfoGroup OBJECT IDENTIFIER ::= { ibIfQoSRTPQObject 2 }

        ibIfQoSRTPQRunInfoTable OBJECT-TYPE
            SYNTAX SEQUENCE OF IbIfQoSRTPQRunInfoEntry
            MAX-ACCESS not-accessible
            STATUS current
            DESCRIPTION
                "A table of statistic information of Real-time protocol information."
            ::= { ibIfQoSRTPQRunInfoGroup 1 }

        ibIfQoSRTPQRunInfoEntry OBJECT-TYPE
            SYNTAX IbIfQoSRTPQRunInfoEntry
            MAX-ACCESS not-accessible
            STATUS current
            DESCRIPTION
                "Statistic information of Real-time protocol information entry."
            INDEX { ifIndex }
            ::= { ibIfQoSRTPQRunInfoTable 1 }

        IbIfQoSRTPQRunInfoEntry ::=
            SEQUENCE
            {
                ibIfQoSRTPQPacketNumber
                    Integer32,
                ibIfQoSRTPQPacketSize
                    Integer32,
                ibIfQoSRTPQOutputPackets
                    Counter64,
                ibIfQoSRTPQDiscardPackets
                    Counter64
            }

        ibIfQoSRTPQPacketNumber OBJECT-TYPE
            SYNTAX Integer32
            MAX-ACCESS read-only
            STATUS current
            DESCRIPTION
                "The number of packets in the Real-time protocol queue."
            ::= { ibIfQoSRTPQRunInfoEntry 1 }

        ibIfQoSRTPQPacketSize OBJECT-TYPE
            SYNTAX Integer32
            MAX-ACCESS read-only
            STATUS current
            DESCRIPTION
                "The size of Real-time protocol queue."
            ::= { ibIfQoSRTPQRunInfoEntry 2 }

        ibIfQoSRTPQOutputPackets OBJECT-TYPE
            SYNTAX Counter64
            MAX-ACCESS read-only
            STATUS current
            DESCRIPTION
                "The number of output packets."
            ::= { ibIfQoSRTPQRunInfoEntry 3 }

        ibIfQoSRTPQDiscardPackets OBJECT-TYPE
            SYNTAX Counter64
            MAX-ACCESS read-only
            STATUS current
            DESCRIPTION
                "The number of discard packets."
            ::= { ibIfQoSRTPQRunInfoEntry 4 }

--
-- nodes of ibIfQoSCarListObject
--
       ibIfQoSCarListObject OBJECT IDENTIFIER ::= { ibIfQoSSoftwareQueueObjects 8 }

       ibIfQoCarListGroup OBJECT IDENTIFIER ::= { ibIfQoSCarListObject 1 }

       ibIfQoSCarlTable OBJECT-TYPE
            SYNTAX SEQUENCE OF IbIfQoSCarlEntry
            MAX-ACCESS not-accessible
            STATUS current
            DESCRIPTION
                   "Committed Access Rate List(CARL) table."
            ::= { ibIfQoCarListGroup 1 }

        ibIfQoSCarlEntry OBJECT-TYPE
            SYNTAX IbIfQoSCarlEntry
            MAX-ACCESS not-accessible
            STATUS current
            DESCRIPTION
                    "CARL configuration information."
            INDEX { ibIfQoSCarlListNum }
            ::= { ibIfQoSCarlTable 1 }

        IbIfQoSCarlEntry ::=
            SEQUENCE {
                         ibIfQoSCarlListNum
                             Integer32,
                         ibIfQoSCarlParaType
                             INTEGER,
                         ibIfQoSCarlParaValue
                             OCTET STRING,
                         ibIfQoSCarlRowStatus
                             RowStatus
                     }

        ibIfQoSCarlListNum OBJECT-TYPE
            SYNTAX Integer32
            MAX-ACCESS not-accessible
            STATUS current
            DESCRIPTION
                    "The index of the table, which is the CARL number."
            ::= { ibIfQoSCarlEntry 1 }

        ibIfQoSCarlParaType OBJECT-TYPE
            SYNTAX INTEGER
                    {
                        macAddress(1),
                        precMask(2),
                        dscpMask(3)
                    }
            MAX-ACCESS read-create
            STATUS current
            DESCRIPTION
                    "Parameter type of the CARL number."
            ::= { ibIfQoSCarlEntry 2 }

        ibIfQoSCarlParaValue OBJECT-TYPE
            SYNTAX OCTET STRING
            MAX-ACCESS read-create
            STATUS current
            DESCRIPTION
                    "Parameter value of the CARL table."
            ::= { ibIfQoSCarlEntry 3 }

        ibIfQoSCarlRowStatus OBJECT-TYPE
            SYNTAX RowStatus
            MAX-ACCESS read-create
            STATUS current
            DESCRIPTION
               "RowStatus."
            ::= { ibIfQoSCarlEntry 4 }

--
-- nodes of ibIfQoSLineRateObject
--
        ibIfQoSLineRateObjects OBJECT IDENTIFIER ::= { ibIfQos2 3 }

        ibIfQoSLRConfigTable OBJECT-TYPE
            SYNTAX SEQUENCE OF IbIfQoSLRConfigEntry
            MAX-ACCESS not-accessible
            STATUS current
            DESCRIPTION
                "A table of line rate configuration information."
            ::= { ibIfQoSLineRateObjects 1 }

        ibIfQoSLRConfigEntry OBJECT-TYPE
            SYNTAX IbIfQoSLRConfigEntry
            MAX-ACCESS not-accessible
            STATUS current
            DESCRIPTION
                "Line rate configuration information entry."
            INDEX { ifIndex, ibIfQoSLRDirection }
            ::= { ibIfQoSLRConfigTable 1 }

        IbIfQoSLRConfigEntry ::=
            SEQUENCE
            {
                ibIfQoSLRDirection
                    Direction,
                ibIfQoSLRCir
                    Unsigned32,
                ibIfQoSLRCbs
                    Unsigned32,
                ibIfQoSLREbs
                    Unsigned32,
                ibIfQoSRowStatus
                    RowStatus,
                ibIfQoSLRPir
                    Unsigned32,
                ibIfQoSLRUnit
                    INTEGER
            }

        ibIfQoSLRDirection OBJECT-TYPE
            SYNTAX Direction
            MAX-ACCESS not-accessible
            STATUS current
            DESCRIPTION
                "Line rate on the inbound or outbound of data stream."
            ::= { ibIfQoSLRConfigEntry 1 }

        ibIfQoSLRCir OBJECT-TYPE
            SYNTAX Unsigned32
            MAX-ACCESS read-create
            STATUS current
            DESCRIPTION
                "Committed Information Rate."
            ::= { ibIfQoSLRConfigEntry 2 }

        ibIfQoSLRCbs  OBJECT-TYPE
            SYNTAX Unsigned32
            MAX-ACCESS read-create
            STATUS current
            DESCRIPTION
                "Committed Burst Size."
            ::= { ibIfQoSLRConfigEntry 3 }

        ibIfQoSLREbs  OBJECT-TYPE
            SYNTAX Unsigned32
            MAX-ACCESS read-create
            STATUS current
            DESCRIPTION
                "Excess Burst Size."
            ::= { ibIfQoSLRConfigEntry 4 }

        ibIfQoSRowStatus  OBJECT-TYPE
            SYNTAX RowStatus
            MAX-ACCESS read-create
            STATUS current
            DESCRIPTION
                "RowStatus."
            ::= { ibIfQoSLRConfigEntry 5 }

        ibIfQoSLRPir OBJECT-TYPE
            SYNTAX Unsigned32
            MAX-ACCESS read-create
            STATUS current
            DESCRIPTION
                "Peak Information Rate."
            ::= { ibIfQoSLRConfigEntry 6 }

        ibIfQoSLRUnit OBJECT-TYPE
            SYNTAX INTEGER
            {
                unitAbsolute(1),
                unitPercent(2)
            }
            MAX-ACCESS read-create
            STATUS current
            DESCRIPTION
                "LR Unit:
                 Absolute, Unit Kbps (1)
                 Percent, Unit % (2)
                "
            DEFVAL { unitAbsolute }
            ::= { ibIfQoSLRConfigEntry 7 }

--
-- nodes of ibIfQoSLRRunInfoTable
--
        ibIfQoSLRRunInfoTable OBJECT-TYPE
            SYNTAX SEQUENCE OF IbIfQoSLRRunInfoEntry
            MAX-ACCESS not-accessible
            STATUS current
            DESCRIPTION
                "A table of line rate run info information."
            ::= { ibIfQoSLineRateObjects 2 }

        ibIfQoSLRRunInfoEntry OBJECT-TYPE
            SYNTAX IbIfQoSLRRunInfoEntry
            MAX-ACCESS not-accessible
            STATUS current
            DESCRIPTION
                "Line rate run info information entry."
            INDEX { ifIndex, ibIfQoSLRDirection }
            ::= { ibIfQoSLRRunInfoTable 1 }

        IbIfQoSLRRunInfoEntry ::=
            SEQUENCE
            {
                ibIfQoSLRRunInfoPassedPackets
                    Counter64,
                ibIfQoSLRRunInfoPassedBytes
                    Counter64,
                ibIfQoSLRRunInfoDelayedPackets
                    Counter64,
                ibIfQoSLRRunInfoDelayedBytes
                    Counter64,
                ibIfQoSLRRunInfoActiveShaping
                    INTEGER
            }

        ibIfQoSLRRunInfoPassedPackets OBJECT-TYPE
            SYNTAX Counter64
            MAX-ACCESS read-only
            STATUS current
            DESCRIPTION
                "The number of passed packets."
            ::= { ibIfQoSLRRunInfoEntry 1 }

        ibIfQoSLRRunInfoPassedBytes OBJECT-TYPE
            SYNTAX Counter64
            MAX-ACCESS read-only
            STATUS current
            DESCRIPTION
                "The number of passed bytes."
            ::= { ibIfQoSLRRunInfoEntry 2 }

        ibIfQoSLRRunInfoDelayedPackets OBJECT-TYPE
            SYNTAX Counter64
            MAX-ACCESS read-only
            STATUS current
            DESCRIPTION
                "The number of delayed packets."
            ::= { ibIfQoSLRRunInfoEntry 3 }

        ibIfQoSLRRunInfoDelayedBytes OBJECT-TYPE
            SYNTAX Counter64
            MAX-ACCESS read-only
            STATUS current
            DESCRIPTION
                "The number of delayed bytes."
            ::= { ibIfQoSLRRunInfoEntry 4 }

        ibIfQoSLRRunInfoActiveShaping OBJECT-TYPE
            SYNTAX INTEGER
            {
                active(1),
                inactive(2)
            }
            MAX-ACCESS read-only
            STATUS current
            DESCRIPTION
                "The flag of shaping."
            ::= { ibIfQoSLRRunInfoEntry 5 }

--
-- nodes of car group
--
        ibIfQoSCARObjects OBJECT IDENTIFIER ::= { ibIfQos2 4 }
--
-- nodes of ibIfQoSAggregativeCarGroup
--
        ibIfQoSAggregativeCarGroup OBJECT IDENTIFIER ::= { ibIfQoSCARObjects 1 }
--
-- nodes of ibIfQoSAggregativeCarConfigTable
--
        ibIfQoSAggregativeCarNextIndex OBJECT-TYPE
            SYNTAX Integer32
            MAX-ACCESS read-only
            STATUS current
            DESCRIPTION
                "This object contains an appropriate value to be used for ibIfQoSAggregativeCarIndex
                 when creating rows in the ibIfQoSAggregativeCarConfigTable.
                 Begin with 1.
                "
            ::= { ibIfQoSAggregativeCarGroup 1 }

        ibIfQoSAggregativeCarConfigTable OBJECT-TYPE
            SYNTAX SEQUENCE OF IbIfQoSAggregativeCarConfigEntry
            MAX-ACCESS not-accessible
            STATUS current
            DESCRIPTION
                "A table of aggregative car information."
            ::= { ibIfQoSAggregativeCarGroup 2 }

        ibIfQoSAggregativeCarConfigEntry OBJECT-TYPE
            SYNTAX IbIfQoSAggregativeCarConfigEntry
            MAX-ACCESS not-accessible
            STATUS current
            DESCRIPTION
                "Aggregative car information."
            INDEX { ibIfQoSAggregativeCarIndex }
            ::= { ibIfQoSAggregativeCarConfigTable 1 }

        IbIfQoSAggregativeCarConfigEntry     ::=
            SEQUENCE
            {
                ibIfQoSAggregativeCarIndex
                    Integer32,
                ibIfQoSAggregativeCarName
                    OCTET STRING,
                ibIfQoSAggregativeCarCir
                    Unsigned32,
                ibIfQoSAggregativeCarCbs
                    Unsigned32,
                ibIfQoSAggregativeCarEbs
                    Unsigned32,
                ibIfQoSAggregativeCarPir
                    Unsigned32,
                ibIfQoSAggregativeCarGreenActionType
                    IbIfCarAction,
                ibIfQoSAggregativeCarGreenActionValue
                    Integer32,
                ibIfQoSAggregativeCarYellowActionType
                    IbIfCarAction,
                ibIfQoSAggregativeCarYellowActionValue
                    Integer32,
                ibIfQoSAggregativeCarRedActionType
                    IbIfCarAction,
                ibIfQoSAggregativeCarRedActionValue
                    Integer32,
                ibIfQoSAggregativeCarType
                    INTEGER,
                ibIfQoSAggregativeCarRowStatus
                    RowStatus
            }

        ibIfQoSAggregativeCarIndex OBJECT-TYPE
            SYNTAX Integer32 (1..65534)
            MAX-ACCESS not-accessible
            STATUS current
            DESCRIPTION
                "The index of aggregative car."
            ::= { ibIfQoSAggregativeCarConfigEntry 1 }

        ibIfQoSAggregativeCarName OBJECT-TYPE
            SYNTAX OCTET STRING (SIZE(1..31))
            MAX-ACCESS read-create
            STATUS current
            DESCRIPTION
                "The name of aggregative car."
            ::= { ibIfQoSAggregativeCarConfigEntry 2 }

        ibIfQoSAggregativeCarCir OBJECT-TYPE
            SYNTAX Unsigned32
            MAX-ACCESS read-create
            STATUS current
            DESCRIPTION
                "Committed-information-rate.  Unit : kbps"
            ::= { ibIfQoSAggregativeCarConfigEntry 3 }

        ibIfQoSAggregativeCarCbs OBJECT-TYPE
            SYNTAX Unsigned32
            MAX-ACCESS read-create
            STATUS current
            DESCRIPTION
                "Committed-burst-size.  Unit : byte"
            ::= { ibIfQoSAggregativeCarConfigEntry 4 }

        ibIfQoSAggregativeCarEbs OBJECT-TYPE
            SYNTAX Unsigned32
            MAX-ACCESS read-create
            STATUS current
            DESCRIPTION
                "Excess-burst-size.  Unit : byte"
            ::= { ibIfQoSAggregativeCarConfigEntry 5 }

        ibIfQoSAggregativeCarPir OBJECT-TYPE
            SYNTAX Unsigned32
            MAX-ACCESS read-create
            STATUS current
            DESCRIPTION
                "Peak-information-rate.  Unit : kbps"
            DEFVAL { 4294967295 }
            ::= { ibIfQoSAggregativeCarConfigEntry 6 }

        ibIfQoSAggregativeCarGreenActionType OBJECT-TYPE
            SYNTAX IbIfCarAction
            MAX-ACCESS read-create
            STATUS current
            DESCRIPTION
                "Supported green action:
                 invalid(0),
                 pass(1),
                 discard(3),
                 remark(4),
                 remark-ip-pass(6),
                 remark-mplsexp-pass(8),
                 remark-dscp-pass(10),
                 remark-dot1p-pass(12),
                 remark-atm-clp-pass(14),
                 remark-fr-de-pass(16),
                 remarkLocalPrePass(18),
                 remarkDropPrePass(20).
                 Hardware QoS : pass, discard, remark.
                 Software QoS : pass, discard, remark-ip-pass(6),
                 remark-mplsexp-pass(8), remark-dscp-pass(10).
                 'invalid' is returned when getting value from software QoS.
                 "
            DEFVAL { pass }
            ::= { ibIfQoSAggregativeCarConfigEntry 7 }

        ibIfQoSAggregativeCarGreenActionValue OBJECT-TYPE
            SYNTAX Integer32 (0..63|255)
            MAX-ACCESS read-create
            STATUS current
            DESCRIPTION
                "The value is to remark When green action is remarking.
                 For remark-dscp-pass, the range is 0 to 63;
                 For remark-ip-pass, remark-mplsexp-pass, remark-dot1p-pass and
                 remarkLocalPrePass, the range is 0 to 7;
                 For remark-fr-de-pass and remark-atm-clp-pass, the range is 0 to 1;
                 For remarkDropPrePass, the range is 0 to 2.
                 Only software QoS support this node.
                 255 is returned only when getting value from hardware QoS or
                 when action being pass, discard of software QoS.
                 255 can't be set.
                "
            ::= { ibIfQoSAggregativeCarConfigEntry 8 }

        ibIfQoSAggregativeCarYellowActionType OBJECT-TYPE
            SYNTAX IbIfCarAction
            MAX-ACCESS read-create
            STATUS current
            DESCRIPTION
                "Supported yellow action:
                 invalid(0),
                 pass(1),
                 discard(3),
                 remark(4),
                 remark-ip-pass(6),
                 remark-mplsexp-pass(8),
                 remark-dscp-pass(10),
                 remark-dot1p-pass(12),
                 remark-atm-clp-pass(14),
                 remark-fr-de-pass(16),
                 remarkLocalPrePass(18),
                 remarkDropPrePass(20).
                 Hardware QoS : pass, discard, remark.
                 Software QoS : pass, discard, remark-ip-pass(6),
                 remark-mplsexp-pass(8), remark-dscp-pass(10).
                 'invalid' is returned when getting value from software QoS.
                "
            ::= { ibIfQoSAggregativeCarConfigEntry 9 }

        ibIfQoSAggregativeCarYellowActionValue OBJECT-TYPE
            SYNTAX Integer32 (0..63|255)
            MAX-ACCESS read-create
            STATUS current
            DESCRIPTION
                "The value is to remark When yellow action is remarking.
                 For remark-dscp-pass, the range is 0 to 63;
                 For remark-ip-pass, remark-mplsexp-pass, remark-dot1p-pass and
                 remarkLocalPrePass, the range is 0 to 7;
                 For remark-fr-de-pass and remark-atm-clp-pass, the range is 0 to 1;
                 For remarkDropPrePass, the range is 0 to 2.
                 Only software QoS support this node.
                 255 is returned only when getting value from hardware QoS or
                 when action being pass, discard of software QoS.
                 255 can't be set.
                "
            ::= { ibIfQoSAggregativeCarConfigEntry 10 }

        ibIfQoSAggregativeCarRedActionType OBJECT-TYPE
            SYNTAX IbIfCarAction
            MAX-ACCESS read-create
            STATUS current
            DESCRIPTION
                "Supported red action:
                 invalid(0),
                 pass(1),
                 discard(3),
                 remark(4),
                 remark-ip-pass(6),
                 remark-mplsexp-pass(8),
                 remark-dscp-pass(10),
                 remark-dot1p-pass(12),
                 remark-atm-clp-pass(14),
                 remark-fr-de-pass(16),
                 remarkLocalPrePass(18),
                 remarkDropPrePass(20).
                 Hardware QoS : pass, discard, remark.
                 Software QoS : pass, discard, remark-ip-pass(6),
                 remark-mplsexp-pass(8), remark-dscp-pass(10).
                 'invalid' is returned when getting value from software QoS.
                "
            ::= { ibIfQoSAggregativeCarConfigEntry 11 }

        ibIfQoSAggregativeCarRedActionValue OBJECT-TYPE
            SYNTAX Integer32 (0..63|255)
            MAX-ACCESS read-create
            STATUS current
            DESCRIPTION
                "The value is to remark When red action is remarking.
                 For remark-dscp-pass, the range is 0 to 63;
                 For remark-ip-pass, remark-mplsexp-pass, remark-dot1p-pass and
                 remarkLocalPrePass, the range is 0 to 7;
                 For remark-fr-de-pass and remark-atm-clp-pass, the range is 0 to 1;
                 For remarkDropPrePass, the range is 0 to 2.
                 Only software QoS support this node.
                 255 is returned only when getting value from hardware QoS or
                 when action being pass, discard of software QoS.
                 255 can't be set.
                "
            ::= { ibIfQoSAggregativeCarConfigEntry 12 }

        ibIfQoSAggregativeCarType OBJECT-TYPE
            SYNTAX INTEGER
            {
                aggregative(1),
                notAggregative(2),
                hierarchy(3)
            }
            MAX-ACCESS read-create
            STATUS current
            DESCRIPTION
                "The type of aggregative CAR.
                 The enumeration 'aggregative' indicates that the ports
                 with a same aggregative CAR use one token bulk.

                 The enumeration 'notAggregative' indicates that each port
                 uses one token bulk.

                 The enumeration 'hierarchy' indicates that each object uses one
                 token bulk after processed first by some other token bulk.
                "
            ::= { ibIfQoSAggregativeCarConfigEntry 13 }

        ibIfQoSAggregativeCarRowStatus OBJECT-TYPE
            SYNTAX RowStatus
            MAX-ACCESS read-create
            STATUS current
            DESCRIPTION
                "RowStatus."
            ::= { ibIfQoSAggregativeCarConfigEntry 14 }
--
-- nodes of ibIfQoSAggregativeCarApplyGroup
--
        ibIfQoSAggregativeCarApplyTable OBJECT-TYPE
            SYNTAX SEQUENCE OF IbIfQoSAggregativeCarApplyEntry
            MAX-ACCESS not-accessible
            STATUS current
            DESCRIPTION
                "A table of aggregative car instance."
            ::= { ibIfQoSAggregativeCarGroup 3 }

        ibIfQoSAggregativeCarApplyEntry OBJECT-TYPE
            SYNTAX IbIfQoSAggregativeCarApplyEntry
            MAX-ACCESS not-accessible
            STATUS current
            DESCRIPTION
                "Aggregative car instance information."
            INDEX { ifIndex,
                    ibIfQoSAggregativeCarApplyDirection,
                    ibIfQoSAggregativeCarApplyRuleType,
                    ibIfQoSAggregativeCarApplyRuleValue
                  }
            ::= { ibIfQoSAggregativeCarApplyTable 1 }

        IbIfQoSAggregativeCarApplyEntry ::=
            SEQUENCE
            {
                ibIfQoSAggregativeCarApplyDirection
                    Direction,
                ibIfQoSAggregativeCarApplyRuleType
                    INTEGER,
                ibIfQoSAggregativeCarApplyRuleValue
                    Integer32,
                ibIfQoSAggregativeCarApplyCarIndex
                    Integer32,
                ibIfQoSAggregativeCarApplyRowStatus
                    RowStatus
            }

        ibIfQoSAggregativeCarApplyDirection OBJECT-TYPE
            SYNTAX Direction
            MAX-ACCESS not-accessible
            STATUS current
            DESCRIPTION
                "Direction."
            ::= { ibIfQoSAggregativeCarApplyEntry 1 }

        ibIfQoSAggregativeCarApplyRuleType OBJECT-TYPE
            SYNTAX INTEGER
            {
                ipv4acl(1),
                ipv6acl(2),
                carl(3),
                any(4)
            }
            MAX-ACCESS not-accessible
            STATUS current
            DESCRIPTION
                "The type of class rule."
            ::= { ibIfQoSAggregativeCarApplyEntry 2 }

        ibIfQoSAggregativeCarApplyRuleValue OBJECT-TYPE
            SYNTAX Integer32 (0..2147483647)
            MAX-ACCESS not-accessible
            STATUS current
            DESCRIPTION
                "The number of class rule.
                 ipv4acl : 2000..5999
                 ipv6acl : 2000..42767
                 carl : 1..199
                 other types: 0.
                "
            ::= { ibIfQoSAggregativeCarApplyEntry 3 }

        ibIfQoSAggregativeCarApplyCarIndex OBJECT-TYPE
            SYNTAX Integer32 (1..65534)
            MAX-ACCESS read-create
            STATUS current
            DESCRIPTION
                "The index of aggregative car."
            ::= { ibIfQoSAggregativeCarApplyEntry 4 }

        ibIfQoSAggregativeCarApplyRowStatus OBJECT-TYPE
            SYNTAX RowStatus
            MAX-ACCESS read-create
            STATUS current
            DESCRIPTION
                "RowStatus."
            ::= { ibIfQoSAggregativeCarApplyEntry 5 }
--
-- nodes of ibIfQoSAggregativeCarRunInfoTable
--
        ibIfQoSAggregativeCarRunInfoTable OBJECT-TYPE
            SYNTAX SEQUENCE OF IbIfQoSAggregativeCarRunInfoEntry
            MAX-ACCESS not-accessible
            STATUS current
            DESCRIPTION
                "A table of aggregative car statistic information."
            ::= { ibIfQoSAggregativeCarGroup 4 }

        ibIfQoSAggregativeCarRunInfoEntry OBJECT-TYPE
            SYNTAX IbIfQoSAggregativeCarRunInfoEntry
            MAX-ACCESS not-accessible
            STATUS current
            DESCRIPTION
                "Aggregative car statistic information."
            INDEX { ibIfQoSAggregativeCarIndex }
            ::= { ibIfQoSAggregativeCarRunInfoTable 1 }

        IbIfQoSAggregativeCarRunInfoEntry ::=
            SEQUENCE
            {
                ibIfQoSAggregativeCarGreenPackets
                    Counter64,
                ibIfQoSAggregativeCarGreenBytes
                    Counter64,
                ibIfQoSAggregativeCarYellowPackets
                    Counter64,
                ibIfQoSAggregativeCarYellowBytes
                    Counter64,
                ibIfQoSAggregativeCarRedPackets
                    Counter64,
                ibIfQoSAggregativeCarRedBytes
                    Counter64
            }

        ibIfQoSAggregativeCarGreenPackets OBJECT-TYPE
            SYNTAX Counter64
            MAX-ACCESS read-only
            STATUS current
            DESCRIPTION
                "Number of packets conforming CIR."
            ::= { ibIfQoSAggregativeCarRunInfoEntry 1 }

        ibIfQoSAggregativeCarGreenBytes OBJECT-TYPE
            SYNTAX Counter64
            MAX-ACCESS read-only
            STATUS current
            DESCRIPTION
                "Number of bytes conforming CIR"
            ::= { ibIfQoSAggregativeCarRunInfoEntry 2 }

        ibIfQoSAggregativeCarYellowPackets OBJECT-TYPE
            SYNTAX Counter64
            MAX-ACCESS read-only
            STATUS current
            DESCRIPTION
                "Number of yellow packets."
            ::= { ibIfQoSAggregativeCarRunInfoEntry 3 }

        ibIfQoSAggregativeCarYellowBytes  OBJECT-TYPE
            SYNTAX Counter64
            MAX-ACCESS read-only
            STATUS current
            DESCRIPTION
                "Number of yellow bytes."
            ::= { ibIfQoSAggregativeCarRunInfoEntry 4 }

        ibIfQoSAggregativeCarRedPackets OBJECT-TYPE
            SYNTAX Counter64
            MAX-ACCESS read-only
            STATUS current
            DESCRIPTION
                "Number of packets exceeding CIR."
            ::= { ibIfQoSAggregativeCarRunInfoEntry 5 }

        ibIfQoSAggregativeCarRedBytes OBJECT-TYPE
            SYNTAX Counter64
            MAX-ACCESS read-only
            STATUS current
            DESCRIPTION
                "Number of bytes exceeding CIR."
            ::= { ibIfQoSAggregativeCarRunInfoEntry 6 }

--
-- nodes of ibIfQoSTricolorCARGroup
--
        ibIfQoSTricolorCarGroup OBJECT IDENTIFIER ::= { ibIfQoSCARObjects 2 }
--
-- nodes of

        ibIfQoSTricolorCarConfigTable OBJECT-TYPE
            SYNTAX SEQUENCE OF IbIfQoSTricolorCarConfigEntry
            MAX-ACCESS not-accessible
            STATUS current
            DESCRIPTION
                "A table of tricolor car configuration information."
            ::= { ibIfQoSTricolorCarGroup 1 }

        ibIfQoSTricolorCarConfigEntry OBJECT-TYPE
            SYNTAX IbIfQoSTricolorCarConfigEntry
            MAX-ACCESS not-accessible
            STATUS current
            DESCRIPTION
                "Tricolor car configuration information entry."
            INDEX { ifIndex,
                    ibIfQoSTricolorCarDirection,
                    ibIfQoSTricolorCarType,
                    ibIfQoSTricolorCarValue
                  }
            ::= { ibIfQoSTricolorCarConfigTable 1 }

        IbIfQoSTricolorCarConfigEntry ::=
            SEQUENCE
            {
                ibIfQoSTricolorCarDirection
                    Direction,
                ibIfQoSTricolorCarType
                    INTEGER,
                ibIfQoSTricolorCarValue
                    Integer32,
                ibIfQoSTricolorCarCir
                    Unsigned32,
                ibIfQoSTricolorCarCbs
                    Unsigned32,
                ibIfQoSTricolorCarEbs
                    Unsigned32,
                ibIfQoSTricolorCarPir
                    Unsigned32,
                ibIfQoSTricolorCarGreenActionType
                    IbIfCarAction,
                ibIfQoSTricolorCarGreenActionValue
                    Integer32,
                ibIfQoSTricolorCarYellowActionType
                    IbIfCarAction,
                ibIfQoSTricolorCarYellowActionValue
                    Integer32,
                ibIfQoSTricolorCarRedActionType
                    IbIfCarAction,
                ibIfQoSTricolorCarRedActionValue
                    Integer32,
                ibIfQoSTricolorCarRowStatus
                    RowStatus,
                ibIfQoSTricolorCarUnitType
                    INTEGER
            }

        ibIfQoSTricolorCarDirection OBJECT-TYPE
            SYNTAX Direction
            MAX-ACCESS not-accessible
            STATUS current
            DESCRIPTION
                "Direction."
            ::= { ibIfQoSTricolorCarConfigEntry 1 }

        ibIfQoSTricolorCarType OBJECT-TYPE
            SYNTAX INTEGER
            {
                ipv4acl(1),
                ipv6acl(2),
                carl(3),
                any(4)
            }
            MAX-ACCESS not-accessible
            STATUS current
            DESCRIPTION
                "The index of the table, which is the matching type for the
                 packets on interface: ipv4acl, ipv6acl, carl, any."
            ::= { ibIfQoSTricolorCarConfigEntry 2 }

        ibIfQoSTricolorCarValue OBJECT-TYPE
            SYNTAX Integer32 (0..2147483647)
            MAX-ACCESS not-accessible
            STATUS current
            DESCRIPTION
                "The index of the table.
                 ipv4acl: the number is ipv4 acl number;
                 ipv6acl: the number is ipv6 acl number;
                 carl: the number is CARL number;
                 any: the number is 0;
                "
            ::= { ibIfQoSTricolorCarConfigEntry 3 }

        ibIfQoSTricolorCarCir OBJECT-TYPE
            SYNTAX Unsigned32
            MAX-ACCESS read-create
            STATUS current
            DESCRIPTION
                "Committed Information Rate.  The unit of this parameter depends
                on the ibIfQoSTricolorCarUnitType node.
                +-----------+----------+------------+
                | Unit type | absolute | percent    |
                +-----------+----------+------------+
                | CIR unit  | kbps     | percentage |
                +-----------+----------+------------+
                "
            ::= { ibIfQoSTricolorCarConfigEntry 4 }

        ibIfQoSTricolorCarCbs OBJECT-TYPE
            SYNTAX Unsigned32
            MAX-ACCESS read-create
            STATUS current
            DESCRIPTION
                "Committed Burst Size.  The unit of this parameter depends
                on the ibIfQoSTricolorCarUnitType node.
                +-----------+----------+--------------+
                | Unit type | absolute | percent      |
                +-----------+----------+--------------+
                | CBS unit  | bytes    | milliseconds |
                +-----------+----------+--------------+
                "
            ::= { ibIfQoSTricolorCarConfigEntry 5 }

        ibIfQoSTricolorCarEbs OBJECT-TYPE
            SYNTAX Unsigned32
            MAX-ACCESS read-create
            STATUS current
            DESCRIPTION
                "Excess Burst Size.  The unit of this parameter depends
                on the ibIfQoSTricolorCarUnitType node.
                +-----------+----------+--------------+
                | Unit type | absolute | percent      |
                +-----------+----------+--------------+
                | EBS unit  | bytes    | milliseconds |
                +-----------+----------+--------------+
                "
            ::= { ibIfQoSTricolorCarConfigEntry 6 }

        ibIfQoSTricolorCarPir OBJECT-TYPE
            SYNTAX Unsigned32
            MAX-ACCESS read-create
            STATUS current
            DESCRIPTION
                "Peak Information Rate.  The unit of this parameter depends
                on the ibIfQoSTricolorCarUnitType node.
                +-----------+----------+------------+
                | Unit type | absolute | percent    |
                +-----------+----------+------------+
                | PIR unit  | kbps     | percentage |
                +-----------+----------+------------+
                "
            DEFVAL { 4294967295 }
            ::= { ibIfQoSTricolorCarConfigEntry 7 }

        ibIfQoSTricolorCarGreenActionType OBJECT-TYPE
            SYNTAX IbIfCarAction
            MAX-ACCESS read-create
            STATUS current
            DESCRIPTION
                "Green Action."
            DEFVAL { pass }
            ::= { ibIfQoSTricolorCarConfigEntry 8 }

        ibIfQoSTricolorCarGreenActionValue OBJECT-TYPE
            SYNTAX Integer32 (0..63|255)
            MAX-ACCESS read-create
            STATUS current
            DESCRIPTION
                "The value is to remark when green action is remarking.
                 For remark-dscp-continue and remark-dscp-pass, the range is 0 to 63;
                 For remark-ip-continue and remark-ip-pass and
                 remark-mplsexp-continue and remark-mplsexp-pass and
                 remark-dot1p-continue and remark-dot1p-pass, the range is 0 to 7;
                 For remark-fr-de-continue and remark-fr-de-pass and
                 remark-atm-clp-continue and remark-atm-clp-pass, the range is 0 and 1.
                 255 is returned only when getting value from hardware QoS
                 or when action being pass, continue, discard of software QoS.
                 255 can't be set.
                "
            ::= { ibIfQoSTricolorCarConfigEntry 9 }

        ibIfQoSTricolorCarYellowActionType OBJECT-TYPE
            SYNTAX IbIfCarAction
            MAX-ACCESS read-create
            STATUS current
            DESCRIPTION
                "Yellow Action."
            DEFVAL { pass }
            ::= { ibIfQoSTricolorCarConfigEntry 10 }

        ibIfQoSTricolorCarYellowActionValue OBJECT-TYPE
            SYNTAX Integer32 (0..63|255)
            MAX-ACCESS read-create
            STATUS current
            DESCRIPTION
                "The value is to remark when yellow action is remarking.
                 For remark-dscp-continue and remark-dscp-pass, the range is 0 to 63;
                 For remark-ip-continue and remark-ip-pass and
                 remark-mplsexp-continue and remark-mplsexp-pass and
                 remark-dot1p-continue and remark-dot1p-pass, the range is 0 to 7;
                 For remark-fr-de-continue and remark-fr-de-pass and
                 remark-atm-clp-continue and remark-atm-clp-pass, the range is 0 and 1.
                 255 is returned only when getting value from hardware QoS
                 or when action being pass, continue, discard of software QoS.
                 255 can't be set.
                "
            ::= { ibIfQoSTricolorCarConfigEntry 11 }

        ibIfQoSTricolorCarRedActionType OBJECT-TYPE
            SYNTAX IbIfCarAction
            MAX-ACCESS read-create
            STATUS current
            DESCRIPTION
                "Red Action"
            DEFVAL { discard }
            ::= { ibIfQoSTricolorCarConfigEntry 12 }

        ibIfQoSTricolorCarRedActionValue OBJECT-TYPE
            SYNTAX Integer32 (0..63|255)
            MAX-ACCESS read-create
            STATUS current
            DESCRIPTION
                "The value is to remark when red action is remarking.
                 For remark-dscp-continue and remark-dscp-pass, the range is 0 to 63;
                 For remark-ip-continue and remark-ip-pass and
                 remark-mplsexp-continue and remark-mplsexp-pass and
                 remark-dot1p-continue and remark-dot1p-pass, the range is 0 to 7;
                 For remark-fr-de-continue and remark-fr-de-pass and
                 remark-atm-clp-continue and remark-atm-clp-pass, the range is 0 and 1.
                 255 is returned only when getting value from hardware QoS
                 or when action being pass, continue, discard of software QoS.
                 255 can't be set.
                "
            ::= { ibIfQoSTricolorCarConfigEntry 13 }

        ibIfQoSTricolorCarRowStatus OBJECT-TYPE
            SYNTAX RowStatus
            MAX-ACCESS read-create
            STATUS current
            DESCRIPTION
                "RowStatus."
            ::= { ibIfQoSTricolorCarConfigEntry 14 }

        ibIfQoSTricolorCarUnitType OBJECT-TYPE
            SYNTAX INTEGER
            {
                unitAbsolute(1),
                unitPercent(2)
            }
            MAX-ACCESS read-create
            STATUS current
            DESCRIPTION
                "Unit of token parameters.  If it is unitAbsolute, the token
                parameters are in kbps and bytes, and if it is unitPercent,
                the token parameters are in percentage and milliseconds."
            DEFVAL { unitAbsolute }
            ::= { ibIfQoSTricolorCarConfigEntry 15 }


--
-- nodes of ibIfQoSTricolorCarRunInfoTable
--
        ibIfQoSTricolorCarRunInfoTable OBJECT-TYPE
            SYNTAX SEQUENCE OF IbIfQoSTricolorCarRunInfoEntry
            MAX-ACCESS not-accessible
            STATUS current
            DESCRIPTION
                "A table of tricolor car statistic information."
            ::= { ibIfQoSTricolorCarGroup 2 }

        ibIfQoSTricolorCarRunInfoEntry OBJECT-TYPE
            SYNTAX IbIfQoSTricolorCarRunInfoEntry
            MAX-ACCESS not-accessible
            STATUS current
            DESCRIPTION
                "Tricolor car statistic information entry."
            INDEX { ifIndex,
                    ibIfQoSTricolorCarDirection,
                    ibIfQoSTricolorCarType,
                    ibIfQoSTricolorCarValue
                  }
            ::= { ibIfQoSTricolorCarRunInfoTable 1 }

        IbIfQoSTricolorCarRunInfoEntry ::=
            SEQUENCE
            {
                ibIfQoSTricolorCarGreenPackets
                    Counter64,
                ibIfQoSTricolorCarGreenBytes
                    Counter64,
                ibIfQoSTricolorCarYellowPackets
                    Counter64,
                ibIfQoSTricolorCarYellowBytes
                    Counter64,
                ibIfQoSTricolorCarRedPackets
                    Counter64,
                ibIfQoSTricolorCarRedBytes
                    Counter64
            }

        ibIfQoSTricolorCarGreenPackets OBJECT-TYPE
            SYNTAX Counter64
            MAX-ACCESS read-only
            STATUS current
            DESCRIPTION
                "The number of green packets."
            ::= { ibIfQoSTricolorCarRunInfoEntry 1 }

        ibIfQoSTricolorCarGreenBytes OBJECT-TYPE
            SYNTAX Counter64
            MAX-ACCESS read-only
            STATUS current
            DESCRIPTION
                "The number of green bytes."
            ::= { ibIfQoSTricolorCarRunInfoEntry 2 }

        ibIfQoSTricolorCarYellowPackets OBJECT-TYPE
            SYNTAX Counter64
            MAX-ACCESS read-only
            STATUS current
            DESCRIPTION
                "The number of yellow packets."
            ::= { ibIfQoSTricolorCarRunInfoEntry 3 }

        ibIfQoSTricolorCarYellowBytes OBJECT-TYPE
            SYNTAX Counter64
            MAX-ACCESS read-only
            STATUS current
            DESCRIPTION
                "The number of yellow bytes."
            ::= { ibIfQoSTricolorCarRunInfoEntry 4 }

        ibIfQoSTricolorCarRedPackets OBJECT-TYPE
            SYNTAX Counter64
            MAX-ACCESS read-only
            STATUS current
            DESCRIPTION
                "The number of red packets."
            ::= { ibIfQoSTricolorCarRunInfoEntry 5 }

        ibIfQoSTricolorCarRedBytes OBJECT-TYPE
            SYNTAX Counter64
            MAX-ACCESS read-only
            STATUS current
            DESCRIPTION
                "The number of red bytes."
            ::= { ibIfQoSTricolorCarRunInfoEntry 6 }
--
-- nodes of ibIfQoSGTSObject
--
        ibIfQoSGTSObjects OBJECT IDENTIFIER ::= { ibIfQos2 5 }

        ibIfQoSGTSConfigTable OBJECT-TYPE
            SYNTAX SEQUENCE OF IbIfQoSGTSConfigEntry
            MAX-ACCESS not-accessible
            STATUS current
            DESCRIPTION
                "A table of generic traffic shaping information."
            ::= { ibIfQoSGTSObjects 1 }

        ibIfQoSGTSConfigEntry OBJECT-TYPE
            SYNTAX IbIfQoSGTSConfigEntry
            MAX-ACCESS not-accessible
            STATUS current
            DESCRIPTION
                "Generic traffic shaping information entry."
            INDEX { ifIndex,
                    ibIfQoSGTSClassRuleType,
                    ibIfQoSGTSClassRuleValue
                  }
            ::= { ibIfQoSGTSConfigTable 1 }

        IbIfQoSGTSConfigEntry ::=
            SEQUENCE
            {
                ibIfQoSGTSClassRuleType
                    INTEGER,
                ibIfQoSGTSClassRuleValue
                    Integer32,
                ibIfQoSGTSCir
                    Unsigned32,
                ibIfQoSGTSCbs
                    Unsigned32,
                ibIfQoSGTSEbs
                    Unsigned32,
                ibIfQoSGTSQueueLength
                    Integer32,
                ibIfQoSGTSConfigRowStatus
                    RowStatus,
                ibIfQoSGTSPir
                    Unsigned32,
                ibIfQoSGTSUnitType
                    INTEGER
            }

        ibIfQoSGTSClassRuleType OBJECT-TYPE
            SYNTAX INTEGER
            {
                any(1),
                ipv4acl(2),
                ipv6acl(3),
                queue(4)
            }

            MAX-ACCESS not-accessible
            STATUS current
            DESCRIPTION
                "The index of the table,
                 which is the matching type for the packets on interface:
                 ipv4acl, ipv6acl, any, queue.
                "
            ::= { ibIfQoSGTSConfigEntry 1 }

        ibIfQoSGTSClassRuleValue OBJECT-TYPE
            SYNTAX Integer32 (0..2147483647)
            MAX-ACCESS not-accessible
            STATUS current
            DESCRIPTION
                "Value of type.
                 ipv4acl : 2000..5999
                 ipv6acl : 2000..42767
                 any : 0
                 queue : 0..7
                 "
            ::= { ibIfQoSGTSConfigEntry 2 }

        ibIfQoSGTSCir OBJECT-TYPE
            SYNTAX Unsigned32
            MAX-ACCESS read-create
            STATUS current
            DESCRIPTION
                "Committed Information Rate.  The unit of this parameter depends
                on the ibIfQoSGTSUnitType node.
                +-----------+----------+------------+
                | Unit type | absolute | percent    |
                +-----------+----------+------------+
                | CIR unit  | kbps     | percentage |
                +-----------+----------+------------+
                "
            ::= { ibIfQoSGTSConfigEntry 3 }

        ibIfQoSGTSCbs OBJECT-TYPE
            SYNTAX Unsigned32
            MAX-ACCESS read-create
            STATUS current
            DESCRIPTION
                "Committed Burst Size.  The unit of this parameter depends
                on the ibIfQoSGTSUnitType node.
                +-----------+----------+--------------+
                | Unit type | absolute | percent      |
                +-----------+----------+--------------+
                | CBS unit  | bytes    | milliseconds |
                +-----------+----------+--------------+
                "
            ::= { ibIfQoSGTSConfigEntry 4 }

        ibIfQoSGTSEbs OBJECT-TYPE
            SYNTAX Unsigned32
            MAX-ACCESS read-create
            STATUS current
            DESCRIPTION
                "Excess Burst Size.  The unit of this parameter depends
                on the ibIfQoSGTSUnitType node.
                +-----------+----------+--------------+
                | Unit type | absolute | percent      |
                +-----------+----------+--------------+
                | EBS unit  | bytes    | milliseconds |
                +-----------+----------+--------------+
                "
            ::= { ibIfQoSGTSConfigEntry 5 }

        ibIfQoSGTSQueueLength OBJECT-TYPE
            SYNTAX Integer32
            MAX-ACCESS read-create
            STATUS current
            DESCRIPTION
                "The length of queue."
            ::= { ibIfQoSGTSConfigEntry 6 }

        ibIfQoSGTSConfigRowStatus OBJECT-TYPE
            SYNTAX RowStatus
            MAX-ACCESS read-create
            STATUS current
            DESCRIPTION
                "RowStatus."
            ::= { ibIfQoSGTSConfigEntry 7 }

        ibIfQoSGTSPir OBJECT-TYPE
            SYNTAX Unsigned32
            MAX-ACCESS read-create
            STATUS current
            DESCRIPTION
                "Peak information rate.  The unit of this parameter depends
                on the ibIfQoSGTSUnitType node.
                +-----------+----------+------------+
                | Unit type | absolute | percent    |
                +-----------+----------+------------+
                | PIR unit  | kbps     | percentage |
                +-----------+----------+------------+
                "
            DEFVAL { 4294967295 }
            ::= { ibIfQoSGTSConfigEntry 8 }

        ibIfQoSGTSUnitType OBJECT-TYPE
            SYNTAX INTEGER
            {
                unitAbsolute(1),
                unitPercent(2)
            }
            MAX-ACCESS read-create
            STATUS current
            DESCRIPTION
                "Unit of token parameters.  If it is unitAbsolute, the token
                parameters are in kbps and bytes, and if it is unitPercent,
                the token parameters are in percentage and milliseconds."
            DEFVAL { unitAbsolute }
            ::= { ibIfQoSGTSConfigEntry 9 }

--
-- nodes of ibIfQoSGTSRunInfoTable
--
        ibIfQoSGTSRunInfoTable OBJECT-TYPE
            SYNTAX SEQUENCE OF IbIfQoSGTSRunInfoEntry
            MAX-ACCESS not-accessible
            STATUS current
            DESCRIPTION
                "A table of  generic traffic shaping's statistic information."
            ::= { ibIfQoSGTSObjects 2 }

        ibIfQoSGTSRunInfoEntry OBJECT-TYPE
            SYNTAX IbIfQoSGTSRunInfoEntry
            MAX-ACCESS not-accessible
            STATUS current
            DESCRIPTION
                "Generic traffic shaping's statistic information entry."
            INDEX { ifIndex,
                    ibIfQoSGTSClassRuleType,
                    ibIfQoSGTSClassRuleValue
                  }
            ::= { ibIfQoSGTSRunInfoTable 1 }

        IbIfQoSGTSRunInfoEntry ::=
            SEQUENCE
            {
                ibIfQoSGTSQueueSize
                    Integer32,
                ibIfQoSGTSPassedPackets
                    Counter64,
                ibIfQoSGTSPassedBytes
                    Counter64,
                ibIfQoSGTSDiscardPackets
                    Counter64,
                ibIfQoSGTSDiscardBytes
                    Counter64,
                ibIfQoSGTSDelayedPackets
                    Counter64,
                ibIfQoSGTSDelayedBytes
                    Counter64
            }

        ibIfQoSGTSQueueSize OBJECT-TYPE
            SYNTAX Integer32
            MAX-ACCESS read-only
            STATUS current
            DESCRIPTION
                "The number of packets in the queue."
            ::= { ibIfQoSGTSRunInfoEntry 1 }

        ibIfQoSGTSPassedPackets OBJECT-TYPE
            SYNTAX Counter64
            MAX-ACCESS read-only
            STATUS current
            DESCRIPTION
                "The number of passed packets."
            ::= { ibIfQoSGTSRunInfoEntry 2 }

        ibIfQoSGTSPassedBytes OBJECT-TYPE
            SYNTAX Counter64
            MAX-ACCESS read-only
            STATUS current
            DESCRIPTION
                "The number of passed bytes."
            ::= { ibIfQoSGTSRunInfoEntry 3 }

        ibIfQoSGTSDiscardPackets OBJECT-TYPE
            SYNTAX Counter64
            MAX-ACCESS read-only
            STATUS current
            DESCRIPTION
                "The number of discard packets."
            ::= { ibIfQoSGTSRunInfoEntry 4 }

        ibIfQoSGTSDiscardBytes OBJECT-TYPE
            SYNTAX Counter64
            MAX-ACCESS read-only
            STATUS current
            DESCRIPTION
                "The number of discard bytes."
            ::= { ibIfQoSGTSRunInfoEntry 5 }

        ibIfQoSGTSDelayedPackets OBJECT-TYPE
            SYNTAX Counter64
            MAX-ACCESS read-only
            STATUS current
            DESCRIPTION
                "The number of delayed packets."
            ::= { ibIfQoSGTSRunInfoEntry 6 }

        ibIfQoSGTSDelayedBytes OBJECT-TYPE
            SYNTAX Counter64
            MAX-ACCESS read-only
            STATUS current
            DESCRIPTION
                "The number of delayed bytes."
            ::= { ibIfQoSGTSRunInfoEntry 7 }
--
-- nodes of ibIfQoSWREDObject
--
        ibIfQoSWREDObjects OBJECT IDENTIFIER ::= { ibIfQos2 6 }
--
-- nodes of WRED group
--
        ibIfQoSWredGroupGroup OBJECT IDENTIFIER ::= { ibIfQoSWREDObjects 1 }

        ibIfQoSWredGroupNextIndex OBJECT-TYPE
            SYNTAX Integer32
            MAX-ACCESS read-only
            STATUS current
            DESCRIPTION
                "This object contains an appropriate value to be used for ibIfQoSWredGroupIndex
                 when creating rows in the ibIfQoSWredGroupTable.
                 Begin with 0.
                "
            ::= { ibIfQoSWredGroupGroup 1 }
--
-- nodes of ibIfQoSWredGroupTable
--
        ibIfQoSWredGroupTable OBJECT-TYPE
            SYNTAX SEQUENCE OF IbIfQoSWredGroupEntry
            MAX-ACCESS not-accessible
            STATUS current
            DESCRIPTION
                "A table of WRED group information."
            ::= { ibIfQoSWredGroupGroup 2 }

        ibIfQoSWredGroupEntry OBJECT-TYPE
            SYNTAX IbIfQoSWredGroupEntry
            MAX-ACCESS not-accessible
            STATUS current
            DESCRIPTION
                "WRED group information."
            INDEX { ibIfQoSWredGroupIndex }
            ::= { ibIfQoSWredGroupTable 1 }

        IbIfQoSWredGroupEntry ::=
            SEQUENCE
            {
                ibIfQoSWredGroupIndex
                    Integer32,
                ibIfQoSWredGroupName
                    OCTET STRING,
                ibIfQoSWredGroupType
                    INTEGER,
                ibIfQoSWredGroupWeightingConstant
                    Integer32,
                ibIfQoSWredGroupRowStatus
                    RowStatus
            }

        ibIfQoSWredGroupIndex OBJECT-TYPE
            SYNTAX Integer32 (0..256)
            MAX-ACCESS not-accessible
            STATUS current
            DESCRIPTION
                "WRED group index."
            ::= { ibIfQoSWredGroupEntry 1 }

        ibIfQoSWredGroupName OBJECT-TYPE
            SYNTAX OCTET STRING (SIZE(1..32))
            MAX-ACCESS read-create
            STATUS current
            DESCRIPTION
                "WRED group name."
            ::= { ibIfQoSWredGroupEntry 2 }

        ibIfQoSWredGroupType OBJECT-TYPE
            SYNTAX INTEGER
            {
                userdefined(0),
                dot1p(1),
                ippre(2),
                dscp(3),
                localpre(4),
                atmclp(5),
                frde(6),
                exp(7),
                queue(8),
                dropLevel(9)
            }
            MAX-ACCESS read-create
            STATUS current
            DESCRIPTION
                "Type of WRED group."
            ::= { ibIfQoSWredGroupEntry 3 }

        ibIfQoSWredGroupWeightingConstant OBJECT-TYPE
            SYNTAX Integer32 (1..15)
            MAX-ACCESS read-create
            STATUS current
            DESCRIPTION
                "Exponent for WRED calculates the average length of queue.
                 If 'ibIfQoSWredGroupType' is 'queue', the object is ineffective.
                 So, it must use the object, which is 'ibIfQoSWredGroupExponent' of
                 ibIfQoSWredGroupContentTable, to indicate the exponent of
                 each queue of the queue WRED group."
            DEFVAL { 9 }
            ::= { ibIfQoSWredGroupEntry 4 }

        ibIfQoSWredGroupRowStatus OBJECT-TYPE
            SYNTAX RowStatus
            MAX-ACCESS read-create
            STATUS current
            DESCRIPTION
                "RowStatus."
            ::= { ibIfQoSWredGroupEntry 6 }

--
-- nodes of ibIfQoSWredGroupContentTable
--
        ibIfQoSWredGroupContentTable OBJECT-TYPE
            SYNTAX SEQUENCE OF IbIfQoSWredGroupContentEntry
            MAX-ACCESS not-accessible
            STATUS current
            DESCRIPTION
                "A table of priority WRED information."
            ::= { ibIfQoSWredGroupGroup 3 }

        ibIfQoSWredGroupContentEntry OBJECT-TYPE
            SYNTAX IbIfQoSWredGroupContentEntry
            MAX-ACCESS not-accessible
            STATUS current
            DESCRIPTION
                "Priority WRED information entry."
            INDEX { ibIfQoSWredGroupIndex,
                    ibIfQoSWredGroupContentIndex,
                    ibIfQoSWredGroupContentSubIndex  }
            ::= { ibIfQoSWredGroupContentTable 1 }

        IbIfQoSWredGroupContentEntry ::=
            SEQUENCE
            {
                ibIfQoSWredGroupContentIndex
                    Integer32,
                ibIfQoSWredGroupContentSubIndex
                    Integer32,
                ibIfQoSWredLowLimit
                    Integer32,
                ibIfQoSWredHighLimit
                    Integer32,
                ibIfQoSWredDiscardProb
                    Integer32,
                ibIfQoSWredGroupExponent
                    Integer32,
                ibIfQoSWredRowStatus
                    RowStatus
            }

        ibIfQoSWredGroupContentIndex OBJECT-TYPE
            SYNTAX Integer32 (0..63)
            MAX-ACCESS not-accessible
            STATUS current
            DESCRIPTION
                "The priority of a packet.
                 Different type of packet has different priority.
                 Type of priority    Range of priority
                 dot1p              0..7
                 ippre              0..7
                 dscp               0..63
                 atmclp             0..1
                 frde               0..1
                 exp                0..7
                 queue              0..7 ( defined by product )
                 dropLevel          0..2
                 "
            ::= { ibIfQoSWredGroupContentEntry 1 }

        ibIfQoSWredGroupContentSubIndex OBJECT-TYPE
            SYNTAX Integer32 (0..63)
            MAX-ACCESS not-accessible
            STATUS current
            DESCRIPTION
                "The sub index.
                 Different type of packet has different value.
                 Type of priority    Range of value
                 queue              0..2
                 other types : 0
                 "
            ::= { ibIfQoSWredGroupContentEntry 2 }

        ibIfQoSWredLowLimit OBJECT-TYPE
            SYNTAX Integer32
            MAX-ACCESS read-create
            STATUS current
            DESCRIPTION
                "Discard low limit."
            ::= { ibIfQoSWredGroupContentEntry 3 }

        ibIfQoSWredHighLimit OBJECT-TYPE
            SYNTAX Integer32
            MAX-ACCESS read-create
            STATUS current
            DESCRIPTION
                "Discard high limit."
            ::= { ibIfQoSWredGroupContentEntry 4 }

        ibIfQoSWredDiscardProb OBJECT-TYPE
            SYNTAX Integer32
            MAX-ACCESS read-create
            STATUS current
            DESCRIPTION
                "Discard probability."
            ::= { ibIfQoSWredGroupContentEntry 5 }

        ibIfQoSWredGroupExponent OBJECT-TYPE
            SYNTAX Integer32 (0..15)
            MAX-ACCESS read-create
            STATUS current
            DESCRIPTION
                "Exponent for WRED calculates the average length of queue.
                 Only 'ibIfQoSWredGroupType' is 'queue', the object is effective.
                 This object is designed to indicate the exponent of
                 each queue of the queue WRED group.
                "
            DEFVAL { 9 }
            ::= { ibIfQoSWredGroupContentEntry 6 }

        ibIfQoSWredRowStatus OBJECT-TYPE
            SYNTAX RowStatus
            MAX-ACCESS read-create
            STATUS current
            DESCRIPTION
                "RowStatus."
            ::= { ibIfQoSWredGroupContentEntry 7 }
--
-- nodes of ibIfQoSWredApplyIfTable
--
        ibIfQoSWredGroupApplyIfTable OBJECT-TYPE
            SYNTAX SEQUENCE OF IbIfQoSWredGroupApplyIfEntry
            MAX-ACCESS not-accessible
            STATUS current
            DESCRIPTION
                "A table of WRED group applied interface information."
            ::= { ibIfQoSWredGroupGroup 4 }

        ibIfQoSWredGroupApplyIfEntry OBJECT-TYPE
            SYNTAX IbIfQoSWredGroupApplyIfEntry
            MAX-ACCESS not-accessible
            STATUS current
            DESCRIPTION
                "WRED group applied interface information."
            INDEX { ifIndex }
            ::= { ibIfQoSWredGroupApplyIfTable 1 }

        IbIfQoSWredGroupApplyIfEntry ::=
            SEQUENCE
            {
                ibIfQoSWredGroupApplyIndex
                    Integer32,
                ibIfQoSWredGroupApplyName
                    OCTET STRING,
                ibIfQoSWredGroupIfRowStatus
                    RowStatus
            }

        ibIfQoSWredGroupApplyIndex OBJECT-TYPE
            SYNTAX Integer32 (0..256)
            MAX-ACCESS read-create
            STATUS current
            DESCRIPTION
                "WRED group index."
            ::= { ibIfQoSWredGroupApplyIfEntry 1 }

        ibIfQoSWredGroupApplyName OBJECT-TYPE
            SYNTAX OCTET STRING (SIZE(1..32))
            MAX-ACCESS read-only
            STATUS current
            DESCRIPTION
                "WRED group name."
            ::= { ibIfQoSWredGroupApplyIfEntry 2 }

        ibIfQoSWredGroupIfRowStatus OBJECT-TYPE
            SYNTAX RowStatus
            MAX-ACCESS read-create
            STATUS current
            DESCRIPTION
                "RowStatus."
            ::= { ibIfQoSWredGroupApplyIfEntry 3 }
--
-- nodes of ibIfQoSWredApplyIfStatisticTable
--
        ibIfQoSWredApplyIfRunInfoTable OBJECT-TYPE
            SYNTAX SEQUENCE OF IbIfQoSWredApplyIfRunInfoEntry
            MAX-ACCESS not-accessible
            STATUS current
            DESCRIPTION
                "A table of WRED statistic information."
            ::= { ibIfQoSWredGroupGroup 5 }

        ibIfQoSWredApplyIfRunInfoEntry  OBJECT-TYPE
            SYNTAX IbIfQoSWredApplyIfRunInfoEntry
            MAX-ACCESS not-accessible
            STATUS current
            DESCRIPTION
                "WRED statistic information."
            INDEX { ifIndex,
                    ibIfQoSWredGroupIndex,
                    ibIfQoSWredGroupContentIndex,
                    ibIfQoSWredGroupContentSubIndex
                  }
            ::= { ibIfQoSWredApplyIfRunInfoTable 1 }

        IbIfQoSWredApplyIfRunInfoEntry ::=
            SEQUENCE
            {
                ibIfQoSWredPreRandomDropNum
                    Counter64,
                ibIfQoSWredPreTailDropNum
                    Counter64
            }

        ibIfQoSWredPreRandomDropNum OBJECT-TYPE
            SYNTAX Counter64
            MAX-ACCESS read-only
            STATUS current
            DESCRIPTION
                "The number of random drop."
            ::= { ibIfQoSWredApplyIfRunInfoEntry 1 }

        ibIfQoSWredPreTailDropNum OBJECT-TYPE
            SYNTAX Counter64
            MAX-ACCESS read-only
            STATUS current
            DESCRIPTION
                "The number of tail drop."
            ::= { ibIfQoSWredApplyIfRunInfoEntry 2 }
--
-- nodes of ibIfQoSPortWREDGroup
--
        ibIfQoSPortWredGroup OBJECT IDENTIFIER ::= { ibIfQoSWREDObjects 2 }

        ibIfQoSPortWredWeightConstantTable OBJECT-TYPE
            SYNTAX SEQUENCE OF IbIfQoSPortWREDWeightConstantEntry
            MAX-ACCESS not-accessible
            STATUS current
            DESCRIPTION
                "A table of port WRED configuration information."
            ::= { ibIfQoSPortWredGroup 1 }

        ibIfQoSPortWredWeightConstantEntry OBJECT-TYPE
            SYNTAX IbIfQoSPortWREDWeightConstantEntry
            MAX-ACCESS not-accessible
            STATUS current
            DESCRIPTION
                "Port WRED configuration information entry."
            INDEX { ifIndex }
            ::= { ibIfQoSPortWredWeightConstantTable 1 }

        IbIfQoSPortWREDWeightConstantEntry ::=
            SEQUENCE
            {
                ibIfQoSPortWredEnable
                    TruthValue,
                ibIfQoSPortWredWeightConstant
                    Integer32,
                ibIfQoSPortWredWeightConstantRowStatus
                    RowStatus
            }

        ibIfQoSPortWredEnable OBJECT-TYPE
            SYNTAX TruthValue
            MAX-ACCESS read-create
            STATUS current
            DESCRIPTION
                "The object is used to enable or disable WRED function of the port.
                 true: Enable WRED function of a port.
                 false: Disable WRED function of a port.
                "
            ::= { ibIfQoSPortWredWeightConstantEntry 1 }

        ibIfQoSPortWredWeightConstant OBJECT-TYPE
            SYNTAX Integer32 (1..16)
            MAX-ACCESS read-create
            STATUS current
            DESCRIPTION
                "Weight constant."
            ::= { ibIfQoSPortWredWeightConstantEntry 2 }

        ibIfQoSPortWredWeightConstantRowStatus OBJECT-TYPE
            SYNTAX RowStatus
            MAX-ACCESS read-create
            STATUS current
            DESCRIPTION
                "RowStatus."
            ::= { ibIfQoSPortWredWeightConstantEntry 3 }
--
-- notes of ibIfQoSPortWredPreConfigTable
--
        ibIfQoSPortWredPreConfigTable OBJECT-TYPE
            SYNTAX SEQUENCE OF IbIfQoSPortWREDPreConfigEntry
            MAX-ACCESS not-accessible
            STATUS current
            DESCRIPTION
                "A table of weighted random early detect precedence configuration information."
            ::= { ibIfQoSPortWredGroup 2 }

        ibIfQoSPortWredPreConfigEntry OBJECT-TYPE
            SYNTAX IbIfQoSPortWREDPreConfigEntry
            MAX-ACCESS not-accessible
            STATUS current
            DESCRIPTION
                "Weighted random early detect precedence configuration information entry."
            INDEX { ifIndex, ibIfQoSPortWredPreID }
            ::= { ibIfQoSPortWredPreConfigTable 1 }

        IbIfQoSPortWREDPreConfigEntry ::=
            SEQUENCE
            {
                ibIfQoSPortWredPreID
                    Integer32,
                ibIfQoSPortWredPreLowLimit
                    Integer32,
                ibIfQoSPortWredPreHighLimit
                    Integer32,
                ibIfQoSPortWredPreDiscardProbability
                    Integer32,
                ibIfQoSPortWredPreRowStatus
                    RowStatus
            }

        ibIfQoSPortWredPreID OBJECT-TYPE
            SYNTAX Integer32
            MAX-ACCESS not-accessible
            STATUS current
            DESCRIPTION
                "IP precedence, from 0 to 7."
            ::= { ibIfQoSPortWredPreConfigEntry 1 }

        ibIfQoSPortWredPreLowLimit OBJECT-TYPE
            SYNTAX Integer32
            MAX-ACCESS read-create
            STATUS current
            DESCRIPTION
                "Low Limit(number of packets)"
            ::= { ibIfQoSPortWredPreConfigEntry 2 }

        ibIfQoSPortWredPreHighLimit OBJECT-TYPE
            SYNTAX Integer32
            MAX-ACCESS read-create
            STATUS current
            DESCRIPTION
                "High limit(number of packets)"
            ::= { ibIfQoSPortWredPreConfigEntry 3 }

        ibIfQoSPortWredPreDiscardProbability OBJECT-TYPE
            SYNTAX Integer32
            MAX-ACCESS read-create
            STATUS current
            DESCRIPTION
                "Discard probability denominator"
            ::= { ibIfQoSPortWredPreConfigEntry 4 }

        ibIfQoSPortWredPreRowStatus OBJECT-TYPE
            SYNTAX RowStatus
            MAX-ACCESS read-create
            STATUS current
            DESCRIPTION
                "RowStatus."
            ::= { ibIfQoSPortWredPreConfigEntry 5 }

--
-- nodes of ibIfQoSPortWredRunInfoTable
--
        ibIfQoSPortWredRunInfoTable OBJECT-TYPE
            SYNTAX SEQUENCE OF IbIfQoSPortWREDRunInfoEntry
            MAX-ACCESS not-accessible
            STATUS current
            DESCRIPTION
                "A table of WRED statistic information."
            ::= { ibIfQoSPortWredGroup 3 }

        ibIfQoSPortWredRunInfoEntry OBJECT-TYPE
            SYNTAX IbIfQoSPortWREDRunInfoEntry
            MAX-ACCESS not-accessible
            STATUS current
            DESCRIPTION
                "WRED statistic information entry."
            INDEX { ifIndex, ibIfQoSPortWredPreID }
            ::= { ibIfQoSPortWredRunInfoTable 1 }

        IbIfQoSPortWREDRunInfoEntry ::=
            SEQUENCE
            {
                ibIfQoSWREDTailDropNum
                    Counter64,
                ibIfQoSWREDRandomDropNum
                    Counter64
            }

        ibIfQoSWREDTailDropNum OBJECT-TYPE
            SYNTAX Counter64
            MAX-ACCESS read-only
            STATUS current
            DESCRIPTION
                "The number of tail drop."
            ::= { ibIfQoSPortWredRunInfoEntry 1 }

        ibIfQoSWREDRandomDropNum OBJECT-TYPE
            SYNTAX Counter64
            MAX-ACCESS read-only
            STATUS current
            DESCRIPTION
                "The number of random drop."
            ::= { ibIfQoSPortWredRunInfoEntry 2 }

--
-- nodes of ibIfQoSPortPriorityObject
--

        ibIfQoSPortPriorityObjects OBJECT IDENTIFIER ::= { ibIfQos2 7 }

        ibIfQoSPortPriorityConfigGroup OBJECT IDENTIFIER ::= { ibIfQoSPortPriorityObjects 1 }

        ibIfQoSPortPriorityTable OBJECT-TYPE
            SYNTAX SEQUENCE OF IbIfQoSPortPriorityEntry
            MAX-ACCESS not-accessible
            STATUS current
            DESCRIPTION
                "A table of port priority information."
            ::= { ibIfQoSPortPriorityConfigGroup 1 }

        ibIfQoSPortPriorityEntry OBJECT-TYPE
            SYNTAX IbIfQoSPortPriorityEntry
            MAX-ACCESS not-accessible
            STATUS current
            DESCRIPTION
                "Port priority information entry."
            INDEX { ifIndex }
            ::= { ibIfQoSPortPriorityTable 1 }

        IbIfQoSPortPriorityEntry    ::=
            SEQUENCE
            {
                ibIfQoSPortPriorityValue
                    Integer32
            }

        ibIfQoSPortPriorityValue OBJECT-TYPE
            SYNTAX Integer32 (0..7)
            MAX-ACCESS read-write
            STATUS current
            DESCRIPTION
                "The priority of a port."
            DEFVAL { 0 }
            ::= { ibIfQoSPortPriorityEntry 1 }
--
-- nodes of ibIfQoSPortPirorityTrustTable
--
        ibIfQoSPortPirorityTrustTable OBJECT-TYPE
            SYNTAX SEQUENCE OF IbIfQoSPortPirorityTrustEntry
            MAX-ACCESS not-accessible
            STATUS current
            DESCRIPTION
                "A table of each port's trusted priority information."
            ::= { ibIfQoSPortPriorityConfigGroup 2 }

        ibIfQoSPortPirorityTrustEntry OBJECT-TYPE
            SYNTAX IbIfQoSPortPirorityTrustEntry
            MAX-ACCESS not-accessible
            STATUS current
            DESCRIPTION
                "Per-port trusted priority information entry."
            INDEX { ifIndex }
            ::= { ibIfQoSPortPirorityTrustTable 1 }

        IbIfQoSPortPirorityTrustEntry ::=
            SEQUENCE
            {
                ibIfQoSPortPriorityTrustTrustType
                    INTEGER,
                ibIfQoSPortPriorityTrustOvercastType
                    INTEGER
            }

        ibIfQoSPortPriorityTrustTrustType OBJECT-TYPE
            SYNTAX INTEGER
            {
                untrust(1),
                dot1p(2),
                dscp(3),
                exp(4),
                ipPrecedence(5),
                dot11e(6),
                auto(7)
            }
            MAX-ACCESS read-write
            STATUS current
            DESCRIPTION
                "Trusted priority type of a port."
            DEFVAL { untrust }
            ::= { ibIfQoSPortPirorityTrustEntry 1 }

        ibIfQoSPortPriorityTrustOvercastType OBJECT-TYPE
            SYNTAX INTEGER
            {
                noOvercast(1),
                overcastDSCP(2),
                overcastCOS(3),
                overcast(4)
            }
            MAX-ACCESS read-write
            STATUS current
            DESCRIPTION
                "The overcast type."
            DEFVAL { noOvercast }
            ::= { ibIfQoSPortPirorityTrustEntry 2 }
--
-- nodes of map object
--
        ibIfQoSMapObjects OBJECT IDENTIFIER ::= { ibIfQos2 9 }
--
-- nodes of ibIfQoSMapConfigGroup
--
        ibIfQoSPriMapConfigGroup OBJECT IDENTIFIER ::= { ibIfQoSMapObjects 1 }

        ibIfQoSPriMapGroupNextIndex OBJECT-TYPE
            SYNTAX Integer32
            MAX-ACCESS read-only
            STATUS current
            DESCRIPTION
                "This object contains an appropriate value to be used for ibIfQoSPriMapGroupIndex
                 when creating rows in the ibIfQoSPriMapGroupTable.
                 Begin with 64.
                "
            ::= { ibIfQoSPriMapConfigGroup 1 }
--
-- nodes of ibIfQoSPriMapConfigTable
--
        ibIfQoSPriMapGroupTable OBJECT-TYPE
            SYNTAX SEQUENCE OF IbIfQoSPriMapGroupEntry
            MAX-ACCESS not-accessible
            STATUS current
            DESCRIPTION
                "A table of map group information."
            ::= { ibIfQoSPriMapConfigGroup 2 }

        ibIfQoSPriMapGroupEntry OBJECT-TYPE
            SYNTAX IbIfQoSPriMapGroupEntry
            MAX-ACCESS not-accessible
            STATUS current
            DESCRIPTION
                "Map group information entry."
            INDEX { ibIfQoSPriMapGroupIndex  }
            ::= { ibIfQoSPriMapGroupTable 1 }

        IbIfQoSPriMapGroupEntry ::=
            SEQUENCE
            {
                ibIfQoSPriMapGroupIndex
                    Integer32,
                ibIfQoSPriMapGroupType
                    INTEGER,
                ibIfQoSPriMapGroupName
                    OCTET STRING,
                ibIfQoSPriMapGroupRowStatus
                    RowStatus
            }

        ibIfQoSPriMapGroupIndex OBJECT-TYPE
            SYNTAX Integer32
            MAX-ACCESS not-accessible
            STATUS current
            DESCRIPTION
                "The index of map, which are defined by system and user.
                 The index of system defined map is 1 to 9.
                 System defined map-name/map-index pairs like this:
                 Map-index    Map-name
                 1            dot1p-dp
                 2            dot1p-dscp
                 3            dot1p-lp
                 4            dscp-dot1p
                 5            dscp-dp
                 6            dscp-dscp
                 7            dscp-lp
                 8            exp-dp
                 9            exp-lp
                "
            ::= { ibIfQoSPriMapGroupEntry 1 }

        ibIfQoSPriMapGroupType OBJECT-TYPE
            SYNTAX INTEGER
            {
                userdefined(1),
                dot1p-dp(2),
                dot1p-dscp(3),
                dot1p-lp(4),
                dscp-dot1p(5),
                dscp-dp(6),
                dscp-dscp(7),
                dscp-lp(8),
                exp-dp(9),
                exp-lp(10)
            }
            MAX-ACCESS read-create
            STATUS current
            DESCRIPTION
                "The type of map group."
            ::= { ibIfQoSPriMapGroupEntry 2 }

        ibIfQoSPriMapGroupName OBJECT-TYPE
            SYNTAX OCTET STRING (SIZE(1..32))
            MAX-ACCESS read-create
            STATUS current
            DESCRIPTION
                "The name of map group."
            ::= { ibIfQoSPriMapGroupEntry 3 }

        ibIfQoSPriMapGroupRowStatus OBJECT-TYPE
            SYNTAX RowStatus
            MAX-ACCESS read-create
            STATUS current
            DESCRIPTION
                "RowStatus."
            ::= { ibIfQoSPriMapGroupEntry 4 }

--
-- nodes of ibIfQoSPriMapContentTable
--
        ibIfQoSPriMapContentTable OBJECT-TYPE
            SYNTAX SEQUENCE OF IbIfQoSPriMapContentEntry
            MAX-ACCESS not-accessible
            STATUS current
            DESCRIPTION
                "A table of priority map configuration information."
            ::= { ibIfQoSPriMapConfigGroup 3 }

        ibIfQoSPriMapContentEntry OBJECT-TYPE
            SYNTAX IbIfQoSPriMapContentEntry
            MAX-ACCESS not-accessible
            STATUS current
            DESCRIPTION
                "Priority map configuration information entry."
            INDEX { ibIfQoSPriMapGroupIndex, ibIfQoSPriMapGroupImportValue }
            ::= { ibIfQoSPriMapContentTable 1 }

        IbIfQoSPriMapContentEntry ::=
            SEQUENCE
            {
                ibIfQoSPriMapGroupImportValue
                    Integer32,
                ibIfQoSPriMapGroupExportValue
                    Integer32,
                ibIfQoSPriMapContentRowStatus
                    RowStatus
            }

        ibIfQoSPriMapGroupImportValue OBJECT-TYPE
            SYNTAX Integer32 (0..63)
            MAX-ACCESS not-accessible
            STATUS current
            DESCRIPTION
                "Priority map table import value list.
                 Different map has different ibIfQoSPriMapConfigImportValue.
                 Map-name       Range of ibIfQoSPriMapConfigImportValue
                 dot1p-dp       (0..7)
                 dot1p-dscp     (0..7)
                 dot1p-lp       (0..7)
                 dscp-dot1p     (0..63)
                 dscp-dp        (0..63)
                 dscp-dscp      (0..63)
                 dscp-lp(7)     (0..63)
                 exp-dp(8)      (0..7)
                 exp-lp         (0..7)
                "
            ::= { ibIfQoSPriMapContentEntry 1 }

        ibIfQoSPriMapGroupExportValue OBJECT-TYPE
            SYNTAX Integer32 (0..63)
            MAX-ACCESS read-create
            STATUS current
            DESCRIPTION
                "Priority map table output.
                 Different map has different ibIfQoSPriMapGroupExportValue.
                 dot1p-dp:   0..7
                 dot1p-dscp: 0..63
                 dot1p-lp:   0..7
                 dscp-dot1p: 0..7
                 dscp-dp:    0..7
                 dscp-dscp:  0..63
                 dscp-lp:    0..7
                 exp-dp:     0..7
                 exp-lp:     0..7
                "
            ::= { ibIfQoSPriMapContentEntry 2 }

        ibIfQoSPriMapContentRowStatus OBJECT-TYPE
            SYNTAX RowStatus
            MAX-ACCESS read-create
            STATUS current
            DESCRIPTION
                "RowStatus."
            ::= { ibIfQoSPriMapContentEntry 3 }

--
-- nodes of ibIfQoSPrePriMapTable
--
        ibIfQoSPrePriMapTable OBJECT-TYPE
            SYNTAX SEQUENCE OF IbIfQoSPrePriMapEntry
            MAX-ACCESS not-accessible
            STATUS current
            DESCRIPTION
                "Pre-defined priority mapping table information."
            ::= { ibIfQoSPriMapConfigGroup 4 }

        ibIfQoSPrePriMapEntry OBJECT-TYPE
            SYNTAX IbIfQoSPrePriMapEntry
            MAX-ACCESS not-accessible
            STATUS current
            DESCRIPTION
                "Pre-defined priority mapping table entry."
            INDEX
            {
                ibIfQoSPrePriMapTableType,
                ibIfQoSPrePriMapTableColor,
                ibIfQoSPrePriMapTableDirection,
                ibIfQoSPrePriMapTableImportValue
            }
            ::= { ibIfQoSPrePriMapTable 1 }

        IbIfQoSPrePriMapEntry ::=
            SEQUENCE
            {
                ibIfQoSPrePriMapTableType
                    INTEGER,
                ibIfQoSPrePriMapTableColor
                    INTEGER,
                ibIfQoSPrePriMapTableDirection
                    INTEGER,
                ibIfQoSPrePriMapTableImportValue
                    Integer32,
                ibIfQoSPrePriMapTableExportValue
                    Integer32
            }

        ibIfQoSPrePriMapTableType OBJECT-TYPE
            SYNTAX INTEGER
            {
                dot1pToLp(1),
                dot1pToDp(2),
                expToLp(3),
                dscpToLp(4),
                expToDp(5),
                dscpToDp(6),
                dscpToDot1p(7),
                dot1pToDscp(8),
                dscpToDscp(9),
                dscpToExp(10),
                expToDscp(11),
                expToDot1p(12),
                expToExp(13),
                lpToDot1p(14),
                dot1pToRpr(15),
                dscpToRpr(16),
                expToRpr(17),
                ippreToRpr(18),
                upToDot1p(19),
                upToDscp(20),
                upToExp(21),
                upToDp(22),
                upToLp(23),
                upToRpr(24),
                upToFc(25),
                lpTodscp(26),
                dot11eToLp(27),
                lpToDot11e(28),
                lpToLp(29),
                dot1pToExp(30),
                lpToExp(31),
                lpToDp(32),
                upToUp(33),
                dot1pToDot1p(34)
            }
            MAX-ACCESS not-accessible
            STATUS current
            DESCRIPTION
                "The type of pre-defined priority mapping table."
            ::= { ibIfQoSPrePriMapEntry 1 }

        ibIfQoSPrePriMapTableColor OBJECT-TYPE
            SYNTAX INTEGER
            {
                noColor(1),
                green(2),
                yellow(3),
                red(4)
            }
            MAX-ACCESS not-accessible
            STATUS current
            DESCRIPTION
                "The color of pre-defined priority mapping table."
            ::= { ibIfQoSPrePriMapEntry 2 }

        ibIfQoSPrePriMapTableDirection OBJECT-TYPE
            SYNTAX INTEGER
            {
                noDirection(1),
                inbound(2),
                outbound(3)
            }
            MAX-ACCESS not-accessible
            STATUS current
            DESCRIPTION
                "The direction of pre-defined priority mapping table."
            ::= { ibIfQoSPrePriMapEntry 3 }

        ibIfQoSPrePriMapTableImportValue OBJECT-TYPE
            SYNTAX Integer32 (0..63)
            MAX-ACCESS not-accessible
            STATUS current
            DESCRIPTION
                "Input value of priority mapping table.
                 Different priority has different ibIfQoSPrePriMapTableImportValue.
                 Priority-type  Range of ibIfQoSPrePriMapTableImportValue
                 dot1p          (0..7)
                 dscp           (0..63)
                 lp             (0..7)
                 exp            (0..7)
                 ipPrecedence   (0..7)
                 up             (0..7)
                 dot11e         (0..7)
                "
            ::= { ibIfQoSPrePriMapEntry 4 }

        ibIfQoSPrePriMapTableExportValue OBJECT-TYPE
            SYNTAX Integer32 (0..63)
            MAX-ACCESS read-write
            STATUS current
            DESCRIPTION
                "Output value of priority mapping table.
                 Different priority has different ibIfQoSPrePriMapTableExportValue.
                 Priority-type  Range of ibIfQoSPrePriMapTableExportValue
                 dot1p          (0..7)
                 dscp           (0..63)
                 lp             (0..7)
                 exp            (0..7)
                 ipPrecedence   (0..7)
                 up             (0..7)
                 dp             (0..2)
                 fc             (0..7)
                 rpr            (0..2)
                "
            ::= { ibIfQoSPrePriMapEntry 5 }

--
-- nodes of L3 plus object
--
        ibIfQoSL3PlusObjects OBJECT IDENTIFIER ::= { ibIfQos2 10 }
--
-- nodes of ibIfQoSPortBindingGroup
--
        ibIfQoSPortBindingGroup OBJECT IDENTIFIER ::= { ibIfQoSL3PlusObjects 1 }

        ibIfQoSPortBindingTable OBJECT-TYPE
            SYNTAX SEQUENCE OF IbIfQoSPortBindingEntry
            MAX-ACCESS not-accessible
            STATUS current
            DESCRIPTION
                "A table of EACL sub-interface binding information
                 for L3+ board ."
            ::= { ibIfQoSPortBindingGroup 1 }

        ibIfQoSPortBindingEntry OBJECT-TYPE
            SYNTAX IbIfQoSPortBindingEntry
            MAX-ACCESS not-accessible
            STATUS current
            DESCRIPTION
                "Binding information entry."
            INDEX { ifIndex }
            ::= { ibIfQoSPortBindingTable 1 }

        IbIfQoSPortBindingEntry ::=
            SEQUENCE
            {
                ibIfQoSBindingIf
                    Integer32,
                ibIfQoSBindingRowStatus
                    RowStatus
            }

        ibIfQoSBindingIf OBJECT-TYPE
            SYNTAX Integer32
            MAX-ACCESS read-create
            STATUS current
            DESCRIPTION
                "The binding interface."
            ::= { ibIfQoSPortBindingEntry 1 }

        ibIfQoSBindingRowStatus OBJECT-TYPE
            SYNTAX RowStatus
            MAX-ACCESS read-create
            STATUS current
            DESCRIPTION
                "RowStatus"
            ::= { ibIfQoSPortBindingEntry 2 }

--
-- node of ibQoSTraStaObjects
--
        ibQoSTraStaObjects OBJECT IDENTIFIER ::= { ibIfQos2 11 }
--
-- nodes of ibQoSTraStaConfigGroup
--
        ibQoSTraStaConfigGroup OBJECT IDENTIFIER ::= { ibQoSTraStaObjects 1 }

        ibQoSIfTraStaConfigInfoTable OBJECT-TYPE
            SYNTAX SEQUENCE OF IbQoSIfTraStaConfigInfoEntry
            MAX-ACCESS not-accessible
            STATUS current
            DESCRIPTION
                "A table of traffic statistics configuration information."
            ::= { ibQoSTraStaConfigGroup 1 }

        ibQoSIfTraStaConfigInfoEntry OBJECT-TYPE
            SYNTAX IbQoSIfTraStaConfigInfoEntry
            MAX-ACCESS not-accessible
            STATUS current
            DESCRIPTION
                "An entry of interface traffic statistics configuration information."
            INDEX { ifIndex, ibQoSIfTraStaConfigDirection }
            ::= { ibQoSIfTraStaConfigInfoTable 1 }

        IbQoSIfTraStaConfigInfoEntry ::=
            SEQUENCE
            {
                ibQoSIfTraStaConfigDirection
                    Direction,
                ibQoSIfTraStaConfigQueue
                    OCTET STRING,
                ibQoSIfTraStaConfigDot1p
                    OCTET STRING,
                ibQoSIfTraStaConfigDscp
                    OCTET STRING,
                ibQoSIfTraStaConfigVlan
                    OCTET STRING,
                ibQoSIfTraStaConfigStatus
                    RowStatus
            }

        ibQoSIfTraStaConfigDirection OBJECT-TYPE
            SYNTAX Direction
            MAX-ACCESS not-accessible
            STATUS current
            DESCRIPTION "The direction of the traffic statistics."
            ::= { ibQoSIfTraStaConfigInfoEntry 1 }

        ibQoSIfTraStaConfigQueue OBJECT-TYPE
            SYNTAX OCTET STRING (SIZE (1))
            MAX-ACCESS read-create
            STATUS current
            DESCRIPTION "The bitmap of Queue ID.
                        The octet specifies queues 0 through 7.  If a bit has
                        a value of '1', the corresponding queue is configured
                        in the set of Queues; if a bit has a value of '0',
                        the corresponding queue is not configured."
            ::= { ibQoSIfTraStaConfigInfoEntry 2 }

        ibQoSIfTraStaConfigDot1p OBJECT-TYPE
            SYNTAX OCTET STRING (SIZE (1))
            MAX-ACCESS read-create
            STATUS current
            DESCRIPTION "The bitmap of Dot1p value.
                        The octet specifies Dot1p values 0 through 7.  If a bit
                        has a value of '1', the corresponding Dot1p value is
                        configured in the set of Dot1p values; if a bit has a
                        value of '0', the corresponding Dot1p value is not
                        configured."
            ::= { ibQoSIfTraStaConfigInfoEntry 3 }

        ibQoSIfTraStaConfigDscp OBJECT-TYPE
            SYNTAX OCTET STRING (SIZE (8))
            MAX-ACCESS read-create
            STATUS current
            DESCRIPTION "The bitmap of Dscp value.
                        Each octet within this value specifies a set of
                        eight Dscp values, with the first octet specifying
                        Dscp values 0 through 7, the second octet specifying
                        Dscp values 8 through 15, etc.  If a bit has a value
                        of '1', the corresponding Dscp value is configured
                        in the set of Dscp values; if a bit has a value of
                        '0', the corresponding Dscp value is not configured."
            ::= { ibQoSIfTraStaConfigInfoEntry 4 }

        ibQoSIfTraStaConfigVlan OBJECT-TYPE
            SYNTAX OCTET STRING (SIZE (512))
            MAX-ACCESS read-create
            STATUS current
            DESCRIPTION "The bitmap of VLAN ID.
                        Each octet within this value specifies a set of
                        eight VLANs, with the first octet specifying
                        VLANs 0 through 7, the second octet specifying VLANs
                        8 through 15, etc.  If a bit has a value of '1', the
                        corresponding VLAN is configured in the set of VLANs;
                        if a bit has a value of '0', the corresponding VLAN
                        is not configured."
            ::= { ibQoSIfTraStaConfigInfoEntry 5 }

        ibQoSIfTraStaConfigStatus OBJECT-TYPE
            SYNTAX RowStatus
            MAX-ACCESS read-create
            STATUS current
            DESCRIPTION "The row status of this table entry."
            ::= { ibQoSIfTraStaConfigInfoEntry 6 }


--
-- nodes of ibQoSTraStaRunGroup
--
        ibQoSTraStaRunGroup OBJECT IDENTIFIER ::= { ibQoSTraStaObjects 2 }

        ibQoSIfTraStaRunInfoTable OBJECT-TYPE
            SYNTAX SEQUENCE OF IbQoSIfTraStaRunInfoEntry
            MAX-ACCESS not-accessible
            STATUS current
            DESCRIPTION
                "A table of traffic statistics running information."
            ::= { ibQoSTraStaRunGroup 1 }

        ibQoSIfTraStaRunInfoEntry OBJECT-TYPE
            SYNTAX IbQoSIfTraStaRunInfoEntry
            MAX-ACCESS not-accessible
            STATUS current
            DESCRIPTION
                "An entry of interface traffic statistics running information."
            INDEX { ifIndex,
                    ibQoSIfTraStaRunObjectType,
                    ibQoSIfTraStaRunObjectValue,
                    ibQoSIfTraStaRunDirection }
            ::= { ibQoSIfTraStaRunInfoTable 1 }

        IbQoSIfTraStaRunInfoEntry ::=
            SEQUENCE
            {
                ibQoSIfTraStaRunObjectType
                    INTEGER,
                ibQoSIfTraStaRunObjectValue
                    Integer32,
                ibQoSIfTraStaRunDirection
                    Direction,
                ibQoSIfTraStaRunPassPackets
                    Counter64,
                ibQoSIfTraStaRunDropPackets
                    Counter64,
                ibQoSIfTraStaRunPassBytes
                    Counter64,
                ibQoSIfTraStaRunDropBytes
                    Counter64,
                ibQoSIfTraStaRunPassPPS
                    Counter64,
                ibQoSIfTraStaRunPassBPS
                    Counter64
            }

        ibQoSIfTraStaRunObjectType OBJECT-TYPE
            SYNTAX INTEGER
            {
                queue(1),
                dot1p(2),
                dscp(3),
                vlanID(4)
            }
            MAX-ACCESS not-accessible
            STATUS current
            DESCRIPTION
                "Type of statistics object."
            ::= { ibQoSIfTraStaRunInfoEntry 1 }

        ibQoSIfTraStaRunObjectValue OBJECT-TYPE
            SYNTAX Integer32
            MAX-ACCESS not-accessible
            STATUS current
            DESCRIPTION
                "Value range for the object type:
                 for Queue: 0~7
                 for Dot1p: 0~7
                 for Dscp: 0~63
                 for VlanID: 1~4094
                 "
            ::= { ibQoSIfTraStaRunInfoEntry 2 }

        ibQoSIfTraStaRunDirection OBJECT-TYPE
            SYNTAX Direction
            MAX-ACCESS not-accessible
            STATUS current
            DESCRIPTION
                "The direction of the traffic statistics."
            ::= { ibQoSIfTraStaRunInfoEntry 3 }

        ibQoSIfTraStaRunPassPackets OBJECT-TYPE
            SYNTAX Counter64
            MAX-ACCESS read-only
            STATUS current
            DESCRIPTION
                "Number of passed packets."
            ::= { ibQoSIfTraStaRunInfoEntry 4 }

        ibQoSIfTraStaRunDropPackets OBJECT-TYPE
            SYNTAX Counter64
            MAX-ACCESS read-only
            STATUS current
            DESCRIPTION
                "Number of dropped packets."
            ::= { ibQoSIfTraStaRunInfoEntry 5 }

        ibQoSIfTraStaRunPassBytes OBJECT-TYPE
            SYNTAX Counter64
            MAX-ACCESS read-only
            STATUS current
            DESCRIPTION
                "Number of passed bytes."
            ::= { ibQoSIfTraStaRunInfoEntry 6 }

        ibQoSIfTraStaRunDropBytes OBJECT-TYPE
            SYNTAX Counter64
            MAX-ACCESS read-only
            STATUS current
            DESCRIPTION
                "Number of dropped bytes."
            ::= { ibQoSIfTraStaRunInfoEntry 7 }

        ibQoSIfTraStaRunPassPPS OBJECT-TYPE
            SYNTAX Counter64
            MAX-ACCESS read-only
            STATUS current
            DESCRIPTION
                "PPS (packets per second) of passed packets."
            ::= { ibQoSIfTraStaRunInfoEntry 8 }

        ibQoSIfTraStaRunPassBPS OBJECT-TYPE
            SYNTAX Counter64
            MAX-ACCESS read-only
            STATUS current
            DESCRIPTION
                "BPS (bytes per second) of passed packets."
            ::= { ibQoSIfTraStaRunInfoEntry 9 }

--
-- nodes of ibQoSGlobalPriorityObject
--
        ibQoSGlobalPriorityObject OBJECT IDENTIFIER ::= { ibIfQos2 12 }

        ibQoSRemarkTcpPortPriTable OBJECT-TYPE
            SYNTAX SEQUENCE OF IbQoSRemarkTcpPortPriEntry
            MAX-ACCESS not-accessible
            STATUS current
            DESCRIPTION
                "A table of remarking TCP port priority information.
                 The priority field of all packets with the specified
                 TCP port will be remarked to the configured value.
                "
            ::= { ibQoSGlobalPriorityObject 1 }

        ibQoSRemarkTcpPortPriEntry OBJECT-TYPE
            SYNTAX IbQoSRemarkTcpPortPriEntry
            MAX-ACCESS not-accessible
            STATUS current
            DESCRIPTION
                "Remarking TCP port priority information entry."
            INDEX { ibQoSRemarkTcpPortStart }
            ::= { ibQoSRemarkTcpPortPriTable 1 }

        IbQoSRemarkTcpPortPriEntry ::=
            SEQUENCE
            {
                ibQoSRemarkTcpPortStart
                    Integer32,
                ibQoSRemarkTcpPortEnd
                    Integer32,
                ibQoSRemarkTcpPortType
                    INTEGER,
                ibQoSRemarkTcpPortDot1p
                    Unsigned32,
                ibQoSRemarkTcpPortDscp
                    Unsigned32,
                ibQoSRemarkTcpPortRowStatus
                    RowStatus
            }

        ibQoSRemarkTcpPortStart OBJECT-TYPE
            SYNTAX Integer32 (0..65535)
            MAX-ACCESS not-accessible
            STATUS current
            DESCRIPTION
                "Start value of TCP port range."
            ::= { ibQoSRemarkTcpPortPriEntry 1 }

        ibQoSRemarkTcpPortEnd OBJECT-TYPE
            SYNTAX Integer32 (0..65535)
            MAX-ACCESS read-create
            STATUS current
            DESCRIPTION
                "End value of TCP port range.
                 It cannot be less than start value.
                "
            ::= { ibQoSRemarkTcpPortPriEntry 2 }

        ibQoSRemarkTcpPortType OBJECT-TYPE
            SYNTAX INTEGER
            {
                ipAll(1),
                ipv4(2),
                ipv6(3)
            }
            MAX-ACCESS read-create
            STATUS current
            DESCRIPTION
                "IPv4 packet, IPv6 packet, or all IP packet."
            DEFVAL { ipAll }
            ::= { ibQoSRemarkTcpPortPriEntry 3 }

        ibQoSRemarkTcpPortDot1p OBJECT-TYPE
            SYNTAX Unsigned32 (0..7|255)
            MAX-ACCESS read-create
            STATUS current
            DESCRIPTION
                "Dot1p value."
            ::= { ibQoSRemarkTcpPortPriEntry 4 }

        ibQoSRemarkTcpPortDscp OBJECT-TYPE
            SYNTAX Unsigned32 (0..63|255)
            MAX-ACCESS read-create
            STATUS current
            DESCRIPTION
                "DSCP value."
            ::= { ibQoSRemarkTcpPortPriEntry 5 }

        ibQoSRemarkTcpPortRowStatus OBJECT-TYPE
            SYNTAX RowStatus
            MAX-ACCESS read-create
            STATUS current
            DESCRIPTION
                "Row status."
            ::= { ibQoSRemarkTcpPortPriEntry 6 }

--ibQoSRemarkUdpPortPriTable

        ibQoSRemarkUdpPortPriTable OBJECT-TYPE
            SYNTAX SEQUENCE OF IbQoSRemarkUdpPortPriEntry
            MAX-ACCESS not-accessible
            STATUS current
            DESCRIPTION
                "A table of remarking UDP port priority information.
                 The priority field of all packets with the specified
                 UDP port will be remarked to the configured value.
                "
            ::= { ibQoSGlobalPriorityObject 2 }

        ibQoSRemarkUdpPortPriEntry OBJECT-TYPE
            SYNTAX IbQoSRemarkUdpPortPriEntry
            MAX-ACCESS not-accessible
            STATUS current
            DESCRIPTION
                "Remarking UDP port priority information entry."
            INDEX { ibQoSRemarkUdpPortStart }
            ::= { ibQoSRemarkUdpPortPriTable 1 }

        IbQoSRemarkUdpPortPriEntry ::=
            SEQUENCE
            {
                ibQoSRemarkUdpPortStart
                    Integer32,
                ibQoSRemarkUdpPortEnd
                    Integer32,
                ibQoSRemarkUdpPortType
                    INTEGER,
                ibQoSRemarkUdpPortDot1p
                    Unsigned32,
                ibQoSRemarkUdpPortDscp
                    Unsigned32,
                ibQoSRemarkUdpPortRowStatus
                    RowStatus
            }

        ibQoSRemarkUdpPortStart OBJECT-TYPE
            SYNTAX Integer32 (0..65535)
            MAX-ACCESS not-accessible
            STATUS current
            DESCRIPTION
                "Start value of UDP port range."
            ::= { ibQoSRemarkUdpPortPriEntry 1 }

        ibQoSRemarkUdpPortEnd OBJECT-TYPE
            SYNTAX Integer32 (0..65535)
            MAX-ACCESS read-create
            STATUS current
            DESCRIPTION
                "End value of UDP port range.
                 It cannot be less than start value.
                "
            ::= { ibQoSRemarkUdpPortPriEntry 2 }

        ibQoSRemarkUdpPortType OBJECT-TYPE
            SYNTAX INTEGER
            {
                ipAll(1),
                ipv4(2),
                ipv6(3)
            }
            MAX-ACCESS read-create
            STATUS current
            DESCRIPTION
                "IPv4 packet, IPv6 packet, or all IP packet."
            DEFVAL { ipAll }
            ::= { ibQoSRemarkUdpPortPriEntry 3 }

        ibQoSRemarkUdpPortDot1p OBJECT-TYPE
            SYNTAX Unsigned32 (0..7|255)
            MAX-ACCESS read-create
            STATUS current
            DESCRIPTION
                "Dot1p value."
            ::= { ibQoSRemarkUdpPortPriEntry 4 }

        ibQoSRemarkUdpPortDscp OBJECT-TYPE
            SYNTAX Unsigned32 (0..63|255)
            MAX-ACCESS read-create
            STATUS current
            DESCRIPTION
                "DSCP value."
            ::= { ibQoSRemarkUdpPortPriEntry 5 }

        ibQoSRemarkUdpPortRowStatus OBJECT-TYPE
            SYNTAX RowStatus
            MAX-ACCESS read-create
            STATUS current
            DESCRIPTION
                "Row status."
            ::= { ibQoSRemarkUdpPortPriEntry 6 }

--ibQoSRemarkIPv4AddrPriTable
        ibQoSRemarkIPv4AddrPriTable OBJECT-TYPE
            SYNTAX SEQUENCE OF IbQoSRemarkIPv4AddrPriEntry
            MAX-ACCESS not-accessible
            STATUS current
            DESCRIPTION
                "A table of remarking IPv4 address priority information."
            ::= { ibQoSGlobalPriorityObject 3 }

        ibQoSRemarkIPv4AddrPriEntry OBJECT-TYPE
            SYNTAX IbQoSRemarkIPv4AddrPriEntry
            MAX-ACCESS not-accessible
            STATUS current
            DESCRIPTION
                "Remarking IPv4 address priority information entry.
                 The priority field of all IPv4 packets with the specified
                 IP address will be remarked to the configured value.
                "
            INDEX { ibQoSRemarkIPv4AddrValue }
            ::= { ibQoSRemarkIPv4AddrPriTable 1 }

        IbQoSRemarkIPv4AddrPriEntry ::=
            SEQUENCE
            {
                ibQoSRemarkIPv4AddrValue
                    IpAddress,
                ibQoSRemarkIPv4AddrMask
                    IpAddress,
                ibQoSRemarkIPv4AddrMaskLength
                    Unsigned32,
                ibQoSRemarkIPv4AddrDot1p
                    Unsigned32,
                ibQoSRemarkIPv4AddrDscp
                    Unsigned32,
                ibQoSRemarkIPv4AddrRowStatus
                    RowStatus
            }

        ibQoSRemarkIPv4AddrValue OBJECT-TYPE
            SYNTAX IpAddress
            MAX-ACCESS not-accessible
            STATUS current
            DESCRIPTION
                "IPv4 address."
            ::= { ibQoSRemarkIPv4AddrPriEntry 1 }

        ibQoSRemarkIPv4AddrMask OBJECT-TYPE
            SYNTAX IpAddress
            MAX-ACCESS read-create
            STATUS current
            DESCRIPTION
                "Mask of IPv4 address."
            ::= { ibQoSRemarkIPv4AddrPriEntry 2 }

        ibQoSRemarkIPv4AddrMaskLength OBJECT-TYPE
            SYNTAX Unsigned32 (1..32 |4294967295)
            MAX-ACCESS read-create
            STATUS current
            DESCRIPTION
                "Mask length of IPv4 address."
            DEFVAL { 32 }
            ::= { ibQoSRemarkIPv4AddrPriEntry 3 }

        ibQoSRemarkIPv4AddrDot1p OBJECT-TYPE
            SYNTAX Unsigned32 (0..7|255)
            MAX-ACCESS read-create
            STATUS current
            DESCRIPTION
                "Dot1p value."
            ::= { ibQoSRemarkIPv4AddrPriEntry 4 }

        ibQoSRemarkIPv4AddrDscp OBJECT-TYPE
            SYNTAX Unsigned32 (0..63|255)
            MAX-ACCESS read-create
            STATUS current
            DESCRIPTION
                "DSCP value."
            ::= { ibQoSRemarkIPv4AddrPriEntry 5 }

        ibQoSRemarkIPv4AddrRowStatus OBJECT-TYPE
            SYNTAX RowStatus
            MAX-ACCESS read-create
            STATUS current
            DESCRIPTION
                "Row status."
            ::= { ibQoSRemarkIPv4AddrPriEntry 6 }

--ibQoSRemarkIPv6AddrPriTable
        ibQoSRemarkIPv6AddrPriTable OBJECT-TYPE
            SYNTAX SEQUENCE OF IbQoSRemarkIPv6AddrPriEntry
            MAX-ACCESS not-accessible
            STATUS current
            DESCRIPTION
                "A table of remarking IPv6 address priority information.
                 The priority field of all IPv6 packets with the specified
                 IP address will be remarked to the configured value.
                "
            ::= { ibQoSGlobalPriorityObject 4 }

        ibQoSRemarkIPv6AddrPriEntry OBJECT-TYPE
            SYNTAX IbQoSRemarkIPv6AddrPriEntry
            MAX-ACCESS not-accessible
            STATUS current
            DESCRIPTION
                "Remarking IPv6 address priority information entry."
            INDEX { ibQoSRemarkIPv6AddrValue }
            ::= { ibQoSRemarkIPv6AddrPriTable 1 }

        IbQoSRemarkIPv6AddrPriEntry ::=
            SEQUENCE
            {
                ibQoSRemarkIPv6AddrValue
                    InetAddressIPv6,
                ibQoSRemarkIPv6AddrPrefixLength
                    InetAddressPrefixLength,
                ibQoSRemarkIPv6AddrDot1p
                    Unsigned32,
                ibQoSRemarkIPv6AddrDscp
                    Unsigned32,
                ibQoSRemarkIPv6AddrRowStatus
                    RowStatus
            }

        ibQoSRemarkIPv6AddrValue OBJECT-TYPE
            SYNTAX InetAddressIPv6
            MAX-ACCESS not-accessible
            STATUS current
            DESCRIPTION
                "IPv6 address."
            ::= { ibQoSRemarkIPv6AddrPriEntry 1 }

        ibQoSRemarkIPv6AddrPrefixLength OBJECT-TYPE
            SYNTAX InetAddressPrefixLength
            MAX-ACCESS read-create
            STATUS current
            DESCRIPTION
                "Prefix length of IPv6 address."
            DEFVAL { 128 }
            ::= { ibQoSRemarkIPv6AddrPriEntry 2 }

        ibQoSRemarkIPv6AddrDot1p OBJECT-TYPE
            SYNTAX Unsigned32 (0..7|255)
            MAX-ACCESS read-create
            STATUS current
            DESCRIPTION
                "Dot1p value."
            ::= { ibQoSRemarkIPv6AddrPriEntry 3 }

        ibQoSRemarkIPv6AddrDscp OBJECT-TYPE
            SYNTAX Unsigned32 (0..63|255)
            MAX-ACCESS read-create
            STATUS current
            DESCRIPTION
                "DSCP value."
            ::= { ibQoSRemarkIPv6AddrPriEntry 4 }

        ibQoSRemarkIPv6AddrRowStatus OBJECT-TYPE
            SYNTAX RowStatus
            MAX-ACCESS read-create
            STATUS current
            DESCRIPTION
                "Row status."
            ::= { ibQoSRemarkIPv6AddrPriEntry 5 }

--ibQoSRemarkProtocolPriTable
        ibQoSRemarkProtocolPriTable OBJECT-TYPE
            SYNTAX SEQUENCE OF IbQoSRemarkProtocolPriEntry
            MAX-ACCESS not-accessible
            STATUS current
            DESCRIPTION
                "A table of remarking layer 3 protocol priority information.
                 The 802.1p priority field of all packets of the specified
                 protocol will be remarked to the configured value.
                "
            ::= { ibQoSGlobalPriorityObject 5 }

        ibQoSRemarkProtocolPriEntry OBJECT-TYPE
            SYNTAX IbQoSRemarkProtocolPriEntry
            MAX-ACCESS not-accessible
            STATUS current
            DESCRIPTION
                "Remarking layer 3 protocol priority information entry."
            INDEX { ibQoSRemarkProtocolValue }
            ::= { ibQoSRemarkProtocolPriTable 1 }

        IbQoSRemarkProtocolPriEntry ::=
            SEQUENCE
            {
                ibQoSRemarkProtocolValue
                    INTEGER,
                ibQoSRemarkProtocolDot1p
                    Unsigned32,
                ibQoSRemarkProtocolRowStatus
                    RowStatus
            }

        ibQoSRemarkProtocolValue OBJECT-TYPE
            SYNTAX INTEGER
            {
                ip(1),
                ipx(2),
                arp(3),
                appletalk(4),
                sna(5),
                netbeui(6)
            }
            MAX-ACCESS not-accessible
            STATUS current
            DESCRIPTION
                "Layer 3 protocol type."
            ::= { ibQoSRemarkProtocolPriEntry 1 }

        ibQoSRemarkProtocolDot1p OBJECT-TYPE
            SYNTAX Unsigned32 (0..7|255)
            MAX-ACCESS read-create
            STATUS current
            DESCRIPTION
                "Dot1p value."
            ::= { ibQoSRemarkProtocolPriEntry 2 }

        ibQoSRemarkProtocolRowStatus OBJECT-TYPE
            SYNTAX RowStatus
            MAX-ACCESS read-create
            STATUS current
            DESCRIPTION
                "Row status."
            ::= { ibQoSRemarkProtocolPriEntry 3 }

--ibQoSRemarkVlanPriTable

        ibQoSRemarkVlanPriTable OBJECT-TYPE
            SYNTAX SEQUENCE OF IbQoSRemarkVlanPriEntry
            MAX-ACCESS not-accessible
            STATUS current
            DESCRIPTION
                "A table of remarking VLAN priority information.
                 The priority field of all packets of the specified
                 VLAN will be remarked to the configured value.
                "
            ::= { ibQoSGlobalPriorityObject 6 }

        ibQoSRemarkVlanPriEntry OBJECT-TYPE
            SYNTAX IbQoSRemarkVlanPriEntry
            MAX-ACCESS not-accessible
            STATUS current
            DESCRIPTION
                "Remarking VLAN priority information entry."
            INDEX { ibQoSRemarkVlanStart }
            ::= { ibQoSRemarkVlanPriTable 1 }

        IbQoSRemarkVlanPriEntry ::=
            SEQUENCE
            {
                ibQoSRemarkVlanStart
                    Integer32,
                ibQoSRemarkVlanEnd
                    Integer32,
                ibQoSRemarkVlanDot1p
                    Unsigned32,
                ibQoSRemarkVlanDscp
                    Unsigned32,
                ibQoSRemarkVlanRowStatus
                    RowStatus
            }

        ibQoSRemarkVlanStart OBJECT-TYPE
            SYNTAX Integer32 (1..4094)
            MAX-ACCESS not-accessible
            STATUS current
            DESCRIPTION
                "Start VLAN ID."
            ::= { ibQoSRemarkVlanPriEntry 1 }

        ibQoSRemarkVlanEnd OBJECT-TYPE
            SYNTAX Integer32 (1..4094)
            MAX-ACCESS read-create
            STATUS current
            DESCRIPTION
                "End VLAN ID.  It cannot be less than start value."
            ::= { ibQoSRemarkVlanPriEntry 2 }

        ibQoSRemarkVlanDot1p OBJECT-TYPE
            SYNTAX Unsigned32 (0..7|255)
            MAX-ACCESS read-create
            STATUS current
            DESCRIPTION
                "Dot1p value."
            ::= { ibQoSRemarkVlanPriEntry 3 }

        ibQoSRemarkVlanDscp OBJECT-TYPE
            SYNTAX Unsigned32 (0..63|255)
            MAX-ACCESS read-create
            STATUS current
            DESCRIPTION
                "DSCP value."
            ::= { ibQoSRemarkVlanPriEntry 4 }

        ibQoSRemarkVlanRowStatus OBJECT-TYPE
            SYNTAX RowStatus
            MAX-ACCESS read-create
            STATUS current
            DESCRIPTION
                "Row status."
            ::= { ibQoSRemarkVlanPriEntry 5 }

--Type of service node
        ibQoSTypeOfServiceObjects OBJECT IDENTIFIER
            ::= { ibQoSGlobalPriorityObject 7 }

        ibQoSTypeOfServiceMode OBJECT-TYPE
            SYNTAX INTEGER
            {
                disabled(1),
                ipPrecedence(2),
                dscp(3)
            }
            MAX-ACCESS read-write
            STATUS current
            DESCRIPTION
                "Global type of service.
                 The type of service is disabled by default.
                 When in ip-precedence mode, device uses ip-precedence value to
                 determine the 802.1p priority of the packet and its outbound queue.
                 When in DSCP mode, device uses DSCP value to determine
                 the 802.1p priority of the packet and its outbound queue.
                "
            DEFVAL { disabled }
            ::= { ibQoSTypeOfServiceObjects 1 }

--
-- nodes of ibIfQoSProcessingStatusObjects
--
        ibIfQoSProcessingStatusObjects OBJECT IDENTIFIER ::= { ibIfQos2 13 }

-- System status when processing

        ibIfQoSProcessingStatus OBJECT-TYPE
            SYNTAX INTEGER
            {
                idle(1),
                busy(2)
            }
            MAX-ACCESS read-only
            STATUS current
            DESCRIPTION
                "This object shows the current running status of the IFQoS module.
                'busy' means a task is being executed in the IFQoS module.  It is
                highly recommended not setting or reading IFQoS MIB objects in this state.
                otherwise, an operation failure might occur.
                'idle' means no task is being executed in the IFQoS module.  In this
                state, operations on IFQoS MIB objects will be accepted and executed
                immediately."

            ::= { ibIfQoSProcessingStatusObjects 1 }

--
-- nodes of ibIfQoSCoppObjects
--
        ibIfQoSCoppObjects OBJECT IDENTIFIER ::= { ibIfQos2 14 }

        ibIfQoSCoppFlowStatTable OBJECT-TYPE
            SYNTAX SEQUENCE OF IbIfQoSCoppFlowStatEntry
            MAX-ACCESS not-accessible
            STATUS current
            DESCRIPTION
                "A table of display the copp flow stat."
            ::= { ibIfQoSCoppObjects 1 }

        ibIfQoSCoppFlowStatEntry OBJECT-TYPE
            SYNTAX IbIfQoSCoppFlowStatEntry
            MAX-ACCESS not-accessible
            STATUS current
            DESCRIPTION
                "Display the copp flow stat entry."
            INDEX { ibIfQoSCoppFlowStatChassis, ibIfQoSCoppFlowStatSlot, ibIfQoSCoppFlowStatProType}
            ::= { ibIfQoSCoppFlowStatTable 1 }

    IbIfQoSCoppFlowStatEntry ::=
            SEQUENCE
            {
                ibIfQoSCoppFlowStatChassis
                    Unsigned32,
                ibIfQoSCoppFlowStatSlot
                    Unsigned32,
                ibIfQoSCoppFlowStatProType
                    Unsigned32,
                ibIfQoSCoppFlowPassPackets
                    Counter64,
                ibIfQoSCoppFlowPassBytes
                    Counter64,
                ibIfQoSCoppFlowDropPackets
                    Counter64,
                ibIfQoSCoppFlowDropBytes
                    Counter64
            }

    ibIfQoSCoppFlowStatChassis OBJECT-TYPE
            SYNTAX Unsigned32
            MAX-ACCESS not-accessible
            STATUS current
            DESCRIPTION
                "The Chassis number."
            ::= { ibIfQoSCoppFlowStatEntry 1 }

    ibIfQoSCoppFlowStatSlot OBJECT-TYPE
            SYNTAX Unsigned32
            MAX-ACCESS not-accessible
            STATUS current
            DESCRIPTION
                "The slot number."
            ::= { ibIfQoSCoppFlowStatEntry 2 }

    ibIfQoSCoppFlowStatProType OBJECT-TYPE
            SYNTAX Unsigned32 (1..65)
            MAX-ACCESS not-accessible
            STATUS current
            DESCRIPTION
                "The protocol type."
            ::= { ibIfQoSCoppFlowStatEntry 3 }

    ibIfQoSCoppFlowPassPackets OBJECT-TYPE
            SYNTAX Counter64
            MAX-ACCESS read-only
            STATUS current
            DESCRIPTION
                "The number of passed packets."
            ::= { ibIfQoSCoppFlowStatEntry 4 }

    ibIfQoSCoppFlowPassBytes OBJECT-TYPE
            SYNTAX Counter64
            MAX-ACCESS read-only
            STATUS current
            DESCRIPTION
                "The number of passed bytes."
            ::= { ibIfQoSCoppFlowStatEntry 5 }

    ibIfQoSCoppFlowDropPackets OBJECT-TYPE
            SYNTAX Counter64
            MAX-ACCESS read-only
            STATUS current
            DESCRIPTION
                "The number of dropped packets."
            ::= { ibIfQoSCoppFlowStatEntry 6 }

    ibIfQoSCoppFlowDropBytes OBJECT-TYPE
            SYNTAX Counter64
            MAX-ACCESS read-only
            STATUS current
            DESCRIPTION
                "The number of dropped bytes."
            ::= { ibIfQoSCoppFlowStatEntry 7 }

--
-- Nodes of ibIfQoSNotificationsBindings
--

    ibIfQoSNotificationsBindings OBJECT IDENTIFIER ::= { ibIfQos2 15 }

    ibIfQoSChassis OBJECT-TYPE
        SYNTAX Integer32   (0..65534)
        MAX-ACCESS accessible-for-notify
        STATUS current
        DESCRIPTION
            "The chassis number."
        ::= { ibIfQoSNotificationsBindings 1 }

    ibIfQoSSlot OBJECT-TYPE
        SYNTAX Integer32   (0..65534)
        MAX-ACCESS accessible-for-notify
        STATUS current
        DESCRIPTION
            "The slot number."
        ::= { ibIfQoSNotificationsBindings 2 }

    ibIfQoSCPU OBJECT-TYPE
        SYNTAX Integer32   (0..65534)
        MAX-ACCESS accessible-for-notify
        STATUS current
        DESCRIPTION
            "The CPU number."
        ::= { ibIfQoSNotificationsBindings 3 }

    ibIfQoSChip OBJECT-TYPE
        SYNTAX Integer32   (0..65534)
        MAX-ACCESS accessible-for-notify
        STATUS current
        DESCRIPTION
            "The chip number."
        ::= { ibIfQoSNotificationsBindings 4 }

    ibIfQoSIfName OBJECT-TYPE
        SYNTAX OCTET STRING (SIZE(1..47))
        MAX-ACCESS accessible-for-notify
        STATUS current
        DESCRIPTION
            "The interface name."
        ::= { ibIfQoSNotificationsBindings 5 }

    ibIfQoSDirection OBJECT-TYPE
        SYNTAX Direction
        MAX-ACCESS accessible-for-notify
        STATUS current
        DESCRIPTION
            "Inbound or outbound."
        ::= { ibIfQoSNotificationsBindings 6 }

    ibIfQoSPassPacketRate OBJECT-TYPE
        SYNTAX Unsigned32
        MAX-ACCESS accessible-for-notify
        STATUS current
        DESCRIPTION
            "Rate of outgoing traffic on an interface."
        ::= { ibIfQoSNotificationsBindings 7 }

    ibIfQoSCoppProtocol OBJECT-TYPE
        SYNTAX OCTET STRING (SIZE(1..31))
        MAX-ACCESS accessible-for-notify
        STATUS current
        DESCRIPTION
            "The protocol name of packets sent to CPU."
        ::= { ibIfQoSNotificationsBindings 8 }

    ibIfQoSBandwidth OBJECT-TYPE
        SYNTAX Unsigned32
        MAX-ACCESS accessible-for-notify
        STATUS current
        DESCRIPTION
            "Bandwidth. Unit: kbps or pps"
        ::= { ibIfQoSNotificationsBindings 9 }

    ibIfQoSServiceName OBJECT-TYPE
        SYNTAX OCTET STRING (SIZE (1..63))
        MAX-ACCESS accessible-for-notify
        STATUS current
        DESCRIPTION
            "Name of the service."
        ::= { ibIfQoSNotificationsBindings 10 }

    ibIfQoSApplyObject OBJECT-TYPE
        SYNTAX OCTET STRING (SIZE (1..127))
        MAX-ACCESS accessible-for-notify
        STATUS current
        DESCRIPTION
            "Name of the applying object."
        ::= { ibIfQoSNotificationsBindings 11 }

    ibIfQoSFailReason OBJECT-TYPE
        SYNTAX OCTET STRING (SIZE (1..127))
        MAX-ACCESS accessible-for-notify
        STATUS current
        DESCRIPTION
            "Failure cause."
        ::= { ibIfQoSNotificationsBindings 12 }

    ibIfQoSBandwidthUnit OBJECT-TYPE
        SYNTAX INTEGER
        {
            unitUnavailable(0),
            unitAbsolute(1),
            unitPercent(2),
            unitRemainPercent(3),
            unitAbsolutePPS(4)
        }
        MAX-ACCESS accessible-for-notify
        STATUS current
        DESCRIPTION
            "The measurement unit for bandwidth.
             Absolute, Unit : Kbps(Kilobits per second)
             Percent, Unit : %
             RemainPercent, Unit : %
             AbsolutePPS, Unit : pps(Packets per sedond)"
        ::= { ibIfQoSNotificationsBindings 13 }

        ibIfQoSQueBufferQueID OBJECT-TYPE
        SYNTAX Unsigned32 (0..65535)
        MAX-ACCESS accessible-for-notify
        STATUS current
        DESCRIPTION
            "Queue ID."
        ::= { ibIfQoSNotificationsBindings 14 }

        ibIfQoSQueBufferUsedCell OBJECT-TYPE
        SYNTAX Unsigned32
        MAX-ACCESS accessible-for-notify
        STATUS current
        DESCRIPTION
            "Buffer value."
        ::= { ibIfQoSNotificationsBindings 15 }

        ibIfQoSQueBufferUsedLength OBJECT-TYPE
        SYNTAX Unsigned32
        MAX-ACCESS accessible-for-notify
        STATUS current
        DESCRIPTION
            "Buffer length."
        ::= { ibIfQoSNotificationsBindings 16 }

        ibIfQoSQueBufferDiscard OBJECT-TYPE
        SYNTAX Counter64
        MAX-ACCESS accessible-for-notify
        STATUS current
        DESCRIPTION
            "The number of dropped bytes."
        ::= { ibIfQoSNotificationsBindings 17 }

        ibIfQoSPortID OBJECT-TYPE
        SYNTAX Integer32   (0..65535)
        MAX-ACCESS accessible-for-notify
        STATUS current
        DESCRIPTION
            "Port ID."
        ::= { ibIfQoSNotificationsBindings 18 }

    --
    -- Nodes of ibIfQoSNotifications
    --

    ibIfQoSNotifications OBJECT IDENTIFIER ::= { ibIfQos2 16 }

    ibIfQoSNotificationsPrefix OBJECT IDENTIFIER ::= { ibIfQoSNotifications 0 }

    ibIfQoS8QueueResouceOverAlarm NOTIFICATION-TYPE
        OBJECTS
        {
            ibIfQoSChassis,
            ibIfQoSSlot,
            ibIfQoSCPU,
            ibIfQoSChip,
            ibIfQoSDirection
        }
        STATUS current
        DESCRIPTION
            "The number of 8-queue user-queues exceeded the specification of the forwarding engine resources."
        ::= { ibIfQoSNotificationsPrefix 1 }

    ibIfQoS8QueueResouceOverRecover NOTIFICATION-TYPE
        OBJECTS
        {
            ibIfQoSChassis,
            ibIfQoSSlot,
            ibIfQoSCPU,
            ibIfQoSChip,
            ibIfQoSDirection
        }
        STATUS current
        DESCRIPTION
            "The number of 8-queue user-queues dropped below the specification of the forwarding engine resources."
        ::= { ibIfQoSNotificationsPrefix 2 }


    ibIfQoS8QueueResoucePreAlarm NOTIFICATION-TYPE
        OBJECTS
        {
            ibIfQoSChassis,
            ibIfQoSSlot,
            ibIfQoSCPU,
            ibIfQoSChip,
            ibIfQoSDirection
        }
        STATUS current
        DESCRIPTION
            "The number of 8-queue user-queues exceeded 90 percent of the specification of the forwarding engine resources."
        ::= { ibIfQoSNotificationsPrefix 3 }

    ibIfQoS8QueueResoucePreRecover NOTIFICATION-TYPE
        OBJECTS
        {
            ibIfQoSChassis,
            ibIfQoSSlot,
            ibIfQoSCPU,
            ibIfQoSChip,
            ibIfQoSDirection
        }
        STATUS current
        DESCRIPTION
            "The number of 8-queue user-queues dropped below 90 percent of the specification of the forwarding engine resources."
        ::= { ibIfQoSNotificationsPrefix 4 }

    ibIfQoSBufferOverAlarm NOTIFICATION-TYPE
        OBJECTS
        {
            ibIfQoSChassis,
            ibIfQoSSlot,
            ibIfQoSCPU,
            ibIfQoSChip,
            ibIfQoSDirection
        }
        STATUS current
        DESCRIPTION
            "The buffer size has been reached."
        ::= { ibIfQoSNotificationsPrefix 5 }

    ibIfQoSBufferOverRecover NOTIFICATION-TYPE
        OBJECTS
        {
            ibIfQoSChassis,
            ibIfQoSSlot,
            ibIfQoSCPU,
            ibIfQoSChip,
            ibIfQoSDirection
        }
        STATUS current
        DESCRIPTION
            "The queue buffer alarm is cleared."
        ::= { ibIfQoSNotificationsPrefix 6 }

    ibIfQoSModeChannelOverPortShapAlarm NOTIFICATION-TYPE
        OBJECTS
        {
            ibIfQoSChassis,
            ibIfQoSSlot,
            ibIfQoSCPU,
            ibIfQoSIfName
        }
        STATUS current
        DESCRIPTION
            "The channelization bandwidth configured on the interface exceeds the port shaping value."
        ::= { ibIfQoSNotificationsPrefix 7 }

    ibIfQoSModeChannelOverPortShapRecover NOTIFICATION-TYPE
        OBJECTS
        {
            ibIfQoSChassis,
            ibIfQoSSlot,
            ibIfQoSCPU,
            ibIfQoSIfName
        }
        STATUS current
        DESCRIPTION
            "The alarm generated when the channelization bandwidth configured on the interface exceeds the port shaping value is cleared."
        ::= { ibIfQoSNotificationsPrefix 8 }

     ibIfQoSExclusiveBandApplyFailAlarm NOTIFICATION-TYPE
        OBJECTS
        {
            ibIfQoSChassis,
            ibIfQoSSlot,
            ibIfQoSCPU,
            ibIfQoSIfName
        }
        STATUS current
        DESCRIPTION
            "The exclusive bandwidth configured on the interface does not take effect."
        ::= { ibIfQoSNotificationsPrefix 9 }

    ibIfQoSExclusiveBandApplyFailRecover NOTIFICATION-TYPE
        OBJECTS
        {
            ibIfQoSChassis,
            ibIfQoSSlot,
            ibIfQoSCPU,
            ibIfQoSIfName
        }
        STATUS current
        DESCRIPTION
            "The exclusive bandwidth service alarm on interface has cleared."
        ::= { ibIfQoSNotificationsPrefix 10 }

    ibIfQoSExclusiveBandOverAlarm NOTIFICATION-TYPE
        OBJECTS
        {
            ibIfQoSChassis,
            ibIfQoSSlot,
            ibIfQoSCPU,
            ibIfQoSIfName
        }
        STATUS current
        DESCRIPTION
            "The exclusive bandwidth configured on the interface exceeds the port bandwidth or port shaping value."
        ::= { ibIfQoSNotificationsPrefix 11 }

    ibIfQoSExclusiveBandOverRecover NOTIFICATION-TYPE
        OBJECTS
        {
            ibIfQoSChassis,
            ibIfQoSSlot,
            ibIfQoSCPU,
            ibIfQoSIfName
        }
        STATUS current
        DESCRIPTION
            "The alarm generated when the exclusive bandwidth configured on the interface exceeds the port bandwidth or port shaping value is cleared."
        ::= { ibIfQoSNotificationsPrefix 12 }

    ibIfQoSLRDiscardAlarm NOTIFICATION-TYPE
        OBJECTS
        {
            ibIfQoSIfName,
            ibIfQoSLRCir,
            ibIfQoSPassPacketRate
        }
        STATUS current
        DESCRIPTION
            "The outgoing traffic on the interface exceeds the CIR of the interface."
        ::= { ibIfQoSNotificationsPrefix 13 }

    ibIfQoSLRDiscardAlarmRecover NOTIFICATION-TYPE
        OBJECTS
        {
            ibIfQoSIfName,
            ibIfQoSLRCir,
            ibIfQoSPassPacketRate
        }
        STATUS current
        DESCRIPTION
            "The outgoing traffic on the interface recovered from congestion."
        ::= { ibIfQoSNotificationsPrefix 14 }

    ibIfQoSCarDiscardAlarm NOTIFICATION-TYPE
        OBJECTS
        {
            ibIfQoSChassis,
            ibIfQoSSlot,
            ibIfQoSIfName,
            ibIfQoSDirection
        }
        STATUS current
        DESCRIPTION
            "Packet loss occurs on the interface due to CAR."
        ::= { ibIfQoSNotificationsPrefix 15 }

    ibIfQoSCarDiscardAlarmRecover NOTIFICATION-TYPE
        OBJECTS
        {
            ibIfQoSChassis,
            ibIfQoSSlot,
            ibIfQoSIfName,
            ibIfQoSDirection
        }
        STATUS current
        DESCRIPTION
            "The interface recovers from the packet loss caused by CAR."
        ::= { ibIfQoSNotificationsPrefix 16 }

    ibIfQoSCoppDropPktAlarm NOTIFICATION-TYPE
        OBJECTS
        {
            ibIfQoSChassis,
            ibIfQoSSlot,
            ibIfQoSCoppProtocol,
            ibIfQoSBandwidth,
            ibIfQoSBandwidthUnit
        }
        STATUS current
        DESCRIPTION
            "Rate of packets to cpu exceeded the control-plane CAR limit."
        ::= { ibIfQoSNotificationsPrefix 17 }

    ibIfQoSCoppDropPktAlarmRecover NOTIFICATION-TYPE
        OBJECTS
        {
            ibIfQoSChassis,
            ibIfQoSSlot,
            ibIfQoSCoppProtocol,
            ibIfQoSBandwidth,
            ibIfQoSBandwidthUnit
        }
        STATUS current
        DESCRIPTION
            "Rate of packets to cpu lowered the control-plane CAR limit."
        ::= { ibIfQoSNotificationsPrefix 18 }

    ibIfQoSQueExcpAlarm NOTIFICATION-TYPE
        OBJECTS
        {
            ibIfQoSChassis,
            ibIfQoSSlot,
            ibIfQoSCoppProtocol
        }
        STATUS current
        DESCRIPTION
            "Failed to forward packets due to an abnormal queue in the specified
             slot."
        ::= { ibIfQoSNotificationsPrefix 19 }

    ibIfQoSQueExcpAlarmRecover NOTIFICATION-TYPE
        OBJECTS
        {
            ibIfQoSChassis,
            ibIfQoSSlot,
            ibIfQoSCoppProtocol
        }
        STATUS current
        DESCRIPTION
            "The forwarding failure caused by an abnormal queue in the specified
             slot is cleared."
        ::= { ibIfQoSNotificationsPrefix 20 }

    ibIfQoSBoardL3AclResLack NOTIFICATION-TYPE
        OBJECTS
        {
            ibIfQoSChassis,
            ibIfQoSSlot,
            ibIfQoSServiceName,
            ibIfQoSFailReason
        }
        STATUS current
        DESCRIPTION
            "Layer 3 service failed because of insufficient ACL resources."
        ::= { ibIfQoSNotificationsPrefix 21 }

    ibIfQoSAclResAlarm NOTIFICATION-TYPE
        OBJECTS
        {
            ibIfQoSChassis,
            ibIfQoSSlot,
            ibIfQoSServiceName,
            ibIfQoSApplyObject,
            ibIfQoSDirection,
            ibIfQoSFailReason
        }
        STATUS current
        DESCRIPTION
            "The service failed to be delivered because ACL resources were
             insufficient."
        ::= { ibIfQoSNotificationsPrefix 22 }

    ibIfQoSAclResAlarmRecover NOTIFICATION-TYPE
        OBJECTS
        {
            ibIfQoSChassis,
            ibIfQoSSlot,
            ibIfQoSServiceName,
            ibIfQoSApplyObject,
            ibIfQoSDirection,
            ibIfQoSFailReason
        }
        STATUS current
        DESCRIPTION
            "ACL resources are sufficient."
        ::= { ibIfQoSNotificationsPrefix 23 }

    ibIfQoSAclMemFullAlarm NOTIFICATION-TYPE
        OBJECTS
        {
            ibIfQoSChassis,
            ibIfQoSSlot
        }
        STATUS current
        DESCRIPTION
            "The ACL memory usage exceeds the specification of the forwarding
             engine in a specified slot."
        ::= { ibIfQoSNotificationsPrefix 24 }

    ibIfQoSAclMemFullAlarmRecover NOTIFICATION-TYPE
        OBJECTS
        {
            ibIfQoSChassis,
            ibIfQoSSlot
        }
        STATUS current
        DESCRIPTION
            "The ACL memory usage of the forwarding engine is recovered in a
             specified slot."
        ::= { ibIfQoSNotificationsPrefix 25 }

        ibIfQoSBufferAlarm NOTIFICATION-TYPE
        OBJECTS
        {
            ibIfQoSSlot,
            ibIfQoSChip
        }
        STATUS current
        DESCRIPTION
            "Queue buffer alarm on slot."
        ::= { ibIfQoSNotificationsPrefix 26 }

        ibIfQoSBufferAlarmRecover NOTIFICATION-TYPE
        OBJECTS
        {
            ibIfQoSSlot,
            ibIfQoSChip
        }
        STATUS current
        DESCRIPTION
            "Queue buffer alarm recovered on slot."
        ::= { ibIfQoSNotificationsPrefix 27 }

        ibIfQoSQueBufferOverrunAlarm NOTIFICATION-TYPE
        OBJECTS
        {
            ibIfQoSQueBufferQueID,
            ibIfQoSIfName,
            ibIfQoSSlot,
            ibIfQoSQueBufferUsedCell,
            ibIfQoSQueBufferUsedLength,
            ibIfQoSQueBufferDiscard
        }
        STATUS current
        DESCRIPTION
            "Interface queue buffer threshold alarm."
        ::= { ibIfQoSNotificationsPrefix 28 }

        ibIfQoSQueBufferOverrunRecover NOTIFICATION-TYPE
        OBJECTS
        {
            ibIfQoSQueBufferQueID,
            ibIfQoSIfName,
            ibIfQoSSlot,
            ibIfQoSQueBufferUsedCell,
            ibIfQoSQueBufferUsedLength,
            ibIfQoSQueBufferDiscard
        }
        STATUS current
        DESCRIPTION
            "Interface queue buffer threshold alarm recovery."
        ::= { ibIfQoSNotificationsPrefix 29 }

        ibIfQoSFCoEPriorityAlarm NOTIFICATION-TYPE
        STATUS current
        DESCRIPTION
            "Priority mapping alarm."
        ::= { ibIfQoSNotificationsPrefix 30 }

        ibIfQoSFCoEPriorityRecover NOTIFICATION-TYPE
        STATUS current
        DESCRIPTION
            "Priority mapping alarm recovery."
        ::= { ibIfQoSNotificationsPrefix 31 }

        ibIfQoSRcyPortPktsDropAlarm NOTIFICATION-TYPE
        OBJECTS
        {
            ibIfQoSPortID,
            ibIfQoSSlot,
            ibIfQoSChip
        }
        STATUS current
        DESCRIPTION
            "Packet loss alarm of loopback port."
        ::= { ibIfQoSNotificationsPrefix 32 }

        ibIfQoSRcyPortPktsDropRecover NOTIFICATION-TYPE
        OBJECTS
        {
            ibIfQoSPortID,
            ibIfQoSSlot,
            ibIfQoSChip
        }
        STATUS current
        DESCRIPTION
            "Packet loss recovery of loopback port."
        ::= { ibIfQoSNotificationsPrefix 33 }

        ibIfQoSStormSuppressAlarm NOTIFICATION-TYPE
        OBJECTS
        {
            ibIfQoSSlot
        }
        STATUS current
        DESCRIPTION
            "QoS storm suppression alarm."
        ::= { ibIfQoSNotificationsPrefix 34}

        ibIfQoSStormSuppressRecover NOTIFICATION-TYPE
        OBJECTS
        {
            ibIfQoSSlot
        }
        STATUS current
        DESCRIPTION
            "QoS storm suppression recovery."
        ::= { ibIfQoSNotificationsPrefix 35 }

        ibIfQoSUniPktsDiscardAlarm NOTIFICATION-TYPE
        OBJECTS
        {
            ibIfQoSSlot
        }
        STATUS current
        DESCRIPTION
            "Unicast packet loss."
        ::= { ibIfQoSNotificationsPrefix 36 }

        ibIfQoSUniPktsDiscardRecover NOTIFICATION-TYPE
        OBJECTS
        {
            ibIfQoSSlot
        }
        STATUS current
        DESCRIPTION
            "Unicast packet loss recovery."
        ::= { ibIfQoSNotificationsPrefix 37 }

        ibIfQoSIngressDiscardAlarm NOTIFICATION-TYPE
        OBJECTS
        {
            ibIfQoSSlot
        }
        STATUS current
        DESCRIPTION
            "Incoming direction message dispatching failure."
        ::= { ibIfQoSNotificationsPrefix 38 }

        ibIfQoSIngressDiscardRecover NOTIFICATION-TYPE
        OBJECTS
        {
            ibIfQoSSlot
        }
        STATUS current
        DESCRIPTION
            "Incoming direction message dispatching recovery."
        ::= { ibIfQoSNotificationsPrefix 39 }

END
