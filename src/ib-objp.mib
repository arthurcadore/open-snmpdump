-- ============================================================================
-- Copyright (C) 2023 Intelbras S.A. All rights reserved.
--
-- Description: This MIB is used for configuration of OBJP(object policy).
-- Reference:
-- Version: V1.0
-- History:
-- V1.0 created by gaoyu.
-- ============================================================================
IB-OBJP-MIB DEFINITIONS ::= BEGIN

IMPORTS
    ibCommon
        FROM  IB-OID-MIB
    OBJECT-TYPE, MODULE-IDENTITY,
    Unsigned32, Counter64
        FROM SNMPv2-SMI;

--
-- Node definitions
--

ibObjp MODULE-IDENTITY
    LAST-UPDATED "201403101536Z"        -- Mar 10, 2014 at 15:36 GMT
    ORGANIZATION
        "Intelbras S.A. Industria de Telecomunicacao Eletronica Brasileria."
    CONTACT-INFO
        ""
    DESCRIPTION
        "Object-policy management information base for managing devices
        that support object policy.
        "
    REVISION "201403101536Z"            -- Mar 10, 2014 at 15:36 GMT
    DESCRIPTION
        "The initial revision of this MIB module."
    ::= { ibCommon 155 }

--
-- Nodes of ibObjpZonePairObjects
--
ibObjpZonePairObjects OBJECT IDENTIFIER ::= { ibObjp 1 }

--
-- Nodes of ibObjpZonePairRunningInfoTable
--
ibObjpZonePairRunningInfoTable OBJECT-TYPE
    SYNTAX SEQUENCE OF IbObjpZonePairRunningInfoEntry
    MAX-ACCESS not-accessible
    STATUS current
    DESCRIPTION
        "Object policy of zone pair running information base."
    ::= { ibObjpZonePairObjects 1 }

ibObjpZonePairRunningInfoEntry OBJECT-TYPE
    SYNTAX IbObjpZonePairRunningInfoEntry
    MAX-ACCESS not-accessible
    STATUS current
    DESCRIPTION
        "Object policy of zone pair running information entry."
    INDEX
    {
        ibObjpZonePairSrcZone,
        ibObjpZonePairDstZone,
        ibObjpZonePairIPVersion,
        ibObjpZonePairRuleID
    }
    ::= { ibObjpZonePairRunningInfoTable 1 }

IbObjpZonePairRunningInfoEntry ::=
    SEQUENCE
    {
        ibObjpZonePairSrcZone
            OCTET STRING,
        ibObjpZonePairDstZone
            OCTET STRING,
        ibObjpZonePairIPVersion
            INTEGER,
        ibObjpZonePairRuleID
            Unsigned32,
        ibObjpZonePairMatchPacketCount
            Counter64,
        ibObjpZonePairLastMatchTime
            Unsigned32
    }

ibObjpZonePairSrcZone OBJECT-TYPE
    SYNTAX OCTET STRING (SIZE(1..31))
    MAX-ACCESS not-accessible
    STATUS current
    DESCRIPTION
        "Name of the source security zone."
    ::= { ibObjpZonePairRunningInfoEntry 1 }

ibObjpZonePairDstZone OBJECT-TYPE
    SYNTAX OCTET STRING (SIZE(1..31))
    MAX-ACCESS not-accessible
    STATUS current
    DESCRIPTION
        "Name of the destination security zone."
    ::= { ibObjpZonePairRunningInfoEntry 2 }

ibObjpZonePairIPVersion OBJECT-TYPE
    SYNTAX INTEGER
    {
        ipv4(1),
        ipv6(2)
    }
    MAX-ACCESS not-accessible
    STATUS current
    DESCRIPTION
        "IP protocol version."
    ::= { ibObjpZonePairRunningInfoEntry 3 }

ibObjpZonePairRuleID OBJECT-TYPE
    SYNTAX Unsigned32 (0..65534)
    MAX-ACCESS not-accessible
    STATUS current
    DESCRIPTION
        "Rule ID of object policy."
    ::= { ibObjpZonePairRunningInfoEntry 4 }

ibObjpZonePairMatchPacketCount OBJECT-TYPE
    SYNTAX Counter64
    MAX-ACCESS read-only
    STATUS current
    DESCRIPTION
        "Number of packets matching the rule."
    ::= { ibObjpZonePairRunningInfoEntry 5 }

ibObjpZonePairLastMatchTime OBJECT-TYPE
    SYNTAX Unsigned32
    MAX-ACCESS read-only
    STATUS current
    DESCRIPTION
        "Interval in seconds between the last match and 1970/1/1 00:00:00."
    ::= { ibObjpZonePairRunningInfoEntry 6 }

END
