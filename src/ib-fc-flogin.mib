-- =====================================================================
-- Copyright (C) 2023 Intelbras S.A. All rights reserved.
--
-- Description:
--      This MIB module is used for representing fabric login information.
-- Reference:
-- Version: V1.1
-- History:
--   V1.0 Initial version
--        created by qiaoxinghua 2013-02-27
--   V1.1 Modified by Zhaoming May.9 2022.The trap 'ibFcFLoginMaxNotify'
--        was added.
-- =====================================================================
IB-FC-FLOGIN-MIB DEFINITIONS ::= BEGIN

IMPORTS
    OBJECT-TYPE, MODULE-IDENTITY, NOTIFICATION-TYPE, Integer32
        FROM SNMPv2-SMI
    TruthValue
        FROM SNMPv2-TC
    IbFcNameId, IbFcAddressId, IbFcBbCredit,
    IbFcClassOfServices, IbFcRxMTU
        FROM IB-FC-TC-MIB
    ibSan, ibVsanIndex
        FROM IB-VSAN-MIB
    ifIndex
        FROM IF-MIB
    MODULE-COMPLIANCE, OBJECT-GROUP, NOTIFICATION-GROUP
        FROM SNMPv2-CONF;

ibFcFLogin MODULE-IDENTITY
    LAST-UPDATED   "202205091523Z"
    ORGANIZATION
        "Intelbras S.A. Industria de Telecomunicacao Eletronica Brasileria."
    CONTACT-INFO
        ""
    DESCRIPTION
        "This MIB module is for representing fabric login information."
    REVISION "202205091523Z"
    DESCRIPTION
        "This revision is about the node ibFcFLoginMaxNotify."
    REVISION       "201302271100Z"
    DESCRIPTION
        "Initial version of this MIB module."
    ::= { ibSan 3 }

--
-- Node definitions
--
ibFcFLoginMibObjects OBJECT IDENTIFIER ::= { ibFcFLogin 1 }

ibFcFLoginTable OBJECT-TYPE
    SYNTAX SEQUENCE OF IbFcFLoginEntry
    MAX-ACCESS         not-accessible
    STATUS             current
    DESCRIPTION
        "A table of Fibre Channel related service parameters
         used to represent the fabric login information in accord
         with each Nx_Port attached to a particular Fibre Channel
         port in a particular VSAN (Virtual Storage Area Network).

         Each entry is created by a fabric switch when an Nx_Port
         successfully logged in to it explicitly or implicitly,
         and is deleted when the port logged out."
    ::= { ibFcFLoginMibObjects 1 }

ibFcFLoginEntry OBJECT-TYPE
    SYNTAX      IbFcFLoginEntry
    MAX-ACCESS  not-accessible
    STATUS      current
    DESCRIPTION
        "A group of Fibre Channel related service parameters
         used to represent fabric login information of a specific
         Nx_Port."
    INDEX { ifIndex,
            ibVsanIndex,
            ibFcFLoginIndex }
    ::= { ibFcFLoginTable 1 }

IbFcFLoginEntry ::=
    SEQUENCE {
        ibFcFLoginIndex
            IbFcAddressId,
        ibFcFLoginPortNodeWWN
            IbFcNameId,
        ibFcFLoginPortWWN
            IbFcNameId,
        ibFcFLoginPortFcId
            IbFcAddressId,
        ibFcFLoginRxBbCredit
            IbFcBbCredit,
        ibFcFLoginTxBbCredit
            IbFcBbCredit,
        ibFcFLoginClass2RxMTU
            IbFcRxMTU,
        ibFcFLoginClass3RxMTU
            IbFcRxMTU,
        ibFcFLoginSuppClassRequested
            IbFcClassOfServices,
        ibFcFLoginClass2ReqAgreed
            TruthValue,
        ibFcFLoginClass3ReqAgreed
            TruthValue
       }

ibFcFLoginIndex OBJECT-TYPE
    SYNTAX      IbFcAddressId
    MAX-ACCESS  not-accessible
    STATUS      current
    DESCRIPTION
        "The index of current fabric login entry.  The Fibre Channel
         address identifier is used to identify the associated Nx_Port
         of this entry."
    ::= { ibFcFLoginEntry 1 }

ibFcFLoginPortNodeWWN OBJECT-TYPE
    SYNTAX      IbFcNameId
    MAX-ACCESS  read-only
    STATUS      current
    DESCRIPTION
        "The world wide name of the Remote Node to which the
         logged-in Nx_Port belongs."
    ::= { ibFcFLoginEntry 2 }

ibFcFLoginPortWWN OBJECT-TYPE
    SYNTAX      IbFcNameId
    MAX-ACCESS  read-only
    STATUS      current
    DESCRIPTION
        "The world wide name of the logged-in Nx_Port."
    ::= { ibFcFLoginEntry 3 }

ibFcFLoginPortFcId OBJECT-TYPE
    SYNTAX      IbFcAddressId
    MAX-ACCESS  read-only
    STATUS      current
    DESCRIPTION
        "The Fibre Channel address identifier that has been
         assigned by the fabric to the logged-in Nx_Port."
    ::= { ibFcFLoginEntry 4 }

ibFcFLoginRxBbCredit OBJECT-TYPE
    SYNTAX      IbFcBbCredit
    MAX-ACCESS  read-only
    STATUS      current
    DESCRIPTION
        "The maximum number of buffers available for a recipient to
         receive frames from the logged-in Nx_Port in Class2, Class3.
         The object is used in the buffer-to-buffer flow control from
         the logged-in Nx_Port to Fx_Port."
    ::= { ibFcFLoginEntry 5 }

ibFcFLoginTxBbCredit OBJECT-TYPE
    SYNTAX      IbFcBbCredit
    MAX-ACCESS  read-only
    STATUS      current
    DESCRIPTION
        "The total number of buffers available for a sender to transmit
        frames to the logged-in Nx_Port in Class2, Class3.
        The object is used in the buffer-to-buffer flow control from
        Fx_Port to the logged-in Nx_Port."
    ::= { ibFcFLoginEntry 6 }

ibFcFLoginClass2RxMTU OBJECT-TYPE
    SYNTAX      IbFcRxMTU
    MAX-ACCESS  read-only
    STATUS      current
    DESCRIPTION
        "The object specifies the Maximum Transmission Unit of an
         Fibre Channel frame that can be received by the logged-in
         Nx_Port in Class 2 service."
    ::= { ibFcFLoginEntry 7 }

ibFcFLoginClass3RxMTU OBJECT-TYPE
    SYNTAX      IbFcRxMTU
    MAX-ACCESS  read-only
    STATUS      current
    DESCRIPTION
        "The object specifies the Maximum Transmission Unit of an
         Fibre Channel frame that can be received by the logged-in
         Nx_Port in Class 3 service."
    ::= { ibFcFLoginEntry 8 }

ibFcFLoginSuppClassRequested OBJECT-TYPE
    SYNTAX      IbFcClassOfServices
    MAX-ACCESS  read-only
    STATUS      current
    DESCRIPTION
        "The object indicating the supported Classes that the logged-in
         Nx_Port has requested."
    ::= { ibFcFLoginEntry 9 }

ibFcFLoginClass2ReqAgreed OBJECT-TYPE
    SYNTAX      TruthValue
    MAX-ACCESS  read-only
    STATUS      current
    DESCRIPTION
        "The object indicating whether the Fx_Port has agreed to support
         Class 2 delivery that the logged-in Nx_Port requested.  It's
         meaningful only when the Class 2 delivery has been requested."
    ::= { ibFcFLoginEntry 10 }

ibFcFLoginClass3ReqAgreed OBJECT-TYPE
    SYNTAX      TruthValue
    MAX-ACCESS  read-only
    STATUS      current
    DESCRIPTION
        "The object indicating whether the Fx_Port has agreed to support
         Class 3 delivery that the logged-in Nx_Port requested.  It's
         meaningful only when the Class 3 delivery has been requested."
    ::= { ibFcFLoginEntry 11 }

-- ===============================================
-- Begin the ibFcFloginTrapObject.
-- ===============================================

ibFcFloginTrapObject OBJECT IDENTIFIER ::= { ibFcFLoginMibObjects 2 }

ibFcFLoginVsanID OBJECT-TYPE
    SYNTAX Integer32 (1..3839)
    MAX-ACCESS accessible-for-notify
    STATUS current
    DESCRIPTION
        "Vsan ID with a trap."
    ::= { ibFcFloginTrapObject 1 }

ibFcFLoginMaxNum OBJECT-TYPE
    SYNTAX Integer32 (1..65535)
    MAX-ACCESS accessible-for-notify
    STATUS current
    DESCRIPTION
        "Under the current VSAN ID, the maximum number login nodes with a trap."
    ::= { ibFcFloginTrapObject 2 }

-- ===============================================
-- Begin the ibFcFLoginMaxTrapCntl.
-- ===============================================

ibFcFLoginTrapCntl OBJECT IDENTIFIER ::= { ibFcFLoginMibObjects 3 }

ibFcFLoginMaxTrapCntl OBJECT-TYPE
    SYNTAX TruthValue
    MAX-ACCESS read-write
    STATUS current
    DESCRIPTION
        "Indicates whether ibFcFLoginMaxNotify traps should be generated."
    ::= { ibFcFLoginTrapCntl 1 }

-- ================================================
-- definition of traps.
-- ================================================

ibFcFLoginTrap OBJECT IDENTIFIER ::= { ibFcFLoginMibObjects 4 }
ibFcFLoginNotifications OBJECT IDENTIFIER ::= { ibFcFLoginTrap 0 }

ibFcFLoginMaxNotify NOTIFICATION-TYPE
    OBJECTS {
                ibFcFLoginVsanID,
                ibFcFLoginMaxNum
            }
    STATUS     current
    DESCRIPTION
        "This notification is generated when the login number reached the
         maximum."
    ::= { ibFcFLoginNotifications 1 }


-- =======================================
-- Conformance Information
-- =======================================
ibFcFLoginConformance   OBJECT IDENTIFIER
                         ::= { ibFcFLogin 2 }
ibFcFLoginCompliances   OBJECT IDENTIFIER
                         ::= { ibFcFLoginConformance 1 }
ibFcFLoginGroups        OBJECT IDENTIFIER
                         ::= { ibFcFLoginConformance 2 }

-- =======================================
-- Compliance Statements
-- =======================================
ibFcFLoginCompliance MODULE-COMPLIANCE
    STATUS current
    DESCRIPTION
        " "
    MODULE -- this module
    MANDATORY-GROUPS
        {
            ibFcFLoginTableGroup,
            ibFcFLoginTrapObjectGroup,
            ibFcFLoginTrapCntlGroup,
            ibFcFLoginTrapGroup
        }
    ::= { ibFcFLoginCompliances 1 }

ibFcFLoginTableGroup OBJECT-GROUP
    OBJECTS {
                ibFcFLoginPortNodeWWN,
                ibFcFLoginPortWWN,
                ibFcFLoginPortFcId,
                ibFcFLoginRxBbCredit,
                ibFcFLoginTxBbCredit,
                ibFcFLoginClass2RxMTU,
                ibFcFLoginClass3RxMTU,
                ibFcFLoginSuppClassRequested,
                ibFcFLoginClass2ReqAgreed,
                ibFcFLoginClass3ReqAgreed
            }
        STATUS current
        DESCRIPTION
            "A group of Fibre Channel related service parameters
             used to represent fabric login information of a specific
             Nx_Port."
    ::= { ibFcFLoginGroups 1 }


ibFcFLoginTrapObjectGroup OBJECT-GROUP
    OBJECTS {
                ibFcFLoginVsanID,
                ibFcFLoginMaxNum
            }
    STATUS current
    DESCRIPTION
        "The group contains all of trap objects of FcFlogin module."
    ::= { ibFcFLoginGroups 2 }

ibFcFLoginTrapCntlGroup OBJECT-GROUP
    OBJECTS {
                ibFcFLoginMaxTrapCntl
            }
    STATUS current
    DESCRIPTION
        "The group contains all of trap switches of FcFLogin module."
    ::= { ibFcFLoginGroups 3 }

ibFcFLoginTrapGroup  NOTIFICATION-GROUP
    NOTIFICATIONS {
                ibFcFLoginMaxNotify
                  }
    STATUS current
    DESCRIPTION
        "The group contains all of trap of FcFLogin module."
    ::= { ibFcFLoginGroups 4 }

END
