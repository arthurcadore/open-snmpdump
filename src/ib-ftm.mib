-- ============================================================================
-- Copyright (C) 2023 Intelbras S.A. All rights reserved.
--
-- Description: this MIB is a MIB for fabric topology management
--
-- Reference:
-- Version:     V2.3
-- History:
-- V1.0 2004/01/13 created by wangjiao
-- V1.1 2004/06/15 modifyied by huxiaolong
-- V1.2 2004/07/13 modified by huxiaolong add ibFtmUnitRole node
-- V1.3 2004/07/16 add ibFtmUnitRole to IbFtmUnitEntry SEQUENCE { }
--           add ibFtmUnitRole OBJECT
-- V2.0 2004-10-12 updated by gaolong
--      Relocate ibFtmManMIB MODULE-IDENTITY.
--      Change MAX-ACCESS clause value of ibFtmIndex to accessible-for-notify
--      because this index is used when sending trap.
--      Relocate ibFtmManMIBNotification.
--      Add MODULE clause for ibFtmMIBCompliance.
--      Change value of ibFtmAuthMode from underscores to hephens.
-- V2.1 2004-11-20 updated by xuhui
--      Add ibFtmFabricVlanID
-- V2.2 2004-12-22 add ibFtmFabricType node by zhuchaopeng
-- V2.3 2005-03-31 add ibFtmNumberMode by yangjianfeng
-- ============================================================================
IB-FTM-MIB DEFINITIONS ::= BEGIN

        IMPORTS
            ibCommon
                FROM IB-OID-MIB
            OBJECT-GROUP, MODULE-COMPLIANCE, NOTIFICATION-GROUP
                FROM SNMPv2-CONF
            Integer32, OBJECT-TYPE, MODULE-IDENTITY, NOTIFICATION-TYPE
                FROM SNMPv2-SMI;

        ibFtmManMIB MODULE-IDENTITY
            LAST-UPDATED "200401131055Z"        -- January 13, 2004 at 10:55 GMT
            ORGANIZATION
                "Intelbras S.A. Industria de Telecomunicacao Eletronica Brasileria."
            CONTACT-INFO
                ""
            DESCRIPTION
                "this MIB will maintain Fabric topology management.
                 The MIB includes unit-id, unit-name and
                      fabric authentication information."
            ::= { ibFtm 1 }

        ibFtm    OBJECT IDENTIFIER ::= { ibCommon 1 }

--
-- Node definitions
--

        ibFtmManMIBObjects OBJECT IDENTIFIER ::= { ibFtmManMIB 1 }

        ibFtmUnitTable OBJECT-TYPE
            SYNTAX SEQUENCE OF IbFtmUnitEntry
            MAX-ACCESS not-accessible
            STATUS current
            DESCRIPTION
                "A table of informations of XRN-Fabric Unit."
            ::= { ibFtmManMIBObjects 1 }

        ibFtmUnitEntry OBJECT-TYPE
            SYNTAX IbFtmUnitEntry
            MAX-ACCESS not-accessible
            STATUS current
            DESCRIPTION
                "An entry for configuring unit informations of XRN-Fabric."
            INDEX { ibFtmIndex }
            ::= { ibFtmUnitTable 1 }

        IbFtmUnitEntry ::=
            SEQUENCE {
                ibFtmIndex
                    Integer32,
                ibFtmUnitID
                    INTEGER,
                ibFtmUnitName
                    OCTET STRING,
                ibFtmUnitRole
                    INTEGER,
                ibFtmNumberMode
                    INTEGER
             }

        ibFtmIndex OBJECT-TYPE
            SYNTAX Integer32
            MAX-ACCESS accessible-for-notify
            STATUS current
            DESCRIPTION
                "The unique index of a unit."
            ::= { ibFtmUnitEntry 1 }

        ibFtmUnitID OBJECT-TYPE
            SYNTAX INTEGER
            MAX-ACCESS read-write
            STATUS current
            DESCRIPTION
                "Identifer of unit in fabric. Its value should be between 1 and the maximum which defines
                in product specification.
                An exception is described in description of ibFtmNumberMode. In that case, the value
                of this object remains its original value after set to zero.
                "
            ::= { ibFtmUnitEntry 2 }

        ibFtmUnitName OBJECT-TYPE
            SYNTAX OCTET STRING
            MAX-ACCESS read-write
            STATUS current
            DESCRIPTION
                "Name of unit in XRN-Fabric. It consists of no more than 64 characters."
            ::= { ibFtmUnitEntry 3 }

        ibFtmUnitRole OBJECT-TYPE
            SYNTAX INTEGER
            {
                master(0),   -- master unit
                slave(1)     -- slave unit
            }
            MAX-ACCESS read-only
            STATUS current
            DESCRIPTION
                "Role of unit in XRN-Fabric. One unit in a XRN-Fabric acts as master role and others
                act as slave roles"
            ::= { ibFtmUnitEntry 4 }

        ibFtmNumberMode OBJECT-TYPE
            SYNTAX INTEGER
            {
                automatic(0),
                manual (1)
            }
            MAX-ACCESS read-only
            STATUS current
            DESCRIPTION
                "Numbering Mode of unit in XRN-Fabric.  If the unit ID is assigned by the auto
                numbering algorithm, the numbering mode will be automatic numbering; if the
                unit ID (ibFtmUnitID) is assigned by the user, the numbering mode will be manual
                numbering; if ibFtmUnitID is set to be zero, the numbering mode will become
                automatic numbering."
            ::= { ibFtmUnitEntry 5 }

        ibFtmAuthMode OBJECT-TYPE
            SYNTAX INTEGER
                {
                ftm-none(0),
                ftm-simple(1),
                ftm-md5(2)
                }
            MAX-ACCESS read-write
            STATUS current
            DESCRIPTION
                "Authentication mode of XRN-Fabric."
            ::= { ibFtmManMIBObjects 2 }

        ibFtmAuthValue OBJECT-TYPE
            SYNTAX OCTET STRING
            MAX-ACCESS read-write
            STATUS current
            DESCRIPTION
                "Authentication value of XRN-Fabric Feature. ftm_none mode means no authentication.
                In simple mode, the value is password of a string of 1 to 16 charactors.
                While in md5 mode, the value is key of a string within 16 charactors."
            ::= { ibFtmManMIBObjects 3 }

        ibFtmFabricVlanID OBJECT-TYPE
            SYNTAX INTEGER(2..4094)
            MAX-ACCESS read-write
            STATUS current
            DESCRIPTION
                "The object is used for get and set the Fabric VlanID.
                Only is the equipment not in the stacking status, the value can be set."
            ::= { ibFtmManMIBObjects 4 }

        ibFtmFabricType OBJECT-TYPE
            SYNTAX INTEGER
                {
                outofStack(1),
                line(2),
                ring(3),
                mesh(4)
                }
            MAX-ACCESS read-only
            STATUS current
            DESCRIPTION
                "Topology type of Fabric.
                outofStack means this unit is not in stack."
            ::= { ibFtmManMIBObjects 5 }

        ibFtmManMIBNotification OBJECT IDENTIFIER ::= { ibFtmManMIB 3 }

        ibFtmUnitIDChange NOTIFICATION-TYPE
            OBJECTS { ibFtmIndex, ibFtmUnitID}
            STATUS current
            DESCRIPTION
                "When unit id changes in fabric, this trap is sent with unit index and its new id ."
            ::= { ibFtmManMIBNotification 1 }

        ibFtmUnitNameChange NOTIFICATION-TYPE
            OBJECTS { ibFtmIndex, ibFtmUnitName }
            STATUS current
            DESCRIPTION
                "When unit name changes in fabric, this trap is sent with unit index and its new name."
            ::= { ibFtmManMIBNotification 2 }

        ibFtmManMIBComformance OBJECT IDENTIFIER ::= { ibFtmManMIB 2 }

        ibFtmMIBCompliances OBJECT IDENTIFIER ::= { ibFtmManMIBComformance 1 }

        ibFtmMIBCompliance MODULE-COMPLIANCE
            STATUS current
            DESCRIPTION
                "The compliance statement for FTM implementing the MIB."
            MODULE IB-FTM-MIB
                MANDATORY-GROUPS { ibFtmConfigGroup, ibFtmNotificationGroup
                     }
            ::= { ibFtmMIBCompliances 1 }

        ibFtmMIBGroups OBJECT IDENTIFIER ::= { ibFtmManMIBComformance 2 }

        ibFtmConfigGroup OBJECT-GROUP
            OBJECTS { ibFtmUnitID, ibFtmUnitName, ibFtmAuthMode, ibFtmAuthValue, ibFtmFabricVlanID,
                      ibFtmFabricType }
            STATUS current
            DESCRIPTION
                "The basic collection of objects for sending trap of FTM Management."
            ::= { ibFtmMIBGroups 1 }

        ibFtmNotificationGroup NOTIFICATION-GROUP
            NOTIFICATIONS { ibFtmUnitIDChange, ibFtmUnitNameChange }
            STATUS current
            DESCRIPTION
                "The basic collection of objects for sending trap of FTM Management."
            ::= { ibFtmMIBGroups 2 }

END
