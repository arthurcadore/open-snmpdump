-- =====================================================================
-- Copyright (C) 2023 Intelbras S.A. All rights reserved.
--
-- Description: STRUNK MIB
-- Reference:
-- Version: V1.0
-- History:
--   V1.0 Initial version, created by wangmeng
-- =====================================================================
IB-STRUNK-MIB DEFINITIONS ::= BEGIN

IMPORTS
    ibCommon
        FROM IB-OID-MIB
    Integer32, OBJECT-TYPE,NOTIFICATION-TYPE,MODULE-IDENTITY
        FROM SNMPv2-SMI;

ibStrunk MODULE-IDENTITY
    LAST-UPDATED "202107191126Z"    -- July 19, 2021 at 11:26 GMT
    ORGANIZATION
        "Intelbras S.A. Industria de Telecomunicacao Eletronica Brasileria."
    CONTACT-INFO
        ""
    DESCRIPTION
        "
        Smart Trunk (S-Trunk) is used on two PEs that provide dual-homed
        access for a CE for link and node redundancy. It virtualizes two
        PEs into one system through a multichassis link aggregation
        called smart trunk.
        "

    REVISION "202107191126Z"
    DESCRIPTION
        "The initial revision of this MIB module."
    ::= { ibCommon 208 }


-- trap --
ibStrunkTrap      OBJECT IDENTIFIER ::= { ibStrunk 1 }


-- All trap definitions should be placed under this object.
ibStrunkTrapPrex OBJECT IDENTIFIER ::= { ibStrunkTrap 0 }

ibStrunkMemberStatusChange NOTIFICATION-TYPE
    OBJECTS
        {   ibStrunkMemberType,
            ibStrunkMemberId,
            ibStrunkMemberStatus,
            ibStrunkMemberReason
        }
    STATUS       current
    DESCRIPTION
        "This trap indicates that S-Trunk member role changed."
    ::= { ibStrunkTrapPrex 1 }

ibStrunkStatusChange NOTIFICATION-TYPE
    OBJECTS {   ibStrunkGroupId,
                ibStrunkGroupStatus,
                ibStrunkGroupReason
            }
    STATUS       current
    DESCRIPTION
        "This trap indicates that S-Trunk Group role changed."
    ::= { ibStrunkTrapPrex 2 }

-- All objects used for TRAP only are defined here.
ibStrunkTrapOjbects OBJECT IDENTIFIER ::= { ibStrunkTrap 1 }

ibStrunkMemberType OBJECT-TYPE
    SYNTAX  INTEGER {
         bagg(1),
         ragg(2)
     }
    MAX-ACCESS   accessible-for-notify
    STATUS       current
    DESCRIPTION
        "The member type of the S-Trunk.
        bagg: The bridge aggregation type.
        ragg: The route aggregation type."
    ::= { ibStrunkTrapOjbects 1 }

ibStrunkMemberId OBJECT-TYPE
    SYNTAX       Integer32
    MAX-ACCESS   accessible-for-notify
    STATUS       current
    DESCRIPTION
        "The member id of the S-Trunk."
    ::= { ibStrunkTrapOjbects 2 }

ibStrunkMemberStatus OBJECT-TYPE
    SYNTAX  INTEGER {
         primary(1),
         secondary(2)
     }
    MAX-ACCESS   accessible-for-notify
    STATUS       current
    DESCRIPTION
        "The status of the S-Trunk.
        primary: The S-Trunk member is primary role.
        secondary: The S-Trunk member is secondary role."
    ::= { ibStrunkTrapOjbects 3 }

ibStrunkMemberReason OBJECT-TYPE
    SYNTAX OCTET STRING (SIZE (0..255))
    MAX-ACCESS   accessible-for-notify
    STATUS       current
    DESCRIPTION
        " The S-Trunk member change reason."
    ::= { ibStrunkTrapOjbects 4 }

ibStrunkGroupId OBJECT-TYPE
    SYNTAX Integer32
    MAX-ACCESS   accessible-for-notify
    STATUS       current
    DESCRIPTION
        " The group id of the S-Trunk."
    ::= { ibStrunkTrapOjbects 5 }

ibStrunkGroupStatus OBJECT-TYPE
    SYNTAX  INTEGER {
            init(1),
            primary(2),
            secondary(3)
        }
    MAX-ACCESS   accessible-for-notify
    STATUS       current
    DESCRIPTION
        "The group status of the S-Trunk.
        init: The S-Trunk group is primary role.
        primary: The S-Trunk group is primary role.
        secondary: The S-Trunk group is secondary role."
    ::= { ibStrunkTrapOjbects 6 }

ibStrunkGroupReason OBJECT-TYPE
    SYNTAX OCTET STRING (SIZE (0..255))
    MAX-ACCESS   accessible-for-notify
    STATUS       current
    DESCRIPTION
        " The S-Trunk group change reason."
    ::= { ibStrunkTrapOjbects 7 }
END
