-- ============================================================================
-- Copyright (C) 2023 Intelbras S.A. All rights reserved.
--
-- Description: 802.1 QinQv2 MIB Version 1
-- Reference:
-- Version: V1.0
-- History:
-- V1.0 Initial version Created by XiaoRen Yang, 2013.3.8
-- ==================================================================
IB-QINQV2-MIB DEFINITIONS ::= BEGIN
IMPORTS
    ibCommon
        FROM IB-OID-MIB
    TruthValue
        FROM SNMPv2-TC
    MODULE-IDENTITY, OBJECT-TYPE, Integer32
        FROM SNMPv2-SMI
    ifIndex
        FROM IF-MIB;

-- ==================================================================
--
-- module identity part
--
-- ==================================================================
ibQinQv2 MODULE-IDENTITY
    LAST-UPDATED
        "201303080000Z"
    ORGANIZATION
        "Intelbras S.A. Industria de Telecomunicacao Eletronica Brasileria."
    CONTACT-INFO
        ""
    DESCRIPTION
        "802.1 QinQv2 MIB Version 1"
    REVISION
        "201303080000Z"
    DESCRIPTION
        "The initial version of this MIB module."
    ::= { ibCommon 137 }

-- ==================================================================
--
-- =====================object definition begin======================
--
-- ==================================================================
ibQinQv2MibObject OBJECT IDENTIFIER ::= { ibQinQv2 1 }

ibQinQv2ScalarObjects OBJECT IDENTIFIER ::= { ibQinQv2MibObject 1 }

ibQinQv2ServiceTPID  OBJECT-TYPE
    SYNTAX      Integer32 (1..65535)
    MAX-ACCESS  read-write
    STATUS      current
    DESCRIPTION
        "TPID globally configured for service VLAN tags.  The global TPID value
        for service VLAN tags does not take effect on interfaces where
        ibQinQIfServiceTPID is configured.
        By default, the global TPID for service VLAN tags is 0x8100."
    ::= { ibQinQv2ScalarObjects 1 }

ibQinQv2CustomerTPID  OBJECT-TYPE
    SYNTAX      Integer32 (1..65535)
    MAX-ACCESS  read-write
    STATUS      current
    DESCRIPTION
        "TPID globally configured for customer VLAN tags.  The global TPID value
        for customer VLAN tags does not take effect on interfaces where
        ibQinQIfCustomerTPID is configured.
        By default, the global TPID for customer VLAN tags is 0x8100."
    ::= { ibQinQv2ScalarObjects 2 }

ibQinQv2IfCfgTable  OBJECT-TYPE
    SYNTAX      SEQUENCE OF IbQinQv2IfCfgEntry
    MAX-ACCESS  not-accessible
    STATUS      current
    DESCRIPTION
        "802.1 QinQ configuration table."
    ::= { ibQinQv2MibObject 2 }

ibQinQv2IfCfgEntry OBJECT-TYPE
    SYNTAX      IbQinQv2IfCfgEntry
    MAX-ACCESS  not-accessible
    STATUS      current
    DESCRIPTION
        "802.1 QinQ configuration entries."
    INDEX { ifIndex }
    ::= { ibQinQv2IfCfgTable 1 }

IbQinQv2IfCfgEntry ::=
    SEQUENCE
    {
        ibQinQv2IfState           TruthValue,
        ibQinQv2IfServiceTPID     Integer32,
        ibQinQv2IfCustomerTPID    Integer32,
        ibQinQv2IfTransVlanList   OCTET STRING
    }

ibQinQv2IfState OBJECT-TYPE
    SYNTAX      TruthValue
    MAX-ACCESS  read-write
    STATUS      current
    DESCRIPTION
        "802.1 QinQ functions on the port.
         The value is false by default."
    DEFVAL { false }
    ::= { ibQinQv2IfCfgEntry 1 }

ibQinQv2IfServiceTPID    OBJECT-TYPE
    SYNTAX      Integer32 (1..65535)
    MAX-ACCESS  read-write
    STATUS      current
    DESCRIPTION
        "Service TPID value on the port."
    ::= { ibQinQv2IfCfgEntry 2 }

ibQinQv2IfCustomerTPID    OBJECT-TYPE
    SYNTAX      Integer32 (1..65535)
    MAX-ACCESS  read-write
    STATUS      current
    DESCRIPTION
        "Customer TPID value on the port."
    ::= { ibQinQv2IfCfgEntry 3 }

ibQinQv2IfTransVlanList    OBJECT-TYPE
    SYNTAX      OCTET STRING (SIZE(512))
    MAX-ACCESS  read-write
    STATUS      current
    DESCRIPTION
        "Transparent VLANs described as a bitmap.  Each octet within this value
        specifies a set of eight VLANs.  The first octet specifies VLANs 1
        through 8.  The second octet specifies VLANs 9 through 16, and so on.
        Within each octet, the most significant bit represents the highest
        numbered VLAN, and the least significant bit represents the lowest
        numbered VLAN."
    ::= { ibQinQv2IfCfgEntry 4 }

END
