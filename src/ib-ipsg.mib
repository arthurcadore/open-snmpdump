-- ============================================================================
-- Copyright (C) 2023 Intelbras S.A. All rights reserved.
--
-- Description: The purpose of this MIB file is to provide the definition of
--              the Ip Source Guard trap.
-- Reference:
-- Version: V1.1
-- History:
-- V1.0 2022-07-27
--   Initial version, created by wangyuqing
-- V1.1 2022-12-22
--   Add 'ibIpsgVlanDropAlarm'
--   And 'ibIpsgVlanDropAlarmResume'
--   And 'ibIpsgDropVlan'
--   And 'ibIpsgChassis'
--   And 'ibIpsgSlot' by wangyuqing
-- ============================================================================
IB-IPSG-MIB DEFINITIONS ::= BEGIN

IMPORTS
        ibCommon
    FROM IB-OID-MIB
        Unsigned32, OBJECT-TYPE, MODULE-IDENTITY, NOTIFICATION-TYPE
    FROM SNMPv2-SMI
        InetAddressType
    FROM INET-ADDRESS-MIB;

-- Node definitions
ibIpsg MODULE-IDENTITY
    LAST-UPDATED "202212221800Z"        -- DEC 22, 2022 at 18:00 GMT
    ORGANIZATION
        "Intelbras S.A. Industria de Telecomunicacao Eletronica Brasileria."
    CONTACT-INFO
        ""
    DESCRIPTION
        "This MIB file is to provide the definition of the Ip Source Guard."
    REVISION "202212221800Z"
    DESCRIPTION
        "Add the objects of ibIpsgVlanDropAlarm, ibIpsgVlanDropAlarmResume,
        ibIpsgChassis, ibIpsgSlot and ibIpsgDropVlan."
    REVISION "202207271800Z"
    DESCRIPTION
        "The initial version of this MIB file."
    ::= { ibCommon 246}

-- ibIpsgTrapPkt
ibIpsgTrapPkt OBJECT IDENTIFIER ::= { ibIpsg 1 }

ibIpsgTrapPkts OBJECT IDENTIFIER  ::= { ibIpsgTrapPkt 0 }

ibIpsgDropAlarm NOTIFICATION-TYPE
    OBJECTS
        {
            ibIpsgDropFamily,
            ibIpsgDropIfName,
            ibIpsgDropThreshold,
            ibIpsgChassis,
            ibIpsgSlot
        }
    STATUS      current
    DESCRIPTION
        "If the number of packets discarded by Ip Source Guard on an interface exceeds the threshold,
         a trap message is generated and sent to the remote monitoring device."
    ::= { ibIpsgTrapPkts 1 }

ibIpsgDropAlarmResume NOTIFICATION-TYPE
    OBJECTS
        {
            ibIpsgDropFamily,
            ibIpsgDropIfName,
            ibIpsgDropThreshold,
            ibIpsgChassis,
            ibIpsgSlot
        }
    STATUS      current
    DESCRIPTION
        "If the number of packets discarded by Ip Source Guard on an interface drops below the threshold,
         a trap message is generated and sent to the remote monitoring device."
    ::= { ibIpsgTrapPkts 2 }

ibIpsgVlanDropAlarm NOTIFICATION-TYPE
    OBJECTS
        {
            ibIpsgDropFamily,
            ibIpsgDropVlan,
            ibIpsgDropThreshold,
            ibIpsgChassis,
            ibIpsgSlot
        }
    STATUS      current
    DESCRIPTION
        "If the number of packets discarded by Ip Source Guard on the vlan exceeds the threshold,
         a trap message is generated and sent to the remote monitoring device."
    ::= { ibIpsgTrapPkts 3 }

ibIpsgVlanDropAlarmResume NOTIFICATION-TYPE
    OBJECTS
        {
            ibIpsgDropFamily,
            ibIpsgDropVlan,
            ibIpsgDropThreshold,
            ibIpsgChassis,
            ibIpsgSlot
        }
    STATUS      current
    DESCRIPTION
        "If the number of packets discarded by Ip Source Guard on the vlan drops below the threshold,
         a trap message is generated and sent to the remote monitoring device."
    ::= { ibIpsgTrapPkts 4 }

ibIpsgTrapPktObjects OBJECT IDENTIFIER  ::= { ibIpsgTrapPkt 1 }

-- ibIpsgTrapPktObjects

ibIpsgDropFamily OBJECT-TYPE
    SYNTAX      InetAddressType
    MAX-ACCESS  accessible-for-notify
    STATUS      current
    DESCRIPTION
        "The protocol family may be ipv4 or ipv6 ."
    ::= { ibIpsgTrapPktObjects 1 }

ibIpsgDropIfName OBJECT-TYPE
    SYNTAX      OCTET STRING(SIZE (0..255))
    MAX-ACCESS  accessible-for-notify
    STATUS      current
    DESCRIPTION
        "The information of interface name."
    ::= { ibIpsgTrapPktObjects 2 }

ibIpsgDropThreshold OBJECT-TYPE
    SYNTAX      Unsigned32
    MAX-ACCESS  accessible-for-notify
    STATUS      current
    DESCRIPTION
        "The information of Threshold."
    ::= { ibIpsgTrapPktObjects 3 }

ibIpsgDropVlan OBJECT-TYPE
    SYNTAX      Unsigned32(1..4094)
    MAX-ACCESS  accessible-for-notify
    STATUS      current
    DESCRIPTION
        "The information of vlan id."
    ::= { ibIpsgTrapPktObjects 4 }

ibIpsgChassis OBJECT-TYPE
    SYNTAX      Unsigned32
    MAX-ACCESS  accessible-for-notify
    STATUS      current
    DESCRIPTION
        "The information of chassis ID. If the value is 65535, the device is
        not a stacked device ."
    ::= { ibIpsgTrapPktObjects 5 }

ibIpsgSlot OBJECT-TYPE
    SYNTAX      Unsigned32
    MAX-ACCESS  accessible-for-notify
    STATUS      current
    DESCRIPTION
        "The information of slot."
    ::= { ibIpsgTrapPktObjects 6 }

END
