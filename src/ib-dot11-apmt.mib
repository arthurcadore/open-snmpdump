-- =============================================================================
-- Copyright (C) 2023 Intelbras S.A. All rights reserved.
--
-- Description:
--   The file defines a MIB to provide AP object information such as
--   performance statistic and notification events.
-- Reference:
-- Version: V3.7
-- History:
--   V1.0 2006-05-10 Initial version, created by shiyang (Richard)
--   V1.1 2007-02-01 modified by xingjichen(Daniel)
--        Changed DESCRIPTION of ibDot11APRxStatisTable,
--        ibDot11APTxStatisTable,ibDot11APMtRadioFailTrap,
--        ibDot11APMtRadioFailRecoverTrap.
--   V1.2 2007-04-27 modified by shiyang(Richard)
--        Add new nodes of ibDot11APChannelChgMode and ibDot11APChgWorkMode.
--        Split ibDot11APObjectTable table into ibDot11APObjectStatusTable
--        and ibDot11APObjectTable.
--        Rename ibDot11APRadioRelationTable as ibDot11APRadioTable.
--        Rename ibDot11APBSSRelationTable as ibDot11APBSSTable.
--   V1.3 2007-06-19 modified by Banasree
--        Add new table of ibDot11APIfTable for ibDot11APObjectGroup.
--        Add new table of ibDot11APAssocStatisTable for ibDot11APStatisGroup.
--        Add new node of ibDot11CurrAPName, ibDot11CurrAPModelName,
--        ibDot11CurrAPImageName, ibDot11CurrAPSoftwareVersion,
--        ibDot11CurrAPIPNetMask, ibDot11CurrRadioModeSupport for
--        ibDot11APObjectTable.
--        Add new node of ibDot11Channel, ibDot11TxPowerLevel,
--        ibDot11APRadioIfIndex, ibDot11AntennaGain for ibDot11APRadioTable.
--        Add new node of ibDot11APManufacturer, ibDot11APCPUType,
--        ibDot11APCPUClockSpeed, ibDot11APMemoryType, ibDot11APMemorySize,
--        ibDot11APFlashType, ibDot11APFlashSize for ibDot11APModelTable
--        Add ibDot11APReset node to the ibDot11APObjectStatusTable.
--        Add ibDot11RxFrameErrorRatio to the ibDot11APRxStatisTable.
--        Add_ibDot11TxFrameRetryRatio to the ibDot11APTxStatisTable.
--   V1.4 2007-12-21 modified by wanghao (Kumar)
--        Add ibDot11BSSRxStatisTable, ibDot11BSSTxStatisTable,
--        ibDot11BSSAssocStatisTable for BSS statistics.
--        Add ibDot11APCpuUsage to ibDot11APObjectStatusTable.
--        Add ibDot11MaxBandwidth to ibDot11APRadioTable.
--        Add ibDot11RxPhyErrorCnt, ibDot11RxMICErrorCnt,
--        ibDot11RxDataFrameBytes to ibDot11APRxStatisTable.
--        Add ibDot11TxDataFrameCnt, ibDot11TxDataFrameBytes to
--        ibDot11APTxStatisTable.
--        Add ibDot11ApStationExDeAuthenSum, ibDot11ApStationCurAssocSum to
--        ibDot11APAssocStatisTable.
--   V1.5 2008-02-25 modified by wanghao (Kumar)
--        Add ibDot11ResourceUseRatio to ibDot11APRadioTable.
--   V1.6 2008-07-09 modified by ChangHuifeng
--        Add ibDot11APConnectionType to ibDot11APObjectStatusTable.
--   V1.7 2008-11-07 modified by Wang Lu and Li Yugang
--        Add ibDot11APLinkStatisTable and ibDot11RadioAssocStatisTable.
--        Add ibDot11CurrIfNumber to ibDot11APObjectTable.
--        Add ibDot11RadioModeSupport, ibDot11TxPowerLevel2 and
--        ibDot11PowerMgmtStatus to ibDot11APRadioTable.
--        Add ibDot11SSID to ibDot11APBSSTable.
--        Add ibDot11APIfSpeed, ibDot11APIfInDataRate and
--        ibDot11APIfOutDataRate to ibDot11APIfTable
--        Add ibDot11RadioRxAverSnr to ibDot11APRxStatisTable.
--        Add ibDot11APMtTimeSynFail, ibDot11APMtChlIntfDetected,
--        ibDot11APMtIntfAPDetected, ibDot11APMtIntfStaDetected,
--        ibDot11APMtIPChange, ibDot11APFlashWriteFailure,
--        ibDot11APSysReboot, ibDot11APMtAvailChlTooLow and
--        ibDot11APImgDwldSuccess to ibDot11APMtTraps.
--        Add ibDot11APIntfDevMACAddress and ibDot11APMtTrapOldIPAddr to
--        ibDot11APMtTrapVarObjects.
--        Add ibDot11ChannelSwitchTimes to ibDot11APRadioTable.
--        Add ibDot11RxPayloadBytes, ibDot11RxTrafficSpeed to
--        ibDot11APRxStatisTable.
--        Add ibDot11TxMSDUCnt, ibDot11TxDiscardMSDUCnt,
--        ibDot11RetryMSDUCnt, ibDot11TxPayloadBytes,
--        ibDot11TxTrafficSpeed to ibDot11APTxStatisTable.
--        Add ibDot11ApStaCurAuthSuccSum, ibDot11AllStationUpSumTime,
--        ibDot11ApStationAssocReqSum to ibDot11APAssocStatisTable.
--        Add ibDot11BSSRxFrameErrorRatio, ibDot11BSSRxPayloadBytes to
--        ibDot11BSSRxStatisTable.
--        Add ibDot11BSSTxPayloadBytes to ibDot11BSSTxStatisTable.
--        Add ibDot11BSSStationAssocReqSum to ibDot11BSSAssocStatisTable.
--        Add new tables ibDot11RadioMngFrameStatisTable,
--        ibDot11APAuthFailStatisTable, ibDot11APAssocFailStatisTable,
--        ibDot11APReassocStatisTable, ibDot11APUserAuthStatisTable,
--        ibDot11APDeauthStatisTable, ibDot11APDeassocStatisTable to
--        ibDot11APStatisGroup.
--   V1.8 2009-04-17 modified by WangChunsheng
--        Add ibDot11AntennaType to ibDot11APRadioTable.
--   V1.9 2009-05-07 modified by Li Yugang, Wang Shaojie, Jin Yi
--        Add ibDot11CurrAPElementID to ibDot11APObjectTable.
--        Add ibDot11DiversitySelectionRx, ibDot11MaxTxPwrLvl,
--        ibDot11PwrAttRange, ibDot11AvgRxSignalStrength,
--        ibDot11HighestRxSignalStrength, ibDot11LowestRxSignalStrength
--        ibDot11RadioIfUpdownTimes, ibDot11RadioIfLastChange
--        to ibDot11APRadioTable.
--        Add ibDot11CurrSSIDResourceUseRatio to ibDot11APBSSTable.
--        Add new table ibDot11APSSIDObjectTable, ibDot11APSysInfoTable
--        to ibDot11APObjectGroup.
--        Add ibDot11TxErrFrameRatio, ibDot11TxFrameRate
--        to ibDot11APTxStatisTable.
--        Add ibDot11BSSRxUniFrameCnt, ibDot11BSSRxNonUniFrameCnt,
--        ibDot11BSSRxAuthenFrameCnt to ibDot11BSSRxStatisTable.
--        Add ibDot11BSSTxRetryCnt, ibDot11BSSTxUniFrameCnt,
--        ibDot11BSSTxNonUniFrameCnt, ibDot11BSSTxAuthenFrameCnt
--        to ibDot11BSSTxStatisTable.
--        Add new table ibDot11APAssocFailStatis2Table, ibDot11APIfStatisTable
--        to ibDot11APStatisGroup.
--        Add ibDot11APInterfDetectedTrap,
--        ibDot11APInterfClearTrap, ibDot11StaInterfDetectedTrap,
--        ibDot11StaInterfClearTrap, ibDot11OtherDevIntDetectedTrap,
--        ibDot11OtherDevIntClearTrap, ibDot11APModuleTroubleTrap,
--        ibDot11APModuleTroubleClearTrap, ibDot11APRadioDownTrap,
--        ibDot11APRadioDownRecovTrap, ibDot11APStaFullTrap,
--        ibDot11APStaFullRecoverTrap, ibDot11DFSFreeCntBelowThrRecov,
--        ibDot11APCpuUsageHigh, ibDot11APCpuUsageHighRecover,
--        ibDot11APMemUsageHigh, ibDot11APMemUsageHighRecover
--        to ibDot11APMtTraps.
--        Add ibDot11CurrInterfDetectedNum, ibDot11StaFullReason,
--        ibDot11StaLimitNumber, ibDot11APRadioDownReason,
--        ibDot11InterfMacList to ibDot11APMtTrapVarObjects.
--        Add ibDot11APLastImgDownloadTime to ibDot11APObjectStatusTable.
--   V2.0 2009-07-29 modified by Heziqi
--        Add new node ibDot11CurrAPMode for ibDot11APObjectTable.
--        Add new node ibDot11APEssVlanId and ibDot11APBSSResourceUseRatio
--        for ibDot11APBSSTable.
--        Add new node ibDot11APTrapUserCnt and ibDot11APTrapUserThreshold
--        for ibDot11APMtTrapVarObjects.
--        Add ibDot11APUserCntOverFlow for ibDot11APMtNotifyGroup.
--        Add new node ibDot11TxDiscardFrameRatio, ibDot11TxFrameRate,
--        ibDot11TxMgtFrameCnt and ibDot11TxCtrlFrameCnt
--        for ibDot11APTxStatisTable.
--        Add new node ibDot11APIPv6Address for ibDot11APObjectStatusTable.
--        Add new node ibDot11CurrAPIPv6Address for ibDot11APObjectTable.
--        Add ibDot11RadioMngFrmStatisTable.
--   V2.1 2009-08-07 modified by wang shaojie, Jin Yi
--        Add ibDot11APIfInBrdcastPkts, ibDot11APIfOutBrdcastPkts,
--        ibDot11APIfInMulcastPkts, ibDot11APIfOutMulcastPkts,
--        ibDot11APIfInPayloadOctets, ibDot11APIfOutPayloadOctets to
--        ibDot11APIfStatisTable.
--        Add new node ibDot11APLastRegisterTime to ibDot11APObjectStatusTable
--        Add new node ibDot11TxMACErrCnt, ibDot11TxErrFrameCnt to
--        ibDot11APTxStatisTable.
--        Add new variable bindings ibDot11APMtChanlChgCount to
--        ibDot11APMtRdoChanlChgTrap.
--   V2.2 2009-12-01 modified by Wang Shaojie, duyanbing
--        Add new table ibDot11APIdleListTable to ibDot11APObjectGroup.
--        Add new table ibDot11APPacketSizeStatisTable,
--        ibDot11APPacketRateStatisTable, ibDot11APPacketMCSRateStatisTable to
--        ibDot11APStatisGroup.
--        Add new node ibDot11RxUcastDataFrameCnt, ibDot11RxNUcastDataFrameCnt
--        to ibDot11APRxStatisTable.
--        Add new node ibDot11TxUcastDataFrameCnt, ibDot11TxNUcastDataFrameCnt
--        to ibDot11APTxStatisTable.
--        Add new node ibDot11CurrAPSSIDNumber to ibDot11APObjectTable.
--        Add new node ibDot11AllStationUpSumTimeTicks to
--        ibDot11APAssocStatisTable
--        Add new node ibDot11RxTotalDiscardFrameCnt to ibDot11APRxStatisTable.
--        Added ibDot11APMtTrapSwitch.
--        2010-02-23 modified by Wang Shaojie
--        Add ibDot11APMtDetectedIntfAP, ibDot11APMtDetectedIntfSTA,
--        ibDot11APMtDetectedIntfOtherDev to ibDot11APMtTraps.
--        Add ibDot11APMtFormerApVersion, ibDot11APMtAPID, ibDot11APMtRadioID
--        ibDot11APMtChannel, ibDot11APMtInterfMacAdd to
--        ibDot11APMtTrapVarObjects.
--        2010-03-15 modified by Deng Gaoliang
--        Add ibDot11APAssocFailStatis3Table
--        Add ibDot11APFlashSizeInBytes
--        Remove ibDot11APMtTrapSwitch
--        2010-05-31 modified by LiuChen, Wang Chunsheng, Wang Shaojie
--        Add new table ibDot11APSysInfoByAPIDTable.
--        Add new node ibDot11CurrAPManufacturer, ibDot11CurrAPMemorySize,
--        ibDot11CurrAPMemSizeInBytes, ibDot11CurrAPFlashSize,
--        ibDot11CurrAPFlashSizeInBytes to ibDot11APObjectTable.
--        Add new table ibDot11APUserSecAuthStatisTable to ibDot11APStatisGroup.
--        Add new table ibDot11APUserInfoStatisTable to ibDot11APStatisGroup.
--        2010-08-05 modified by LiuChen, Yinjunjie
--        Add new node ibDot11CurrAPReleasedVersion to ibDot11APObjectTable.
--        Add new node ibDot11BSSStationCurAuthSum to ibDot11BSSAssocStatisTable.
--        Add new node ibDot11APMtAdjChannel.
--        Add ibDot11DetcAdjChlIntfAP, ibDot11DetcAdjChlIntfAPClear
--        to ibDot11APMtTraps.
--        2010-08-05 modified by Yinjunjie
--        Add new table ibDot11APReassocStatis2Table
--        2010-09-16 Change names from ibDot11APIfLastChange and
--        ibDot11APIfLastChange2 to ibDot11APIfStatusKeepTime and
--        ibDot11APIfStatusKeepTime2 by shuaixiaojuan
--   V2.3 2010-10-11 modified by Wuxiaopeng
--        Add new node ibDot11APIfInDataOctets2, ibDot11APIfOutDataOctets2,
--        to ibDot11APIfStatisByAPIDTable.
--        Add new node ibDot11APMacAddress2 to ibDot11APSysInfoByAPIDTable.
--        Modify node ibDot11APChgWorkMode.
--   V2.4 2011-07-13 modified by Yu Bo
--        Add new node ibDot11RxTotalIPCheckErrPacketCnt to ibDot11APRxStatisTable
--        Add new node ibDot11APConfigPortalStaNum to ibDot11APSSIDObjectTable
--        2011-08-08 modified by Donglaqi
--        Add new node ibDot11AllUserOnlineTime to ibDot11APUserSecAuthStatisTable
--        2011-08-10 modified by limingjin
--        Add new node ibDot11RadioModeSupport2 to ibDot11APRadioTable
--        Add new node ibDot11CurrRadioModeSupport2 to ibDot11APObjectTable
--   V2.5 2011-09-27 modified by Limingjin
--        Add ibDot11TrafficTable
--        2011-09-28 modified by Li Honghao & jiaolibin
--        Add new table ibDot11APEchoStatisTable
--        Add ibDot11APEchoAvgDelay, ibDot11APEchoRequestCnt,
--        ibDot11APEchoRespLossCnt to ibDot11APEchoStatisTable
--        Add ibDot11APMtFirstTrapTime to ibDot11APMtTrapVarObjects and
--        varialbe bindings ibDot11APMtFirstTrapTime for
--        ibDot11APInterfClearTrap, ibDot11StaInterfDetectedTrap,
--        ibDot11StaInterfClearTrap, ibDot11OtherDevIntDetectedTrap,
--        ibDot11OtherDevIntClearTrap, ibDot11APRadioDownTrap ,
--        ibDot11APRadioDownRecovTrap, ibDot11APStaFullTrap,
--        ibDot11APStaFullRecoverTrap, ibDot11APMtDetectedIntfAP,
--        ibDot11DetcAdjChlIntfAP, ibDot11DetcAdjChlIntfAPClear,
--        ibDot11APMtDetectedIntfSTA
--   V2.6 2012-05-08 modified by Lihonghao
--        Add new table ibDot11APUserSecAuthTypeStatisTable
--        Add ibDot11APPortalOnlineUserNum, ibDot11APAuthFreeOnlineUserNum,
--        ibDot11APAssocAuthOnlineUserNum, ibDot11APMacAuthOnlineUserNum,
--        ibDot11APAllPortalUserOnlineTime, ibDot11APAllAuthFreeUserOnlineTime,
--        ibDot11APAllAssocAuthUserOnlineTime, ibDot11APAllMacAuthUserOnlineTime,
--        ibDot11APPortalUserLostCnntCnt, ibDot11APAuthFreeUserLostCnntCnt,
--        ibDot11APAssocAuthUserLostCnntCnt, ibDot11APMacAuthUserLostCnntCnt,
--        ibDot11APPortalAuthReqCnt, ibDot11APAssocAuthReqCnt,
--        ibDot11APMacAuthReqCnt, ibDot11APPortalAuthSucCnt,
--        ibDot11APAssocAuthSucCnt, ibDot11APMacAuthSucCnt,
--        ibDot11APPortalAuthReqFailCnt, ibDot11APAssocAuthReqFailCnt,
--        ibDot11APMacAuthReqFailCnt to ibDot11APUserSecAuthTypeStatisTable
--    2012-04-25 modified by Wang Shaojie
--        Add new table ibDot11RadioRxStatis64Table, ibDot11RadioTxStatis64Table,
--        ibDot11BSSRxStatis64Table, ibDot11BSSTxStatis64Table to
--        ibDot11APStatisGroup.
--    2012-08-12 modified by Zhang Congcong & Chen Zhao liang & Li Xin
--        Add new node   ibDot11APMtTrapAPMacAddress to ibDot11APMtTrapVarObjects
--        Add new object ibDot11APMtTrapAPMacAddress to ibDot11APMtWorkModeChgTrap
--        Add new object ibDot11APMtTrapAPMacAddress to ibDot11APFlashWriteFailure
--        Add new object ibDot11APMtTrapAPMacAddress to ibDot11APMtDetectedIntfAP
--        Add new object ibDot11APMtTrapAPMacAddress to ibDot11APInterfClearTrap
--        Add new object ibDot11APMtTrapAPMacAddress to ibDot11APMtDetectedIntfSTA
--        Add new object ibDot11APMtTrapAPMacAddress to ibDot11StaInterfClearTrap
--        Add new object ibDot11APMtTrapAPMacAddress to ibDot11APMtDetectedIntfOtherDev
--        Add new object ibDot11APMtTrapAPMacAddress to ibDot11OtherDevIntClearTrap
--        Add new object ibDot11APMtTrapAPMacAddress to ibDot11APModuleTroubleTrap
--        Add new object ibDot11APMtTrapAPMacAddress to ibDot11APModuleTroubleClearTrap
--        Add new object ibDot11APMtTrapAPMacAddress to ibDot11APRadioDownTrap
--        Add new object ibDot11APMtTrapAPMacAddress to ibDot11APRadioDownRecovTrap
--        Add new object ibDot11APMtTrapAPMacAddress to ibDot11APStaFullTrap
--        Add new object ibDot11APMtTrapAPMacAddress to ibDot11APStaFullRecoverTrap
--        Add new object ibDot11APMtTrapAPMacAddress to ibDot11APMtAvailChlTooLow
--        Add new object ibDot11APMtTrapAPMacAddress to ibDot11DFSFreeCntBelowThrRecov
--        Add new object ibDot11APMtTrapAPMacAddress to ibDot11APMtRdoChanlChgTrap
--   V2.7 2013-01-16 modified by Peng Nao
--        Add new object ibDot11APMtTrapAPMacAddress to ibDot11APCpuUsageHigh
--        Add new object ibDot11APMtTrapAPMacAddress to ibDot11APCpuUsageHighRecover
--        Add new object ibDot11APMtTrapAPMacAddress to ibDot11APMemUsageHigh
--        Add new object ibDot11APMtTrapAPMacAddress to ibDot11APMemUsageHighRecover
--   V2.8 2013-07-01 modified by LiuYanjie
--        Add new table ibDot11APPacketMCSRateStatis2Table to ibDot11APStatisGroup.
--        2013-07-08 modified by Chen Guoxi
--        Add new node  ibDot11ApStationReassocReqSum      to ibDot11APAssocStatisEntry
--        Add new node  ibDot11ApStationReassocFailSum     to ibDot11APAssocStatisEntry
--   V2.9 2013-09-02 Added ibDot11OperStatusCM to ibDot11APRadioTable by Zhang Siyu
--        2013-09-13 Added ibDot11APIfAdminStatus,ibDot11APIfOperStatusCM and
--        ibDot11APACAssociateStatusCM by duyanbing
--   V3.0 2014-02-10 modified by weixiangxiang
--        Add new object ibDot11APResetCM to ibDot11APObjectStatusTable
--        Add new object ibDot11CurrAPCPUTypeCM to ibDot11APObjectTable
--        Add new object ibDot11CurrAPMemoryTypeCM to ibDot11APObjectTable
--        Add new object ibDot11CurrAPBSSIDNumberCM to ibDot11APObjectTable
--        Add new object ibDot11APIfTypeCM to ibDot11APIfTable
--        Add new object ibDot11RxSignalStrengthPacketCntCM to ibDot11APRxStatisTable
--        Add new object ibDot11APAssocFailStatis3RSSILowCntCM to ibDot11APAssocFailStatis3Table
--        Add new object ibDot11APUserLoginNameCM to ibDot11APUserInfoStatisTable
--        Add new object ibDot11APUserAuthTypeCM to ibDot11APUserInfoStatisTable
--        Add new object ibDot11APUserTxPacketCntCM to ibDot11APUserInfoStatisTable
--        Add new object ibDot11APUserTxBytesCM to ibDot11APUserInfoStatisTable
--        Add new object ibDot11APUserRxPacketCntCM to ibDot11APUserInfoStatisTable
--        Add new object ibDot11APUserRxBytesCM to ibDot11APUserInfoStatisTable
--        Add new table ibDot11APUserSecAuthStatisCMTable to ibDot11APStatisGroup
--        Add new object ibDot11APAutoAuthOnlineUserNumCM to ibDot11APUserSecAuthTypeStatisTable
--        Add new object ibDot11APAllAutoAuthOnlineTimeCM to ibDot11APUserSecAuthTypeStatisTable
--        Add new object ibDot11APAutoAuthUserLostCnntCntCM to ibDot11APUserSecAuthTypeStatisTable
--        Add new object ibDot11APAutoAuthReqCntCM to ibDot11APUserSecAuthTypeStatisTable
--        Add new object ibDot11APAutoAuthSucCntCM to ibDot11APUserSecAuthTypeStatisTable
--        Add new object ibDot11APAutoAuthReqFailCntCM to ibDot11APUserSecAuthTypeStatisTable
--        Modify object ibDot11APPortalOnlineUserNum from ibDot11APUserSecAuthTypeStatisTable
--        Modify object ibDot11APAssocAuthOnlineUserNum from ibDot11APUserSecAuthTypeStatisTable
--        Add ibDot11RxDataFrameCntCM to ibDot11APRxStatisTable
--        Add ibDot11Rx64DataFrameBytesCM to ibDot11RadioRxStatis64Table
--   V3.1 2014-05-15 modified by yubo
--        Add new object ibDot11PrivateSrvRxFrameBytes  to ibDot11APLinkStatisTable
--        Add new object ibDot11PrivateSrvTxFrameBytes  to ibDot11APLinkStatisTable
--        Add new object ibDot11APInternetAllRxBytes    to ibDot11APLinkStatisTable
--        Add new object ibDot11APInternetAllTxBytes    to ibDot11APLinkStatisTable
--        Add new object ibDot11APLocalAllRxBytes       to ibDot11APLinkStatisTable
--        Add new object ibDot11APLocalAllTxBytes       to ibDot11APLinkStatisTable
--        Add new object ibDot11APPowerOffTrap          to ibDot11APMtTraps
--        Add new object ibDot11APPowerOnTrap           to ibDot11APMtTraps
--        Add new object ibDot11UpLinkSwitchTrap        to ibDot11APMtTraps
--        Add new object ibDot11APMtUpLinkSwitchInfo    to ibDot11APMtTrapVarObjects
--        Add new object ibDot11APMtUpLinkSwitchTime    to ibDot11APMtTrapVarObjects
--        Add new object ibDot11APMtOldCellId           to ibDot11APMtTrapVarObjects
--        Add new object ibDot11APMtCurCellId           to ibDot11APMtTrapVarObjects
--        Add new object ibDot11APMtOldBand             to ibDot11APMtTrapVarObjects
--        Add new object ibDot11APMtActiveBand          to ibDot11APMtTrapVarObjects
--        Add new table ibDot11APUserInfoStatis2CMTable to ibDot11APStatisGroup
--        Add new object ibDot11RxTotalFrameCnt         to ibDot11APRxStatisTable
--        Add new object ibDot11TxTotalFrameCnt         to ibDot11APTxStatisTable
--   V3.2 2014-11-19 modified by yubo
--        Add new object ibDot11AirPrimChnlBusy       to ibDot11APRadioTable
--        Add new object ibDot11AirPrimChnlTxBusy     to ibDot11APRadioTable
--        Add new object ibDot11AirPrimChnlRxBusy     to ibDot11APRadioTable
--        Add new object ibDot11AirExtChnlBusy        to ibDot11APRadioTable
--        Add new object ibDot11CurrAPIPv6PrefixLen   to ibDot11APObjectTable
--        Add new object ibDot11APIPv6PrefixLen       to ibDot11APObjectStatusTable
--        Add new object ibDot11APUserIPv6Addr2CM     to ibDot11APUserInfoStatis2CMTable
--        2014-12-12 modified by yubo
--        Add new object ibDot11APAssocStaNum   to ibDot11APSSIDObjectTable
--   V3.3 2015-6-20 modified by wangshaojie
--        Add new object ibDot11WTUAPInfoTable        to ibDot11APObjectGroup
--   V3.4 2016-3-11 modified by yubo 04460
--        Changed DESCRIPTION of ibDot11RadioModeSupport, ibDot11RadioModeSupport2,
--        ibDot11TxDiscardFrameBytes, ibDot11Tx64DiscardFrameBytes
--        Add ibDot11APUserInCirValueCM to ibDot11APUserInfoStatis2CMTable
--        Add ibDot11APUserOutCirValueCM to ibDot11APUserInfoStatis2CMTable
--        Add ibDot11APUserMac2CM to ibDot11APUserInfoStatis2CMTable
--        Add ibDot11BSSRxFrameErrCntCM to ibDot11BSSRxStatisTable
--        Add ibDot11BSSTxFrameErrCntCM to ibDot11BSSTxStatisTable
--        Add ibDot11APFactoryDataResetCM to ibDot11APObjectStatusTable
--        2016-6-15 modified by zhouwenshuai kf6157
--        Add new node  ibDot11WsmAPLicenseType      to ibDot11APModelTable
--   V3.5 2018-06-04 modified licheng lkf7405
--        Add new table ibDot11ApBriefInfoTable to ibDot11APObjectGroup
--        Add new nodes ibDot11APGpsLongitude, ibDot11APGpsLatitude,
--        ibDot11APGpsVelocity, ibDot11APGpsOrientation,
--        ibDot11APGpsElevation, and ibDot11APGpsObtainTime to IbDot11APObjectStatusEntry
--        Add new table ibDot11MaxPowerCapaTable to ibDot11APObjectGroup
--        Add new nodes ibDot11APGateWayIPv4 and ibDot11APGateWayIPv6 to IbDot11APObjectStatusEntry
--   V3.6 2021-06-18 modified by liyapeng
--        Add new object ibDot11APMtTrapRadioFailReason to ibDot11APMtRadioFailRecoverTrap
--   V3.7 2023-01-06 modified by fanwenyang
--        Add new object ibDot11RadioType to ibDot11APRadioTable
--        Add new object ibDot11RadioOper to ibDot11APRadioTable
--        Add new object ibDot11BindSSID to ibDot11APRadioTable
--        Add new object ibDot11RadioAverageSignalStrength to ibDot11APRadioTable
--        Add new object ibDot11RadioMaxSignalStrength to ibDot11APRadioTable
--        Add new object ibDot11RadioMinSignalStrength to ibDot11APRadioTable
-- =============================================================================
IB-DOT11-APMT-MIB DEFINITIONS ::= BEGIN

IMPORTS
        MODULE-IDENTITY,
        OBJECT-TYPE,
        NOTIFICATION-TYPE,
        Integer32,
        Counter32,
        IpAddress,
        Unsigned32,
        TimeTicks,
        Counter64,
        Gauge32
    FROM SNMPv2-SMI
        MacAddress,
        TruthValue,
        DateAndTime,
        TimeStamp
    FROM SNMPv2-TC
        ibDot11,
        IbDot11ObjectIDType,
        IbDot11MACModeType,
        IbDot11RadioScopeType,
        IbDot11NotifyReasonType,
        IbDot11ChannelScopeType,
        IbDot11ServicePolicyIDType,
        IbDot11RFModeType,
        IbDot11TxPwrLevelScopeType,
        IbDot11RadioElementIndex,
        ibDot11APElementIndex,
        IbDot11SSIDStringType
    FROM IB-DOT11-REF-MIB;

ibDot11APMT MODULE-IDENTITY
    LAST-UPDATED "202301061800Z"        -- Jan 6, 2023 at 18:00 GMT
    ORGANIZATION
        "Intelbras S.A. Industria de Telecomunicacao Eletronica Brasileria."
    CONTACT-INFO
        ""
    DESCRIPTION
        "This MIB provides AP information which includes AP current object
        information, AP statistic data.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Fat AP
        Applied in the home, SOHO and so on, and it could
        work independently without help from AC.

        Fit AP
        Applied in the enterprise environment, it will work
        under the control and management from AC.

        Control And Provisioning of Wireless Access Points Protocol
        The short name of protocol is CAPWAP.  AC will control
        and manage AP by CAPWAP tunnel protocol defined by IETF.
        Also, a data tunnel will be set up between AC and AP.

        BSS
        IEEE 802.11 Basic Service Set (Radio Cell).  The
        BSS of an AP comprises of the stations directly
        associating with the AP.

        Radio
        The chip set to receive and send wireless signal.

        Association
        The service used to establish access point
        or station mapping and enable STA invocation
        of the distribution system services.
        (Wireless clients attempt to connect to
        access points.)

        Basic Rate
        A data rate that is mandatory for client
        devices to support in order for them to achieve
        successful association."
    REVISION "202301061800Z"        -- Jan 6, 2023 at 18:00 GMT
    DESCRIPTION
        "Modified to add new nodes."
    REVISION "202106181800Z"        -- Jun 18, 2021 at 18:00 GMT
    DESCRIPTION
        " Modify the OBJECTS of the trap node."
    REVISION "201806041800Z"        -- Jun 04, 2018 at 18:00 GMT
    DESCRIPTION
        "Modified to add new tables and new nodes."
    REVISION "201603111800Z"        -- Mar 11, 2016 at 18:00 GMT
    DESCRIPTION
        "Modified to add new tables and new nodes."
    REVISION "201506201800Z"        -- June 20, 2015 at 18:00 GMT
    DESCRIPTION
        "Modified to add new tables and new nodes."

    REVISION "201205071800Z"        -- May 07, 2012 at 18:00 GMT
    DESCRIPTION
        "Modified to add new tables."

    REVISION "201010111800Z"        -- Oct 11, 2010 at 18:00 GMT
    DESCRIPTION
        "Modified to add new nodes."
    REVISION "201009151200Z"        -- Sep 15, 2010 at 12:00 GMT
    DESCRIPTION
        "Modified to add new table."
    REVISION "200908071800Z"        -- Aug 07, 2009 at 18:00 GMT
    DESCRIPTION
        "Modified to add new nodes."
    REVISION "200907291800Z"        -- Jul 29, 2009 at 18:00 GMT
    DESCRIPTION
        "Modified to add new nodes."
    REVISION "200905072000Z"        -- May 7, 2009 at 20:00 GMT
    DESCRIPTION
        "Modified to add new tables and new nodes."
    REVISION "200811071000Z"        -- Nov 07, 2008 at 10:00 GMT
    DESCRIPTION
        "Modified to add new tables and new nodes."
    REVISION "200807091800Z"        -- July 09, 2008 at 18:00 GMT
    DESCRIPTION
        "Modified to add new nodes."
    REVISION "200802251800Z"        -- Feb 25, 2008 at 18:00 GMT
    DESCRIPTION
        "Modified to add new nodes."
    REVISION "200712211800Z"        -- Dec 21, 2007 at 18:00 GMT
    DESCRIPTION
        "Modified to add new tables and new nodes."
    REVISION "200706191800Z"        -- June 19, 2007 at 18:00 GMT
    DESCRIPTION
        "Modified for new requirements and fix some issue."
    REVISION "200704272000Z"        -- Apr 27, 2007 at 20:00 GMT
    DESCRIPTION
        "Modified to fix some issue."
    REVISION "200702012000Z"        -- February 01, 2007 at 20:00 GMT
    DESCRIPTION
        "Modified to support fat AP."
    REVISION "200605101900Z"        -- May 10, 2006 at 19:00 GMT
    DESCRIPTION
        "The initial revision of this MIB module."
    ::= { ibDot11 2 }

-- *****************************************************************************
-- *  Major sections
-- *****************************************************************************
--  AP Object Group
--  DEFINED AS "The group to provide the basic information for APs.
--  In order to support fit and fat AP, it uses tables to keep
--  information.  For fat AP, if it is needful, it could add more
--  tables to keep information."
ibDot11APObjectGroup OBJECT IDENTIFIER   ::= { ibDot11APMT 1 }

--  AP Object Group has the following children:
--  ibDot11APObjectStatusTable           ::= { ibDot11APObjectGroup 1 }
--  ibDot11APObjectTable                 ::= { ibDot11APObjectGroup 2 }
--  ibDot11APRadioTable                  ::= { ibDot11APObjectGroup 3 }
--  ibDot11APBSSTable                    ::= { ibDot11APObjectGroup 4 }
--  ibDot11APModelTable                  ::= { ibDot11APObjectGroup 5 }
--  ibDot11APIfTable                     ::= { ibDot11APObjectGroup 6 }
--  ibDot11APSSIDObjectTable             ::= { ibDot11APObjectGroup 7 }
--  ibDot11APSysInfoTable                ::= { ibDot11APObjectGroup 8 }
--  ibDot11APIdleListTable               ::= { ibDot11APObjectGroup 9 }
--  ibDot11APSysInfoByAPIDTable          ::= { ibDot11APObjectGroup 10 }
--  ibDot11WTUAPInfoTable                ::= { ibDot11APObjectGroup 11 }
--  ibDot11ApBriefInfoTable              ::= { ibDot11APObjectGroup 12 }
--  ibDot11MaxPowerCapaTable             ::= { ibDot11APObjectGroup 13 }

--  AP Statistic Group
--  DEFINED AS "The group to provide the statistic information of Rx
--  and Tx for AP."
ibDot11APStatisGroup OBJECT IDENTIFIER   ::= { ibDot11APMT 2 }

--  AP Statistic Group has the following children:
--  ibDot11APRxStatisTable               ::= { ibDot11APStatisGroup 1 }
--  ibDot11APTxStatisTable               ::= { ibDot11APStatisGroup 2 }
--  ibDot11APAssocStatisTable            ::= { ibDot11APStatisGroup 3 }
--  ibDot11BSSRxStatisTable              ::= { ibDot11APStatisGroup 4 }
--  ibDot11BSSTxStatisTable              ::= { ibDot11APStatisGroup 5 }
--  ibDot11BSSAssocStatisTable           ::= { ibDot11APStatisGroup 6 }
--  ibDot11APLinkStatisTable             ::= { ibDot11APStatisGroup 7 }
--  ibDot11RadioAssocStatisTable         ::= { ibDot11APStatisGroup 8 }
--  ibDot11RadioMngFrameStatisTable      ::= { ibDot11APStatisGroup 9 }
--  ibDot11APAuthFailStatisTable         ::= { ibDot11APStatisGroup 10 }
--  ibDot11APAssocFailStatisTable        ::= { ibDot11APStatisGroup 11 }
--  ibDot11APReassocStatisTable          ::= { ibDot11APStatisGroup 12 }
--  ibDot11APUserAuthStatisTable         ::= { ibDot11APStatisGroup 13 }
--  ibDot11APDeauthStatisTable           ::= { ibDot11APStatisGroup 14 }
--  ibDot11APDeassocStatisTable          ::= { ibDot11APStatisGroup 15 }
--  ibDot11APAssocFailStatis2Table       ::= { ibDot11APStatisGroup 16 }
--  ibDot11APIfStatisTable               ::= { ibDot11APStatisGroup 17 }
--  ibDot11RadioMngFrmStatisTable        ::= { ibDot11APStatisGroup 18 }
--  ibDot11APPacketSizeStatisTable       ::= { ibDot11APStatisGroup 19 }
--  ibDot11APPacketRateStatisTable       ::= { ibDot11APStatisGroup 20 }
--  ibDot11APPacketMCSRateStatisTable    ::= { ibDot11APStatisGroup 21 }
--  ibDot11APAssocFailStatis3Table       ::= { ibDot11APStatisGroup 22 }
--  ibDot11APIfStatisByAPIDTable         ::= { ibDot11APStatisGroup 23 }
--  ibDot11APUserSecAuthStatisTable      ::= { ibDot11APStatisGroup 24 }
--  ibDot11APUserInfoStatisTable         ::= { ibDot11APStatisGroup 25 }
--  ibDot11APReassocStatis2Table         ::= { ibDot11APStatisGroup 26 }
--  ibDot11TrafficTable                  ::= { ibDot11APStatisGroup 27 }
--  ibDot11APEchoStatisTable             ::= { ibDot11APStatisGroup 28 }
--  ibDot11APUserSecAuthTypeStatisTable  ::= { ibDot11APStatisGroup 29 }
--  ibDot11RadioRxStatis64Table          ::= { ibDot11APStatisGroup 30 }
--  ibDot11RadioTxStatis64Table          ::= { ibDot11APStatisGroup 31 }
--  ibDot11BSSRxStatis64Table            ::= { ibDot11APStatisGroup 32 }
--  ibDot11BSSTxStatis64Table            ::= { ibDot11APStatisGroup 33 }
--  ibDot11APPacketMCSRateStatis2Table   ::= { ibDot11APStatisGroup 34 }
--  ibDot11APUserSecAuthStatisCMTable    ::= { ibDot11APStatisGroup 35 }
--  ibDot11APUserInfoStatis2CMTable      ::= { ibDot11APStatisGroup 36 }

--  AP Event Notification
--  DEFINED AS " The group to provide AP management notification."
ibDot11APMtNotifyGroup OBJECT IDENTIFIER ::= { ibDot11APMT 3 }

-- *****************************************************************************
-- *  ibDot11APObjectStatusTable Definition
-- *****************************************************************************
ibDot11APObjectStatusTable OBJECT-TYPE
    SYNTAX      SEQUENCE OF IbDot11APObjectStatusEntry
    MAX-ACCESS  not-accessible
    STATUS      current
    DESCRIPTION
        "The table will provide the general information about APs in
        different status."
    ::= { ibDot11APObjectGroup 1 }

ibDot11APObjectStatusEntry OBJECT-TYPE
    SYNTAX      IbDot11APObjectStatusEntry
    MAX-ACCESS  not-accessible
    STATUS      current
    DESCRIPTION
        "Each entry contains the general information of an AP."
    INDEX
        {
            ibDot11APID
        }
    ::= { ibDot11APObjectStatusTable 1 }

IbDot11APObjectStatusEntry ::= SEQUENCE
    {
        ibDot11APID                  IbDot11ObjectIDType,
        ibDot11APIPAddress           IpAddress,
        ibDot11APMacAddress          MacAddress,
        ibDot11APOperationStatus     INTEGER,
        ibDot11APTemplateNameOfAP    OCTET STRING,
        ibDot11APReset               TruthValue,
        ibDot11APCpuUsage            Integer32,
        ibDot11APConnectionType      INTEGER,
        ibDot11APLastImgDownloadTime DateAndTime,
        ibDot11APIPv6Address         OCTET STRING,
        ibDot11APLastRegisterTime    DateAndTime,
        ibDot11APResetCM             INTEGER,
        ibDot11APIPv6PrefixLen       Integer32,
        ibDot11APFactoryDataResetCM  INTEGER,
        ibDot11APGpsLongitude        OCTET STRING,
        ibDot11APGpsLatitude         OCTET STRING,
        ibDot11APGpsVelocity         OCTET STRING,
        ibDot11APGpsOrientation      OCTET STRING,
        ibDot11APGpsElevation        OCTET STRING,
        ibDot11APGpsObtainTime       DateAndTime,
        ibDot11APGateWayIPv4         IpAddress,
        ibDot11APGateWayIPv6         OCTET STRING
    }

ibDot11APID OBJECT-TYPE
    SYNTAX      IbDot11ObjectIDType
    MAX-ACCESS  accessible-for-notify
    STATUS      current
    DESCRIPTION
        "To uniquely identify each AP, and relation-ship between ibDot11APID
        and AP device will be static."
    ::= { ibDot11APObjectStatusEntry 1 }

ibDot11APIPAddress OBJECT-TYPE
    SYNTAX      IpAddress
    MAX-ACCESS  read-only
    STATUS      current
    DESCRIPTION
        "Represents the IP address of an AP."
    ::= { ibDot11APObjectStatusEntry 2 }

ibDot11APMacAddress OBJECT-TYPE
    SYNTAX      MacAddress
    MAX-ACCESS  read-only
    STATUS      current
    DESCRIPTION
        "Represents the MAC address of an AP."
    ::= { ibDot11APObjectStatusEntry 3 }

ibDot11APOperationStatus OBJECT-TYPE
    SYNTAX      INTEGER
        {
            join(1),
            joinConfirm(2),
            download(3),
            config(4),
            run(5)
        }
    MAX-ACCESS  read-only
    STATUS      current
    DESCRIPTION
        "Represents operational status of AP.
        The following values are supported:
        join         - AP is joining to AC.
        joinConfirm  - AC confirm whether permit AP to join.
        download     - AP is downloading software from AC.
        config       - AP and AC exchange configuration before AP
        - provide WLAN service.
        run          - The WLAN service is ready."
    ::= { ibDot11APObjectStatusEntry 4 }

ibDot11APTemplateNameOfAP OBJECT-TYPE
    SYNTAX      OCTET STRING
    MAX-ACCESS  read-only
    STATUS      current
    DESCRIPTION
        "Represents the name of current AP template configured for AP."
    ::= { ibDot11APObjectStatusEntry 5 }

ibDot11APReset OBJECT-TYPE
    SYNTAX      TruthValue
    MAX-ACCESS  read-write
    STATUS      current
    DESCRIPTION
        "When read the value from the node
        2: Represents the AP cannot be reset.
        1: Represents the AP can be reset.
        When write the value to the node
        1: Represents resetting the AP.  Other values are not supported"
    ::= { ibDot11APObjectStatusEntry 6 }

ibDot11APCpuUsage OBJECT-TYPE
    SYNTAX      Integer32(0..100)
    UNITS       "onepercent"
    MAX-ACCESS  read-only
    STATUS      current
    DESCRIPTION
        "Represents the current CPU usage for AP."
    ::= { ibDot11APObjectStatusEntry 7 }

ibDot11APConnectionType OBJECT-TYPE
    SYNTAX      INTEGER
        {
            master(1),
            slave(2),
            notAvailable(3)
        }
    MAX-ACCESS  read-only
    STATUS      current
    DESCRIPTION
        "Represents the current connection type."
    ::= { ibDot11APObjectStatusEntry 8 }

ibDot11APLastImgDownloadTime OBJECT-TYPE
    SYNTAX      DateAndTime
    MAX-ACCESS  read-only
    STATUS      current
    DESCRIPTION
        "Represents the time at which the device last downloaded image."
    ::= { ibDot11APObjectStatusEntry 9 }

ibDot11APIPv6Address OBJECT-TYPE
    SYNTAX      OCTET STRING
    MAX-ACCESS  read-only
    STATUS      current
    DESCRIPTION
        "Represents the IPv6 address of AP."
    ::= { ibDot11APObjectStatusEntry 10 }

ibDot11APLastRegisterTime OBJECT-TYPE
    SYNTAX      DateAndTime
    MAX-ACCESS  read-only
    STATUS      current
    DESCRIPTION
        "Represents the time at which the device last registered with AC."
    ::= { ibDot11APObjectStatusEntry 11 }

ibDot11APResetCM OBJECT-TYPE
    SYNTAX      INTEGER
        {
            normal(0),
            restart(1)
        }
    MAX-ACCESS  read-write
    STATUS      current
    DESCRIPTION
        "When reading the value from the node
        normal  - Represents the AP cannot be reset.
        restart - Represents the AP can be reset.
        When writing the value to the node
        restart - Represents resetting the AP.  Other values are not supported."
    ::= { ibDot11APObjectStatusEntry 12 }

ibDot11APIPv6PrefixLen OBJECT-TYPE
    SYNTAX      Integer32
    MAX-ACCESS  read-only
    STATUS      current
    DESCRIPTION
        "Represents the prefix length of an AP IPv6 address."
    ::= { ibDot11APObjectStatusEntry 13 }

ibDot11APFactoryDataResetCM OBJECT-TYPE
    SYNTAX      INTEGER
        {
            normal(0),
            restart(1)
        }
    MAX-ACCESS  read-write
    STATUS      current
    DESCRIPTION
        "When reading the value from the node
        normal  - Represents the AP cannot be reset.
        restart - Represents the AP can be reset.
        When writing the value to the node
        restart - Represents resetting the AP.  Other values are not supported."
    ::= { ibDot11APObjectStatusEntry 14 }

ibDot11APGpsLongitude OBJECT-TYPE
    SYNTAX      OCTET STRING
    MAX-ACCESS  read-only
    STATUS      current
    DESCRIPTION
        "Get the current longitudes of online APs by GPS."
    ::= { ibDot11APObjectStatusEntry 15 }

ibDot11APGpsLatitude OBJECT-TYPE
    SYNTAX      OCTET STRING
    MAX-ACCESS  read-only
    STATUS      current
    DESCRIPTION
        "Get the current latitudes of online APs by GPS."
    ::= { ibDot11APObjectStatusEntry 16 }

ibDot11APGpsVelocity OBJECT-TYPE
    SYNTAX      OCTET STRING
    MAX-ACCESS  read-only
    STATUS      current
    DESCRIPTION
        "Get the current velocities of online APs by GPS."
    ::= { ibDot11APObjectStatusEntry 17 }

ibDot11APGpsOrientation OBJECT-TYPE
    SYNTAX      OCTET STRING
    MAX-ACCESS  read-only
    STATUS      current
    DESCRIPTION
        "Get the current orientations of online APs by GPS."
    ::= { ibDot11APObjectStatusEntry 18 }

ibDot11APGpsElevation OBJECT-TYPE
    SYNTAX      OCTET STRING
    MAX-ACCESS  read-only
    STATUS      current
    DESCRIPTION
        "Get the current elevations of online APs by GPS."
    ::= { ibDot11APObjectStatusEntry 19 }

ibDot11APGpsObtainTime OBJECT-TYPE
    SYNTAX      DateAndTime
    MAX-ACCESS  read-only
    STATUS      current
    DESCRIPTION
        "Get the current online AP time by GPS."
    ::= { ibDot11APObjectStatusEntry 20 }

ibDot11APGateWayIPv4 OBJECT-TYPE
    SYNTAX      IpAddress
    MAX-ACCESS  read-only
    STATUS      current
    DESCRIPTION
        "Represents the gateway IPv4 address of APs."
    ::= { ibDot11APObjectStatusEntry 21 }

ibDot11APGateWayIPv6 OBJECT-TYPE
    SYNTAX      OCTET STRING
    MAX-ACCESS  read-only
    STATUS      current
    DESCRIPTION
        "Represents the gateway IPv6 address of APs."
    ::= { ibDot11APObjectStatusEntry 22 }

-- *****************************************************************************
-- *  End of IbDot11APObjectStatusTable Definition
-- *****************************************************************************

-- *****************************************************************************
-- *  ibDot11APObjectTable Definition
-- *****************************************************************************
ibDot11APObjectTable OBJECT-TYPE
    SYNTAX      SEQUENCE OF IbDot11APObjectEntry
    MAX-ACCESS  not-accessible
    STATUS      current
    DESCRIPTION
        "The table will provide information for APs in the running status."
    ::= { ibDot11APObjectGroup 2 }

ibDot11APObjectEntry OBJECT-TYPE
    SYNTAX      IbDot11APObjectEntry
    MAX-ACCESS  not-accessible
    STATUS      current
    DESCRIPTION
        "Each entry contains information of an AP in run status."
    INDEX
        {
            ibDot11APObjID
        }
    ::= { ibDot11APObjectTable 1 }

IbDot11APObjectEntry ::= SEQUENCE
    {
        ibDot11APObjID                    IbDot11ObjectIDType,
        ibDot11CurrAPIPAddress            IpAddress,
        ibDot11CurrAPMacAddress           MacAddress,
        ibDot11CurrACPortIndex            Integer32,
        ibDot11CurrAPMACMode              IbDot11MACModeType,
        ibDot11CurrAPTemplateName         OCTET STRING,
        ibDot11CurrAPStationAssocCount    Integer32,
        ibDot11CurrAPName                 OCTET STRING,
        ibDot11CurrAPModelName            OCTET STRING,
        ibDot11CurrAPImageName            OCTET STRING,
        ibDot11CurrAPSoftwareVersion      OCTET STRING,
        ibDot11CurrAPIPNetMask            IpAddress,
        ibDot11CurrRadioModeSupport       Integer32,
        ibDot11CurrIfNumber               Integer32,
        ibDot11CurrAPElementID            Integer32,
        ibDot11CurrAPMode                 INTEGER,
        ibDot11CurrAPIPv6Address          OCTET STRING,
        ibDot11CurrAPSSIDNumber           Integer32,
        ibDot11CurrAPManufacturer         OCTET STRING,
        ibDot11CurrAPMemorySize           Integer32,
        ibDot11CurrAPMemSizeInBytes       Integer32,
        ibDot11CurrAPFlashSize            Integer32,
        ibDot11CurrAPFlashSizeInBytes     Integer32,
        ibDot11CurrAPReleasedVersion      OCTET STRING,
        ibDot11CurrRadioModeSupport2      Integer32,
        ibDot11CurrAPCPUTypeCM            OCTET STRING,
        ibDot11CurrAPMemoryTypeCM         OCTET STRING,
        ibDot11CurrAPBSSIDNumberCM        Integer32,
        ibDot11CurrAPIPv6PrefixLen        Integer32
    }

ibDot11APObjID OBJECT-TYPE
    SYNTAX      IbDot11ObjectIDType
    MAX-ACCESS  read-only
    STATUS      current
    DESCRIPTION
        "To uniquely identify each AP, and relation-ship between ibDot11APObjID
        and AP device will be static."
    ::= { ibDot11APObjectEntry 1 }

ibDot11CurrAPIPAddress OBJECT-TYPE
    SYNTAX      IpAddress
    MAX-ACCESS  read-only
    STATUS      current
    DESCRIPTION
        "Represents the IP address of an AP."
    ::= { ibDot11APObjectEntry 2 }

ibDot11CurrAPMacAddress OBJECT-TYPE
    SYNTAX      MacAddress
    MAX-ACCESS  read-only
    STATUS      current
    DESCRIPTION
        "Represents the MAC address of an AP."
    ::= { ibDot11APObjectEntry 3 }

ibDot11CurrACPortIndex OBJECT-TYPE
    SYNTAX      Integer32
    MAX-ACCESS  read-only
    STATUS      current
    DESCRIPTION
        "Represents the port on the AC, by which the traffic of this AP comes
        through.  NMS could refer it to access information kept in the
        MIB-2."
    ::= { ibDot11APObjectEntry 4 }

ibDot11CurrAPMACMode OBJECT-TYPE
    SYNTAX      IbDot11MACModeType
    MAX-ACCESS  read-only
    STATUS      current
    DESCRIPTION
        "Represents what MAC mode defined in the CAPWAP is applied.
        For fat AP, the value will be fatap."
    ::= { ibDot11APObjectEntry 5 }

ibDot11CurrAPTemplateName OBJECT-TYPE
    SYNTAX      OCTET STRING
    MAX-ACCESS  read-only
    STATUS      current
    DESCRIPTION
        "Represents the name of current AP template."
    ::= { ibDot11APObjectEntry 6 }

ibDot11CurrAPStationAssocCount OBJECT-TYPE
    SYNTAX      Integer32
    MAX-ACCESS  read-only
    STATUS      current
    DESCRIPTION
        "Represents the total number of stations which are associating
        to AP."
    ::= { ibDot11APObjectEntry 7 }

ibDot11CurrAPName OBJECT-TYPE
    SYNTAX      OCTET STRING
    MAX-ACCESS  read-only
    STATUS      current
    DESCRIPTION
        "Represents the name of AP."
    ::= { ibDot11APObjectEntry 8 }

ibDot11CurrAPModelName OBJECT-TYPE
    SYNTAX      OCTET STRING
    MAX-ACCESS  read-only
    STATUS      current
    DESCRIPTION
        "Represents index of WTP model,with it to get AP model information."
    ::= { ibDot11APObjectEntry 9 }

ibDot11CurrAPImageName OBJECT-TYPE
    SYNTAX      OCTET STRING
    MAX-ACCESS  read-only
    STATUS      current
    DESCRIPTION
        "Represents the image file name of AP."
    ::= { ibDot11APObjectEntry 10 }

ibDot11CurrAPSoftwareVersion OBJECT-TYPE
    SYNTAX      OCTET STRING
    MAX-ACCESS  read-only
    STATUS      current
    DESCRIPTION
        "Represents the software version of AP."
    ::= { ibDot11APObjectEntry 11 }

ibDot11CurrAPIPNetMask OBJECT-TYPE
    SYNTAX      IpAddress
    MAX-ACCESS  read-only
    STATUS      current
    DESCRIPTION
        "Represents the IP netmask of AP."
    ::= { ibDot11APObjectEntry 12 }

ibDot11CurrRadioModeSupport OBJECT-TYPE
    SYNTAX      Integer32
    MAX-ACCESS  read-only
    STATUS      current
    DESCRIPTION
        "Represents which radio type supported by the AP.
        The WLAN system support the following possible radio type.
        dot11a(1),
        dot11b(2),
        dot11g(4),
        dot11n(8),
        dot11an(16),
        dot11gn(32),
        dot11ac(64),
        dot11gac(128)
        For a AP,it could support multiple radio types at
        the same time.So the value of object could combine multiple value
        of radio type above.
        For example:
        For one AP which support both b and g mode radio, when getting the value
        from the node, the value is 6(2 + 4)."
    ::= { ibDot11APObjectEntry 13 }

ibDot11CurrIfNumber OBJECT-TYPE
    SYNTAX      Integer32
    MAX-ACCESS  read-only
    STATUS      current
    DESCRIPTION
        "Represents number of interface of the AP."
    ::= { ibDot11APObjectEntry 14 }

ibDot11CurrAPElementID OBJECT-TYPE
    SYNTAX      Integer32
    MAX-ACCESS  read-only
    STATUS      current
    DESCRIPTION
    "Represents the AP element ID."
    ::= { ibDot11APObjectEntry 15 }

ibDot11CurrAPMode OBJECT-TYPE
    SYNTAX      INTEGER
        {
            bridge(1),
            route(2)
        }
    MAX-ACCESS  read-only
    STATUS      current
    DESCRIPTION
        "Represents the forward mode of the AP."
    ::= { ibDot11APObjectEntry 16 }

ibDot11CurrAPIPv6Address OBJECT-TYPE
    SYNTAX      OCTET STRING
    MAX-ACCESS  read-only
    STATUS      current
    DESCRIPTION
        "Represents the IPv6 address of AP."
    ::= { ibDot11APObjectEntry 17 }

ibDot11CurrAPSSIDNumber OBJECT-TYPE
    SYNTAX      Integer32
    MAX-ACCESS  read-only
    STATUS      current
    DESCRIPTION
        "Represents the number of SSID configured on AP."
    ::= { ibDot11APObjectEntry 18 }

ibDot11CurrAPManufacturer OBJECT-TYPE
    SYNTAX      OCTET STRING
    MAX-ACCESS  read-only
    STATUS      current
    DESCRIPTION
        "By the 'SMI Network Management Private Enterprise Codes'
        assigned by the IANA, NMS could know which vendor manufactures
        the AP."
    ::= { ibDot11APObjectEntry 19 }

ibDot11CurrAPMemorySize OBJECT-TYPE
    SYNTAX      Integer32
    UNITS       "kbytes"
    MAX-ACCESS  read-only
    STATUS      current
    DESCRIPTION
        "Represents the size of AP memory."
    ::= { ibDot11APObjectEntry 20 }

ibDot11CurrAPMemSizeInBytes OBJECT-TYPE
    SYNTAX      Integer32
    UNITS       "bytes"
    MAX-ACCESS  read-only
    STATUS      current
    DESCRIPTION
        "Represents the size of AP memory."
    ::= { ibDot11APObjectEntry 21 }

ibDot11CurrAPFlashSize OBJECT-TYPE
    SYNTAX      Integer32
    UNITS       "Kbytes"
    MAX-ACCESS  read-only
    STATUS      current
    DESCRIPTION
        "Represents the size of AP flash."
    ::= { ibDot11APObjectEntry 22 }

ibDot11CurrAPFlashSizeInBytes OBJECT-TYPE
    SYNTAX      Integer32
    UNITS       "bytes"
    MAX-ACCESS  read-only
    STATUS      current
    DESCRIPTION
        "This object represents the size of AP flash."
    ::= { ibDot11APObjectEntry 23 }

ibDot11CurrAPReleasedVersion OBJECT-TYPE
    SYNTAX      OCTET STRING
    MAX-ACCESS  read-only
    STATUS      current
    DESCRIPTION
        "Represents the released version of AP."
    ::= { ibDot11APObjectEntry 24 }

ibDot11CurrRadioModeSupport2 OBJECT-TYPE
    SYNTAX      Integer32
    MAX-ACCESS  read-only
    STATUS      current
    DESCRIPTION
        "Represents which radio type supported by the AP.
        The WLAN system support the following possible radio type.
        dot11a(1),
        dot11b(2),
        dot11g(4),
        dot11an(8),
        dot11gn(16),
        dot11gac(32),
        dot11ac(64)
        For a AP,it could support multiple radio types at
        the same time.So the value of object could combine multiple value
        of radio type above.
        For example:
        For one AP which support both b and g mode radio, when getting the value
        from the node, the value is 6(2 + 4)."
    ::= { ibDot11APObjectEntry 25 }

ibDot11CurrAPCPUTypeCM OBJECT-TYPE
    SYNTAX      OCTET STRING
    MAX-ACCESS  read-only
    STATUS      current
    DESCRIPTION
        "Represents the CPU type of AP."
    ::= { ibDot11APObjectEntry 26 }

ibDot11CurrAPMemoryTypeCM OBJECT-TYPE
    SYNTAX      OCTET STRING
    MAX-ACCESS  read-only
    STATUS      current
    DESCRIPTION
        "Represents the memory card type of AP."
    ::= { ibDot11APObjectEntry 27 }

ibDot11CurrAPBSSIDNumberCM OBJECT-TYPE
    SYNTAX      Integer32
    MAX-ACCESS  read-only
    STATUS      current
    DESCRIPTION
        "Represents the number of BSSID configured on AP."
    ::= { ibDot11APObjectEntry 28 }

ibDot11CurrAPIPv6PrefixLen OBJECT-TYPE
    SYNTAX      Integer32
    MAX-ACCESS  read-only
    STATUS      current
    DESCRIPTION
        "Represents the prefix length of an AP IPv6 address."
    ::= { ibDot11APObjectEntry 29 }
-- *****************************************************************************
-- *  End of ibDot11APObjectTable Definition
-- *****************************************************************************

-- *****************************************************************************
-- *  ibDot11APRadioTable Definition
-- *****************************************************************************
ibDot11APRadioTable OBJECT-TYPE
    SYNTAX      SEQUENCE OF IbDot11APRadioEntry
    MAX-ACCESS  not-accessible
    STATUS      current
    DESCRIPTION
        "The table will describe the radio information of AP.  The AP here will
        be in running status."
    ::= { ibDot11APObjectGroup 3 }

ibDot11APRadioEntry OBJECT-TYPE
    SYNTAX      IbDot11APRadioEntry
    MAX-ACCESS  not-accessible
    STATUS      current
    DESCRIPTION
        "Each entry contains the information of each radio of a specific AP."
    INDEX
        {
            ibDot11CurAPID,
            ibDot11RadioID
        }
    ::= { ibDot11APRadioTable 1 }

IbDot11APRadioEntry ::= SEQUENCE
    {
        ibDot11CurAPID            OCTET STRING,
        ibDot11RadioID            Integer32,
        ibDot11AdminStatus        TruthValue,
        ibDot11OperStatus         TruthValue,
        ibDot11Channel            IbDot11ChannelScopeType,
        ibDot11TxPowerLevel       IbDot11TxPwrLevelScopeType,
        ibDot11APRadioIfIndex     Integer32,
        ibDot11AntennaGain        Integer32,
        ibDot11MaxBandwidth       Integer32,
        ibDot11ResourceUseRatio   Integer32,
        ibDot11RadioModeSupport   Unsigned32,
        ibDot11TxPowerLevel2      Integer32,
        ibDot11PowerMgmtStatus    TruthValue,
        ibDot11ChannelSwitchTimes Counter32,
        ibDot11AntennaType        OCTET STRING,
        ibDot11DiversitySelectionRx     TruthValue,
        ibDot11MaxTxPwrLvl              OCTET STRING,
        ibDot11PwrAttRange              Integer32,
        ibDot11AvgRxSignalStrength      Integer32,
        ibDot11HighestRxSignalStrength  Integer32,
        ibDot11LowestRxSignalStrength   Integer32,
        ibDot11RadioIfUpdownTimes       Counter32,
        ibDot11RadioIfLastChange        TimeTicks,
        ibDot11RadioModeSupport2        Unsigned32,
        ibDot11OperStatusCM             INTEGER,
        ibDot11AirPrimChnlBusy          Integer32,
        ibDot11AirPrimChnlTxBusy        Integer32,
        ibDot11AirPrimChnlRxBusy        Integer32,
        ibDot11AirExtChnlBusy           Integer32,
        ibDot11RadioType                Integer32,
        ibDot11RadioOper                Integer32,
        ibDot11BindSSID                 OCTET STRING,
        ibDot11RadioAverageSignalStrength Integer32,
        ibDot11RadioMaxSignalStrength   Integer32,
        ibDot11RadioMinSignalStrength   Integer32
    }

ibDot11CurAPID OBJECT-TYPE
    SYNTAX      OCTET STRING(SIZE(0..64))
    MAX-ACCESS  read-only
    STATUS      current
    DESCRIPTION
        "To uniquely identify a AP in running status."
    ::= { ibDot11APRadioEntry 1 }

ibDot11RadioID OBJECT-TYPE
    SYNTAX      Integer32(0..2147483647)
    MAX-ACCESS  read-only
    STATUS      current
    DESCRIPTION
        "Represents each radio."
    ::= { ibDot11APRadioEntry 2 }

ibDot11AdminStatus OBJECT-TYPE
    SYNTAX      TruthValue
    MAX-ACCESS  read-only
    STATUS      current
    DESCRIPTION
        "Represents the administrator status of radio."
    ::= { ibDot11APRadioEntry 3 }

ibDot11OperStatus OBJECT-TYPE
    SYNTAX      TruthValue
    MAX-ACCESS  read-only
    STATUS      current
    DESCRIPTION
        "Represents the operational status of radio."
    ::= { ibDot11APRadioEntry 4 }

ibDot11Channel OBJECT-TYPE
    SYNTAX      IbDot11ChannelScopeType
    MAX-ACCESS  read-only
    STATUS      current
    DESCRIPTION
        "Represents the current channel allocation for radio."
    ::= { ibDot11APRadioEntry 5 }

ibDot11TxPowerLevel OBJECT-TYPE
    SYNTAX      IbDot11TxPwrLevelScopeType
    UNITS       "dbm"
    MAX-ACCESS  read-only
    STATUS      current
    DESCRIPTION
        "Represents the current transmit power level for radio."
    ::= { ibDot11APRadioEntry 6 }

ibDot11APRadioIfIndex OBJECT-TYPE
    SYNTAX      Integer32
    MAX-ACCESS  read-only
    STATUS      current
    DESCRIPTION
        "Represents the interface index for the radio."
    ::= { ibDot11APRadioEntry 7 }

ibDot11AntennaGain OBJECT-TYPE
    SYNTAX      Integer32
    UNITS       "dBi"
    MAX-ACCESS  read-only
    STATUS      current
    DESCRIPTION
        "Represents the current gain for antenna."
    ::= { ibDot11APRadioEntry 8 }

ibDot11MaxBandwidth OBJECT-TYPE
    SYNTAX      Integer32
    UNITS       "Mbps"
    MAX-ACCESS  read-only
    STATUS      current
    DESCRIPTION
        "Represents the maximum bandwidth for the radio."
    ::= { ibDot11APRadioEntry 9 }

ibDot11ResourceUseRatio OBJECT-TYPE
    SYNTAX      Integer32
    UNITS       "onepercent"
    MAX-ACCESS  read-only
    STATUS      current
    DESCRIPTION
        "Represents the ratio of radio resource usage."
    ::= { ibDot11APRadioEntry 10 }

ibDot11RadioModeSupport OBJECT-TYPE
    SYNTAX      Unsigned32
    MAX-ACCESS  read-only
    STATUS      current
    DESCRIPTION
        "Represents radio type supported by the radio.
        The WLAN system supports the following possible radio type:
        dot11a(1),
        dot11b(2),
        dot11g(4),
        dot11gn(16),
        dot11an(32),
        dot11ac(64),
        dot11gac(128)
        For the radio, it could support multiple radio types at
        the same time.  So the value of this object could combine multiple
        values of radio type above.
        For example:
        For one radio which supports both dot11b and dot11g mode, when get
        value from the object, the value is 6(2 + 4)."
    ::= { ibDot11APRadioEntry 11 }

ibDot11TxPowerLevel2 OBJECT-TYPE
    SYNTAX      Integer32(1..8)
    MAX-ACCESS  read-only
    STATUS      current
    DESCRIPTION
        "The TxPowerLevel N currently being used to transmit data."
    ::= { ibDot11APRadioEntry 12 }

ibDot11PowerMgmtStatus OBJECT-TYPE
    SYNTAX      TruthValue
    MAX-ACCESS  read-only
    STATUS      current
    DESCRIPTION
        "Represents status of power management of the radio."
    ::= { ibDot11APRadioEntry 13 }

ibDot11ChannelSwitchTimes OBJECT-TYPE
    SYNTAX      Counter32
    MAX-ACCESS  read-only
    STATUS      current
    DESCRIPTION
        "Represents the channel switch times."
    ::= { ibDot11APRadioEntry 14 }

ibDot11AntennaType OBJECT-TYPE
    SYNTAX      OCTET STRING
    MAX-ACCESS  read-only
    STATUS      current
    DESCRIPTION
        "Represents type of the antenna which radio used."
    ::= { ibDot11APRadioEntry 15 }

ibDot11DiversitySelectionRx OBJECT-TYPE
    SYNTAX      TruthValue
    MAX-ACCESS  read-only
    STATUS      current
    DESCRIPTION
        "Represents the diversity selection received."
    ::= { ibDot11APRadioEntry 16 }

ibDot11MaxTxPwrLvl OBJECT-TYPE
    SYNTAX      OCTET STRING
    MAX-ACCESS  read-only
    STATUS      current
    DESCRIPTION
        "Represents the maximum transmit power."
    ::= { ibDot11APRadioEntry 17 }

ibDot11PwrAttRange OBJECT-TYPE
    SYNTAX      Integer32
    MAX-ACCESS  read-only
    STATUS      current
    DESCRIPTION
        "Represents the range of power attenuation."
    ::= { ibDot11APRadioEntry 18 }

ibDot11AvgRxSignalStrength OBJECT-TYPE
    SYNTAX      Integer32
    UNITS       "dBm"
    MAX-ACCESS  read-only
    STATUS      current
    DESCRIPTION
        "Represents the average received signal strength."
    ::= { ibDot11APRadioEntry 19 }

ibDot11HighestRxSignalStrength OBJECT-TYPE
    SYNTAX      Integer32
    UNITS       "dBm"
    MAX-ACCESS  read-only
    STATUS      current
    DESCRIPTION
        "Represents the highest received signal strength."
    ::= { ibDot11APRadioEntry 20 }

ibDot11LowestRxSignalStrength OBJECT-TYPE
    SYNTAX      Integer32
    UNITS       "dBm"
    MAX-ACCESS  read-only
    STATUS      current
    DESCRIPTION
        "Represents the lowest received signal strength."
    ::= { ibDot11APRadioEntry 21 }

ibDot11RadioIfUpdownTimes OBJECT-TYPE
    SYNTAX      Counter32
    MAX-ACCESS  read-only
    STATUS      current
    DESCRIPTION
        "Represents the up/down times on radio interface."
    ::= { ibDot11APRadioEntry 22 }

ibDot11RadioIfLastChange OBJECT-TYPE
    SYNTAX      TimeTicks
    MAX-ACCESS  read-only
    STATUS      current
    DESCRIPTION
        "Represents time at last change that occurred on radio interface."
    ::= { ibDot11APRadioEntry 23 }

ibDot11RadioModeSupport2 OBJECT-TYPE
    SYNTAX      Unsigned32
    MAX-ACCESS  read-only
    STATUS      current
    DESCRIPTION
        "Represents radio type supported by the radio.
        The WLAN system supports the following possible radio type:
        dot11a(1),
        dot11b(2),
        dot11g(4),
        dot11an(8),
        dot11gn(16),
        dot11gac(32),
        dot11ac(64)
        For the radio, it could support multiple radio types at
        the same time.  So the value of this object could combine multiple
        values of radio type above.
        For example:
        For one radio which supports both dot11b and dot11g mode, when get
        value from the object, the value is 6(2 + 4)."
    ::= { ibDot11APRadioEntry 24 }

ibDot11OperStatusCM OBJECT-TYPE
    SYNTAX      INTEGER
        {
            up(1),
            down(2),
            testing(3),
            admindown(4)
        }
    MAX-ACCESS  read-only
    STATUS      current
    DESCRIPTION
        "Represents the operational status of radio."
    ::= { ibDot11APRadioEntry 25 }

ibDot11AirPrimChnlBusy OBJECT-TYPE
    SYNTAX      Integer32(0..100 | 255)
    MAX-ACCESS  read-only
    STATUS      current
    DESCRIPTION
    "Represents air interface utilization on the primary channel.
    The value 255 represents an invalid value."
    ::= { ibDot11APRadioEntry 26 }

ibDot11AirPrimChnlTxBusy OBJECT-TYPE
    SYNTAX      Integer32(0..100 | 255)
    MAX-ACCESS  read-only
    STATUS      current
    DESCRIPTION
    "Represents air interface utilization for signal sending on the
    primary channel.
    The value 255 represents an invalid value."
    ::= { ibDot11APRadioEntry 27 }

ibDot11AirPrimChnlRxBusy OBJECT-TYPE
    SYNTAX      Integer32(0..100 | 255)
    MAX-ACCESS  read-only
    STATUS      current
    DESCRIPTION
    "Represents air interface utilization for signal receiving on the
    primary channel.
    The value 255 represents an invalid value."
    ::= { ibDot11APRadioEntry 28 }

ibDot11AirExtChnlBusy OBJECT-TYPE
    SYNTAX      Integer32(0..100 | 255)
    MAX-ACCESS  read-only
    STATUS      current
    DESCRIPTION
    "Represents air interface utilization on the secondary channel.
    The value 255 represents an invalid value."
    ::= { ibDot11APRadioEntry 29 }

ibDot11RadioType OBJECT-TYPE
    SYNTAX      Integer32
    MAX-ACCESS  read-only
    STATUS      current
    DESCRIPTION
    "Represents the radio type of the radio."
    ::= { ibDot11APRadioEntry 30 }

ibDot11RadioOper OBJECT-TYPE
    SYNTAX      Integer32
    MAX-ACCESS  read-write
    STATUS      current
    DESCRIPTION
    "Set the status of the radio."
    ::= { ibDot11APRadioEntry 31 }

ibDot11BindSSID OBJECT-TYPE
    SYNTAX      OCTET STRING
    MAX-ACCESS  read-only
    STATUS      current
    DESCRIPTION
    "Represents all SSIDs of the radio."
    ::= { ibDot11APRadioEntry 32 }

ibDot11RadioAverageSignalStrength OBJECT-TYPE
    SYNTAX      Integer32
    UNITS       "dBm"
    MAX-ACCESS  read-only
    STATUS      current
    DESCRIPTION
        "Represents the average received signal strength."
    ::= { ibDot11APRadioEntry 33 }

ibDot11RadioMaxSignalStrength OBJECT-TYPE
    SYNTAX      Integer32
    UNITS       "dBm"
    MAX-ACCESS  read-only
    STATUS      current
    DESCRIPTION
        "Represents the highest received signal strength."
    ::= { ibDot11APRadioEntry 34 }

ibDot11RadioMinSignalStrength OBJECT-TYPE
    SYNTAX      Integer32
    UNITS       "dBm"
    MAX-ACCESS  read-only
    STATUS      current
    DESCRIPTION
        "Represents the lowest received signal strength."
    ::= { ibDot11APRadioEntry 35 }

-- *****************************************************************************
-- *  End of ibDot11APRadioTable Definition
-- *****************************************************************************

-- *****************************************************************************
-- *  ibDot11APBSSTable Definition
-- *****************************************************************************
ibDot11APBSSTable OBJECT-TYPE
    SYNTAX      SEQUENCE OF IbDot11APBSSEntry
    MAX-ACCESS  not-accessible
    STATUS      current
    DESCRIPTION
        "After AP connect to AC and get AP template configuration,
        it will create BSS data structure for each radio.
        The table will describe BSS information of AP and service
        policy as per BSS."
    ::= { ibDot11APObjectGroup 4 }

ibDot11APBSSEntry OBJECT-TYPE
    SYNTAX      IbDot11APBSSEntry
    MAX-ACCESS  not-accessible
    STATUS      current
    DESCRIPTION
        "Each entry contains information of each BSS for specific radio."
    INDEX
        {
            ibDot11CurAPID,
            ibDot11RadioID,
            ibDot11WlanID
        }
    ::= { ibDot11APBSSTable 1 }

IbDot11APBSSEntry ::= SEQUENCE
    {
        ibDot11WlanID             Integer32,
        ibDot11BSSID              MacAddress,
        ibDot11CurrSvcPolicyID    IbDot11ServicePolicyIDType,
        ibDot11SSID               OCTET STRING,
        ibDot11CurrSSIDResourceUseRatio             Integer32,
        ibDot11APEssVlanId                          Integer32
    }

ibDot11WlanID OBJECT-TYPE
    SYNTAX      Integer32(0..2147483647)
    MAX-ACCESS  not-accessible
    STATUS      current
    DESCRIPTION
        "Represents ID of a specific ESS."
    ::= { ibDot11APBSSEntry 1 }

ibDot11BSSID OBJECT-TYPE
    SYNTAX      MacAddress
    MAX-ACCESS  read-only
    STATUS      current
    DESCRIPTION
        "As MAC Address format, it is to identify BSS."
    ::= { ibDot11APBSSEntry 2 }

ibDot11CurrSvcPolicyID OBJECT-TYPE
    SYNTAX      IbDot11ServicePolicyIDType
    MAX-ACCESS  read-only
    STATUS      current
    DESCRIPTION
        "Represents the ID of each service policy used by the AP."
    ::= { ibDot11APBSSEntry 3 }

ibDot11SSID OBJECT-TYPE
    SYNTAX      OCTET STRING
    MAX-ACCESS  read-only
    STATUS      current
    DESCRIPTION
        "This object represents the SSID corresponding to this BSS."
    ::= { ibDot11APBSSEntry 4 }

ibDot11CurrSSIDResourceUseRatio OBJECT-TYPE
    SYNTAX      Integer32
    MAX-ACCESS  read-only
    STATUS      current
    DESCRIPTION
        "Represents the ratio of resource usage of curr SSID"
    ::= { ibDot11APBSSEntry 5 }

ibDot11APEssVlanId OBJECT-TYPE
    SYNTAX      Integer32
    MAX-ACCESS  read-only
    STATUS      current
    DESCRIPTION
        "This object represents the VlanID of the interface ESS
        corresponding to this BSS."
    ::= { ibDot11APBSSEntry 6 }
-- *****************************************************************************
-- *  End of ibDot11APBSSTable Definition
-- *****************************************************************************

-- *****************************************************************************
-- *  ibDot11APModelTable Definition
-- *****************************************************************************
ibDot11APModelTable OBJECT-TYPE
    SYNTAX      SEQUENCE OF IbDot11APModelEntry
    MAX-ACCESS  not-accessible
    STATUS      current
    DESCRIPTION
        "The table defines the capability information for a specific
        kind of AP."
    ::= { ibDot11APObjectGroup 5 }

ibDot11APModelEntry OBJECT-TYPE
    SYNTAX      IbDot11APModelEntry
    MAX-ACCESS  not-accessible
    STATUS      current
    DESCRIPTION
        "Each entry contains capability information for a specific kind
        of AP."
    INDEX
        {
            IMPLIED ibDot11APModelAlias
        }
    ::= { ibDot11APModelTable 1 }

IbDot11APModelEntry ::= SEQUENCE
    {
        ibDot11APModelAlias         OCTET STRING,
        ibDot11APModelName          OCTET STRING,
        ibDot11RadioNumSupport      IbDot11RadioScopeType,
        ibDot11StationNumSupport    Integer32,
        ibDot11MACModeSupport       IbDot11MACModeType,
        ibDot11APManufacturer       OCTET STRING,
        ibDot11APCPUType            OCTET STRING,
        ibDot11APCPUClockSpeed      Unsigned32,
        ibDot11APMemoryType         OCTET STRING,
        ibDot11APMemorySize         Unsigned32,
        ibDot11APFlashType          OCTET STRING,
        ibDot11APFlashSize          Unsigned32,
        ibDot11APMemSize            Gauge32,
        ibDot11APFlashSizeInBytes   Unsigned32,
        ibDot11WsmAPLicenseType     INTEGER
    }

ibDot11APModelAlias OBJECT-TYPE
    SYNTAX      OCTET STRING(SIZE(0..127))
    MAX-ACCESS  not-accessible
    STATUS      current
    DESCRIPTION
        "Represents alias of AP model name."
    ::= { ibDot11APModelEntry 1 }

ibDot11APModelName OBJECT-TYPE
    SYNTAX      OCTET STRING
    MAX-ACCESS  read-only
    STATUS      current
    DESCRIPTION
        "Represents AP model name(like WA2100)."
    ::= { ibDot11APModelEntry 2 }

ibDot11RadioNumSupport OBJECT-TYPE
    SYNTAX      IbDot11RadioScopeType
    MAX-ACCESS  read-only
    STATUS      current
    DESCRIPTION
        "Represents how many radios the specific AP model
        could support."
    ::= { ibDot11APModelEntry 3 }

ibDot11StationNumSupport OBJECT-TYPE
    SYNTAX      Integer32
    MAX-ACCESS  read-only
    STATUS      current
    DESCRIPTION
        "Represents how many station could be supported by a specific
        AP model."
    ::= { ibDot11APModelEntry 4 }

ibDot11MACModeSupport OBJECT-TYPE
    SYNTAX      IbDot11MACModeType
    MAX-ACCESS  read-only
    STATUS      current
    DESCRIPTION
        "Represents the MAC mode type could be supported by a specific
        AP model."
    DEFVAL      { split }
    ::= { ibDot11APModelEntry 5 }

ibDot11APManufacturer OBJECT-TYPE
    SYNTAX      OCTET STRING
    MAX-ACCESS  read-only
    STATUS      current
    DESCRIPTION
        "By the 'SMI Network Management Private Enterprise Codes'
        assigned by the IANA, NMS could know which vendor manufactures
        the AP."
    ::= { ibDot11APModelEntry 6 }

ibDot11APCPUType OBJECT-TYPE
    SYNTAX      OCTET STRING
    MAX-ACCESS  read-only
    STATUS      current
    DESCRIPTION
        "Represents the CPU type of AP"
    ::= { ibDot11APModelEntry 7 }

ibDot11APCPUClockSpeed OBJECT-TYPE
    SYNTAX      Unsigned32
    UNITS       "Hz"
    MAX-ACCESS  read-only
    STATUS      current
    DESCRIPTION
        "Represents the clock speed of CPU."
    ::= { ibDot11APModelEntry 8 }

ibDot11APMemoryType OBJECT-TYPE
    SYNTAX      OCTET STRING
    MAX-ACCESS  read-only
    STATUS      current
    DESCRIPTION
        "Represents the memory card type of AP"
    ::= { ibDot11APModelEntry 9 }

ibDot11APMemorySize OBJECT-TYPE
    SYNTAX      Unsigned32
    UNITS       "kbytes"
    MAX-ACCESS  read-only
    STATUS      current
    DESCRIPTION
        "Represents the size of AP memory card."
    ::= { ibDot11APModelEntry 20 }

ibDot11APFlashType OBJECT-TYPE
    SYNTAX      OCTET STRING
    MAX-ACCESS  read-only
    STATUS      current
    DESCRIPTION
        "Represents the flash card type of AP"
    ::= { ibDot11APModelEntry 11 }

ibDot11APFlashSize OBJECT-TYPE
    SYNTAX      Unsigned32
    UNITS       "kbytes"
    MAX-ACCESS  read-only
    STATUS      current
    DESCRIPTION
        "Represents the size of AP flash card."
    ::= { ibDot11APModelEntry 12 }

ibDot11APMemSize OBJECT-TYPE
    SYNTAX      Gauge32
    UNITS       "bytes"
    MAX-ACCESS  read-only
    STATUS      current
    DESCRIPTION
        "Represents the size of AP memory card."
    ::= { ibDot11APModelEntry 13 }

ibDot11APFlashSizeInBytes OBJECT-TYPE
    SYNTAX      Unsigned32
    UNITS       "bytes"
    MAX-ACCESS  read-only
    STATUS      current
    DESCRIPTION
        "This object represents the size of AP flash card in bytes."
    ::= { ibDot11APModelEntry 14 }

ibDot11WsmAPLicenseType OBJECT-TYPE
    SYNTAX      INTEGER
        {
            normal(1),
            wtu(2),
            wt(3),
            iot(4),
            other(5)
        }
    MAX-ACCESS  read-only
    STATUS      current
    DESCRIPTION
        "Represents AP license type for iMc WSM."
    ::= { ibDot11APModelEntry 15 }


-- *****************************************************************************
-- *  End of ibDot11APModelTable Definition
-- *****************************************************************************

-- *****************************************************************************
-- *  ibDot11APIfTable Definition
-- *****************************************************************************
ibDot11APIfTable OBJECT-TYPE
    SYNTAX      SEQUENCE OF IbDot11APIfEntry
    MAX-ACCESS  not-accessible
    STATUS      current
    DESCRIPTION
        "This table represents the AP interface information."
    ::= { ibDot11APObjectGroup 6 }

ibDot11APIfEntry OBJECT-TYPE
    SYNTAX      IbDot11APIfEntry
    MAX-ACCESS  not-accessible
    STATUS      current
    DESCRIPTION
        "Each entry of the table will provide data for the interface of AP."
    INDEX
        {
            ibDot11APObjID,
            ibDot11APIfIndex
        }
    ::= { ibDot11APIfTable 1 }

IbDot11APIfEntry ::= SEQUENCE
    {
        ibDot11APIfIndex         Integer32,
        ibDot11APIfDescr         OCTET STRING,
        ibDot11APIfType          Integer32,
        ibDot11APIfMtu           Integer32,
        ibDot11APIfPHYAddress    OCTET STRING,
        ibDot11APIfSpeed         Integer32,
        ibDot11APIfInDataRate    Integer32,
        ibDot11APIfOutDataRate   Integer32,
        ibDot11APIfSpeedKbps     Gauge32,
        ibDot11APIfTypeCM        Integer32
    }

ibDot11APIfIndex OBJECT-TYPE
    SYNTAX      Integer32
    MAX-ACCESS  not-accessible
    STATUS      current
    DESCRIPTION
        "Represents the index for an interface."
    ::= { ibDot11APIfEntry 1 }

ibDot11APIfDescr OBJECT-TYPE
    SYNTAX      OCTET STRING
    MAX-ACCESS  read-only
    STATUS      current
    DESCRIPTION
        "Represents the interface description for an interface."
    ::= { ibDot11APIfEntry 2 }

ibDot11APIfType OBJECT-TYPE
    SYNTAX      Integer32
    MAX-ACCESS  read-only
    STATUS      current
    DESCRIPTION
        "Represents the interface type for an interface."
    ::= { ibDot11APIfEntry 3 }

ibDot11APIfMtu OBJECT-TYPE
    SYNTAX      Integer32
    MAX-ACCESS  read-write
    STATUS      current
    DESCRIPTION
        "Represents size of the largest datagram which can
        be sent/received on the interface, specified in octets."
    ::= { ibDot11APIfEntry 4 }

ibDot11APIfPHYAddress OBJECT-TYPE
    SYNTAX      OCTET STRING
    MAX-ACCESS  read-only
    STATUS      current
    DESCRIPTION
        "Represents the PHY address of interface."
    ::= { ibDot11APIfEntry 5 }

ibDot11APIfSpeed OBJECT-TYPE
    SYNTAX      Integer32
    UNITS       "Mbps"
    MAX-ACCESS  read-only
    STATUS      current
    DESCRIPTION
        "Represents maximum bandwidth of this interface."
    ::= { ibDot11APIfEntry 6 }

ibDot11APIfInDataRate OBJECT-TYPE
    SYNTAX      Integer32
    UNITS       "Kbps"
    MAX-ACCESS  read-only
    STATUS      current
    DESCRIPTION
        "Represents the average input data rate of this interface in
        latest 300 seconds."
    ::= { ibDot11APIfEntry 7 }

ibDot11APIfOutDataRate OBJECT-TYPE
    SYNTAX      Integer32
    UNITS       "Kbps"
    MAX-ACCESS  read-only
    STATUS      current
    DESCRIPTION
        "Represents the average output data rate of this interface in
        latest 300 seconds."
    ::= { ibDot11APIfEntry 8 }

ibDot11APIfSpeedKbps OBJECT-TYPE
    SYNTAX      Gauge32
    UNITS       "kbps"
    MAX-ACCESS  read-only
    STATUS      current
    DESCRIPTION
        "Represents maximum bandwidth of this interface."
    ::= { ibDot11APIfEntry 9 }

ibDot11APIfTypeCM OBJECT-TYPE
    SYNTAX      Integer32
    MAX-ACCESS  read-only
    STATUS      current
    DESCRIPTION
        "Represents the interface type."
    ::= { ibDot11APIfEntry 10 }

-- *****************************************************************************
-- *  End of ibDot11APIfTable Definition
-- *****************************************************************************

-- *****************************************************************************
-- *  ibDot11APSSIDObjectTable Definition
-- *****************************************************************************
ibDot11APSSIDObjectTable OBJECT-TYPE
    SYNTAX      SEQUENCE OF IbDot11APSSIDObjectEntry
    MAX-ACCESS  not-accessible
    STATUS      current
    DESCRIPTION
        "This table provides BSSID number configuration information
         based on SSID."
    ::= { ibDot11APObjectGroup 7 }

ibDot11APSSIDObjectEntry OBJECT-TYPE
    SYNTAX      IbDot11APSSIDObjectEntry
    MAX-ACCESS  not-accessible
    STATUS      current
    DESCRIPTION
        "Each entry provides BSSID number configuration information
         of a SSID."
    INDEX
        {
            ibDot11APConfigSPID
        }
    ::= { ibDot11APSSIDObjectTable 1 }

IbDot11APSSIDObjectEntry ::= SEQUENCE
    {
        ibDot11APConfigSPID              IbDot11ServicePolicyIDType,
        ibDot11APConfigSSIDName          IbDot11SSIDStringType,
        ibDot11APConfigBSSIDNum          Integer32,
        ibDot11APConfigPortalStaNum      Integer32,
        ibDot11APAssocStaNum             Integer32
    }

ibDot11APConfigSPID OBJECT-TYPE
    SYNTAX      IbDot11ServicePolicyIDType
    MAX-ACCESS  not-accessible
    STATUS      current
    DESCRIPTION
        "Represents the service policy ID."
    ::= { ibDot11APSSIDObjectEntry 1 }

ibDot11APConfigSSIDName OBJECT-TYPE
    SYNTAX      IbDot11SSIDStringType
    MAX-ACCESS  read-only
    STATUS      current
    DESCRIPTION
        "Represents the SSID name of this service policy."
    ::= { ibDot11APSSIDObjectEntry 2 }

ibDot11APConfigBSSIDNum OBJECT-TYPE
    SYNTAX      Integer32
    MAX-ACCESS  read-only
    STATUS      current
    DESCRIPTION
        "Represents the number of BSSID that be configured
         with current SSID."
    ::= { ibDot11APSSIDObjectEntry 3 }

ibDot11APConfigPortalStaNum OBJECT-TYPE
    SYNTAX      Integer32
    MAX-ACCESS  read-only
    STATUS      current
    DESCRIPTION
        "Represents the total number of associated protal
        stations with current SSID."
    ::= { ibDot11APSSIDObjectEntry 4 }

ibDot11APAssocStaNum OBJECT-TYPE
    SYNTAX      Integer32
    MAX-ACCESS  read-only
    STATUS      current
    DESCRIPTION
        "Represents the total number of associated stations with current SSID."
    ::= { ibDot11APSSIDObjectEntry 5 }

-- *****************************************************************************
-- *  End of ibDot11APSSIDObjectTable Definition
-- *****************************************************************************

-- *****************************************************************************
-- *  ibDot11APSysInfoTable Definition
-- *****************************************************************************
ibDot11APSysInfoTable OBJECT-TYPE
    SYNTAX      SEQUENCE OF IbDot11APSysInfoEntry
    MAX-ACCESS  not-accessible
    STATUS      current
    DESCRIPTION
        "The table provides the system information of the AP."
    ::= { ibDot11APObjectGroup 8 }

ibDot11APSysInfoEntry OBJECT-TYPE
    SYNTAX      IbDot11APSysInfoEntry
    MAX-ACCESS  not-accessible
    STATUS      current
    DESCRIPTION
        "Each entry provides system information of an AP."
    INDEX
        {
            ibDot11APElementIndex
        }
    ::= { ibDot11APSysInfoTable 1 }

IbDot11APSysInfoEntry ::= SEQUENCE
    {
        ibDot11APSysUpTime           TimeTicks,
        ibDot11APCPURTUsage          Integer32,
        ibDot11APCPUAvgUsage         Integer32,
        ibDot11APMemRTUsage          Integer32,
        ibDot11APMemAvgUsage         Integer32,
        ibDot11APIPAddressGateway    IpAddress,
        ibDot11APACAssociateStatus   INTEGER,
        ibDot11APManuBuildInfo       OCTET STRING,
        ibDot11APFlashFreeSize       Unsigned32,
        ibDot11APTemperature         Integer32
    }

ibDot11APSysUpTime OBJECT-TYPE
    SYNTAX      TimeTicks
    MAX-ACCESS  read-only
    STATUS      current
    DESCRIPTION
        "Represents how long AP has been powered on."
    ::= { ibDot11APSysInfoEntry 1 }

ibDot11APCPURTUsage OBJECT-TYPE
    SYNTAX      Integer32(0..100)
    UNITS       "onepercent"
    MAX-ACCESS  read-only
    STATUS      current
    DESCRIPTION
        "Represents the CPU real time usage for AP."
    ::= { ibDot11APSysInfoEntry 2 }

ibDot11APCPUAvgUsage OBJECT-TYPE
    SYNTAX      Integer32(0..100)
    UNITS       "onepercent"
    MAX-ACCESS  read-only
    STATUS      current
    DESCRIPTION
        "Represents the CPU average usage for AP."
    ::= { ibDot11APSysInfoEntry 3 }

ibDot11APMemRTUsage OBJECT-TYPE
    SYNTAX      Integer32(0..100)
    UNITS       "onepercent"
    MAX-ACCESS  read-only
    STATUS      current
    DESCRIPTION
        "Represents the memory real time usage for AP."
    ::= { ibDot11APSysInfoEntry 4 }

ibDot11APMemAvgUsage OBJECT-TYPE
    SYNTAX      Integer32(0..100)
    UNITS       "onepercent"
    MAX-ACCESS  read-only
    STATUS      current
    DESCRIPTION
        "Represents the average memory usage for AP."
    ::= { ibDot11APSysInfoEntry 5 }

ibDot11APIPAddressGateway OBJECT-TYPE
    SYNTAX      IpAddress
    MAX-ACCESS  read-only
    STATUS      current
    DESCRIPTION
        "Represents the IP address gateway for AP."
    ::= { ibDot11APSysInfoEntry 6 }

ibDot11APACAssociateStatus OBJECT-TYPE
    SYNTAX      INTEGER
        {
            associated(1),
            deassociated(2),
            downloadingImage(3)
        }
    MAX-ACCESS  read-only
    STATUS      current
    DESCRIPTION
        "Represents associate status of AP and AC."
    ::= { ibDot11APSysInfoEntry 7 }

ibDot11APManuBuildInfo OBJECT-TYPE
    SYNTAX      OCTET STRING(SIZE(0..255))
    MAX-ACCESS  read-only
    STATUS      current
    DESCRIPTION
        "Represents the device version information for AP."
    ::= { ibDot11APSysInfoEntry 8 }

ibDot11APFlashFreeSize OBJECT-TYPE
    SYNTAX      Unsigned32
    UNITS       "bytes"
    MAX-ACCESS  read-only
    STATUS      current
    DESCRIPTION
        "Represents the free size of AP flash card."
    ::= { ibDot11APSysInfoEntry 9 }

ibDot11APTemperature OBJECT-TYPE
    SYNTAX      Integer32
    MAX-ACCESS  read-only
    STATUS      current
    DESCRIPTION
        "Represents the device temperature information for AP."
    ::= { ibDot11APSysInfoEntry 10 }

-- *****************************************************************************
-- *  End of ibDot11APSysInfoTable Definition
-- *****************************************************************************

-- *****************************************************************************
-- *  ibDot11APIdleListTable Definition
-- *****************************************************************************
ibDot11APIdleListTable OBJECT-TYPE
    SYNTAX      SEQUENCE OF IbDot11APIdleListEntry
    MAX-ACCESS  not-accessible
    STATUS      current
    DESCRIPTION
        "This table provides the list of idle AP."
    ::= { ibDot11APObjectGroup 9 }

ibDot11APIdleListEntry OBJECT-TYPE
    SYNTAX      IbDot11APIdleListEntry
    MAX-ACCESS  not-accessible
    STATUS      current
    DESCRIPTION
        "Each entry provides information of a idle AP."
    INDEX
        {
            ibDot11APIdleTemplateName
        }
    ::= { ibDot11APIdleListTable 1 }

IbDot11APIdleListEntry ::= SEQUENCE
    {
        ibDot11APIdleTemplateName OCTET STRING,
        ibDot11APIdleSerialID     OCTET STRING
    }

ibDot11APIdleTemplateName OBJECT-TYPE
    SYNTAX      OCTET STRING(SIZE(0..127))
    MAX-ACCESS  not-accessible
    STATUS      current
    DESCRIPTION
        "Represents the name of idle AP template."
    ::= { ibDot11APIdleListEntry 1 }

ibDot11APIdleSerialID    OBJECT-TYPE
    SYNTAX      OCTET STRING
    MAX-ACCESS  read-only
    STATUS      current
    DESCRIPTION
        "Represents AP serial ID."
    ::= { ibDot11APIdleListEntry 2 }

-- *****************************************************************************
-- *  End of ibDot11APIdleListTable Definition
-- *****************************************************************************

-- *****************************************************************************
-- *  ibDot11APSysInfoByAPIDTable Definition
-- *****************************************************************************
ibDot11APSysInfoByAPIDTable OBJECT-TYPE
    SYNTAX      SEQUENCE OF IbDot11APSysInfoByAPIDEntry
    MAX-ACCESS  not-accessible
    STATUS      current
    DESCRIPTION
        "The table provides the system information of the AP."
    ::= { ibDot11APObjectGroup 10 }

ibDot11APSysInfoByAPIDEntry OBJECT-TYPE
    SYNTAX      IbDot11APSysInfoByAPIDEntry
    MAX-ACCESS  not-accessible
    STATUS      current
    DESCRIPTION
        "Each entry provides system information of an AP."
    INDEX
        {
            ibDot11APObjID
        }
    ::= { ibDot11APSysInfoByAPIDTable 1 }

IbDot11APSysInfoByAPIDEntry ::= SEQUENCE
    {
        ibDot11APSysUpTime2           TimeTicks,
        ibDot11APCPURTUsage2          Integer32,
        ibDot11APCPUAvgUsage2         Integer32,
        ibDot11APMemRTUsage2          Integer32,
        ibDot11APMemAvgUsage2         Integer32,
        ibDot11APIPAddressGateway2    IpAddress,
        ibDot11APACAssociateStatus2   INTEGER,
        ibDot11APManuBuildInfo2       OCTET STRING,
        ibDot11APFlashFreeSize2       Unsigned32,
        ibDot11APTemperature2         Integer32,
        ibDot11APMacAddress2          MacAddress,
        ibDot11APACAssociateStatusCM  INTEGER
    }

ibDot11APSysUpTime2 OBJECT-TYPE
    SYNTAX      TimeTicks
    MAX-ACCESS  read-only
    STATUS      current
    DESCRIPTION
        "Represents how long AP has been powered on."
    ::= { ibDot11APSysInfoByAPIDEntry 1 }

ibDot11APCPURTUsage2 OBJECT-TYPE
    SYNTAX      Integer32(0..100)
    UNITS       "onepercent"
    MAX-ACCESS  read-only
    STATUS      current
    DESCRIPTION
        "Represents the CPU real time usage for AP."
    ::= { ibDot11APSysInfoByAPIDEntry 2 }

ibDot11APCPUAvgUsage2 OBJECT-TYPE
    SYNTAX      Integer32(0..100)
    UNITS       "onepercent"
    MAX-ACCESS  read-only
    STATUS      current
    DESCRIPTION
        "Represents the CPU average usage for AP."
    ::= { ibDot11APSysInfoByAPIDEntry 3 }

ibDot11APMemRTUsage2 OBJECT-TYPE
    SYNTAX      Integer32(0..100)
    UNITS       "onepercent"
    MAX-ACCESS  read-only
    STATUS      current
    DESCRIPTION
        "Represents the memory real time usage for AP."
    ::= { ibDot11APSysInfoByAPIDEntry 4 }

ibDot11APMemAvgUsage2 OBJECT-TYPE
    SYNTAX      Integer32(0..100)
    UNITS       "onepercent"
    MAX-ACCESS  read-only
    STATUS      current
    DESCRIPTION
        "Represents the average memory usage for AP."
    ::= { ibDot11APSysInfoByAPIDEntry 5 }

ibDot11APIPAddressGateway2 OBJECT-TYPE
    SYNTAX      IpAddress
    MAX-ACCESS  read-only
    STATUS      current
    DESCRIPTION
        "Represents the IP address gateway for AP."
    ::= { ibDot11APSysInfoByAPIDEntry 6 }

ibDot11APACAssociateStatus2 OBJECT-TYPE
    SYNTAX      INTEGER
        {
            associated(1),
            deassociated(2),
            downloadingImage(3)
        }
    MAX-ACCESS  read-only
    STATUS      current
    DESCRIPTION
        "Represents associate status of AP and AC."
    ::= { ibDot11APSysInfoByAPIDEntry 7 }

ibDot11APManuBuildInfo2 OBJECT-TYPE
    SYNTAX      OCTET STRING(SIZE(0..255))
    MAX-ACCESS  read-only
    STATUS      current
    DESCRIPTION
        "Represents the device version information for AP."
    ::= { ibDot11APSysInfoByAPIDEntry 8 }

ibDot11APFlashFreeSize2 OBJECT-TYPE
    SYNTAX      Unsigned32
    UNITS       "bytes"
    MAX-ACCESS  read-only
    STATUS      current
    DESCRIPTION
        "Represents the free size of AP flash card."
    ::= { ibDot11APSysInfoByAPIDEntry 9 }

ibDot11APTemperature2 OBJECT-TYPE
    SYNTAX      Integer32
    MAX-ACCESS  read-only
    STATUS      current
    DESCRIPTION
        "Represents the device temperature information for AP."
    ::= { ibDot11APSysInfoByAPIDEntry 10 }

ibDot11APMacAddress2 OBJECT-TYPE
    SYNTAX      MacAddress
    MAX-ACCESS  read-only
    STATUS      current
    DESCRIPTION
        "Represents the MAC address of AP."
    ::= { ibDot11APSysInfoByAPIDEntry 11 }

ibDot11APACAssociateStatusCM OBJECT-TYPE
    SYNTAX      INTEGER
        {
            deassociated(0),
            associated(1)
        }
    MAX-ACCESS  read-only
    STATUS      current
    DESCRIPTION
        "Represents associate status of AP and AC."
    ::= { ibDot11APSysInfoByAPIDEntry 12 }

-- *****************************************************************************
-- *  End of ibDot11APSysInfoByAPIDTable Definition
-- *****************************************************************************

-- *****************************************************************************
-- *  ibDot11WTUAPInfoTable Definition
-- *****************************************************************************
ibDot11WTUAPInfoTable OBJECT-TYPE
    SYNTAX      SEQUENCE OF IbDot11WTUAPInfoEntry
    MAX-ACCESS  not-accessible
    STATUS      current
    DESCRIPTION
        "The table provides relationship information between wireless terminator units (WTUs) and WTs."
    ::= { ibDot11APObjectGroup 11 }

ibDot11WTUAPInfoEntry OBJECT-TYPE
    SYNTAX      IbDot11WTUAPInfoEntry
    MAX-ACCESS  not-accessible
    STATUS      current
    DESCRIPTION
        "Each entry provides relationship information between a WTU and a WT."
    INDEX
        {
            ibDot11ContainerSerialID,
            ibDot11WTUAPSerialID
        }
    ::= { ibDot11WTUAPInfoTable 1 }

IbDot11WTUAPInfoEntry ::= SEQUENCE
    {
        ibDot11ContainerSerialID    IbDot11ObjectIDType,
        ibDot11WTUAPSerialID        IbDot11ObjectIDType,
        ibDot11WTUAPSubSlotID       Unsigned32
    }

ibDot11ContainerSerialID OBJECT-TYPE
    SYNTAX      IbDot11ObjectIDType
    MAX-ACCESS  not-accessible
    STATUS      current
    DESCRIPTION
        "Serial ID that uniquely identifies a WT."
    ::= { ibDot11WTUAPInfoEntry 1 }

ibDot11WTUAPSerialID OBJECT-TYPE
    SYNTAX      IbDot11ObjectIDType
    MAX-ACCESS  not-accessible
    STATUS      current
    DESCRIPTION
        "Serial ID that uniquely identifies a WTU."
    ::= { ibDot11WTUAPInfoEntry 2 }

ibDot11WTUAPSubSlotID OBJECT-TYPE
    SYNTAX      Unsigned32
    MAX-ACCESS  read-only
    STATUS      current
    DESCRIPTION
        "Represents the sub-slot ID of a WTU."
    ::= { ibDot11WTUAPInfoEntry 3 }

-- *****************************************************************************
-- *  End of ibDot11WTUAPInfoTable Definition
-- *****************************************************************************

-- *****************************************************************************
-- *  ibDot11ApBriefInfoTable Definition
-- *****************************************************************************
ibDot11ApBriefInfoTable OBJECT-TYPE
    SYNTAX      SEQUENCE OF IbDot11ApBriefInfoEntry
    MAX-ACCESS  not-accessible
    STATUS      current
    DESCRIPTION
        "The table provides AP information."
    ::= { ibDot11APObjectGroup 12 }

ibDot11ApBriefInfoEntry OBJECT-TYPE
    SYNTAX      IbDot11ApBriefInfoEntry
    MAX-ACCESS  not-accessible
    STATUS      current
    DESCRIPTION
        "Each entry contains information about an AP."
    INDEX
        {
            ibDot11BrfAPName
        }
    ::= { ibDot11ApBriefInfoTable 1 }

IbDot11ApBriefInfoEntry ::= SEQUENCE
    {
        ibDot11BrfAPName                 OCTET STRING,
        ibDot11BrfAPSerialID             OCTET STRING,
        ibDot11BrfAPModelName            OCTET STRING,
        ibDot11BrfAPDescription          OCTET STRING,
        ibDot11BrfAPStatisInterv         Integer32,
        ibDot11BrfAPStaIdleInterv        Integer32,
        ibDot11BrfAPStaKeepAliveInterv   Integer32,
        ibDot11BrfAPCir                  Integer32,
        ibDot11BrfAPCbs                  Integer32,
        ibDot11BrfAPPriorityLevel        Integer32,
        ibDot11BrfAPElementID            Integer32,
        ibDot11BrfAPSupportRadioMode     Integer32,
        ibDot11BrfAPControlAddressState  INTEGER,
        ibDot11BrfAPControlAddressIPv4   IpAddress,
        ibDot11BrfAPLocalACName          OCTET STRING,
        ibDot11BrfAPIPAddress            IpAddress,
        ibDot11BrfAPMacAddress           MacAddress,
        ibDot11BrfAPConnectType          INTEGER,
        ibDot11BrfAPIPv6Address          OCTET STRING,
        ibDot11BrfAPACPortIndex          Integer32,
        ibDot11BrfAPStaAssocCount        Integer32,
        ibDot11BrfAPImageName            OCTET STRING,
        ibDot11BrfAPSoftwareVersion      OCTET STRING,
        ibDot11BrfAPIPNetMask            IpAddress,
        ibDot11BrfAPOperationStatus      INTEGER
    }

ibDot11BrfAPName OBJECT-TYPE
    SYNTAX      OCTET STRING(SIZE(1..127))
    MAX-ACCESS  not-accessible
    STATUS      current
    DESCRIPTION
        "Represents the name of an AP template."
    ::= { ibDot11ApBriefInfoEntry 1 }

ibDot11BrfAPSerialID OBJECT-TYPE
    SYNTAX      OCTET STRING
    MAX-ACCESS  read-only
    STATUS      current
    DESCRIPTION
        "Represents an AP serial ID."
    ::= { ibDot11ApBriefInfoEntry 2 }

ibDot11BrfAPModelName OBJECT-TYPE
    SYNTAX      OCTET STRING
    MAX-ACCESS  read-only
    STATUS      current
    DESCRIPTION
        "Represents an AP model."
    ::= { ibDot11ApBriefInfoEntry 3 }

ibDot11BrfAPDescription OBJECT-TYPE
    SYNTAX      OCTET STRING
    MAX-ACCESS  read-only
    STATUS      current
    DESCRIPTION
        "Represents an AP description. The administrator can use
         the description to specify the location, owner, or other
         information of an AP."
    ::= { ibDot11ApBriefInfoEntry 4 }

ibDot11BrfAPStatisInterv OBJECT-TYPE
    SYNTAX      Integer32
    UNITS       "second"
    MAX-ACCESS  read-only
    STATUS      current
    DESCRIPTION
        "Represents the interval for collecting radio statistics."
    ::= { ibDot11ApBriefInfoEntry 5 }

ibDot11BrfAPStaIdleInterv OBJECT-TYPE
    SYNTAX      Integer32
    UNITS       "second"
    MAX-ACCESS  read-only
    STATUS      current
    DESCRIPTION
        "Represents the idle timeout for AP-client connections."
    ::= { ibDot11ApBriefInfoEntry 6 }

ibDot11BrfAPStaKeepAliveInterv OBJECT-TYPE
    SYNTAX      Integer32
    UNITS       "second"
    MAX-ACCESS  read-only
    STATUS      current
    DESCRIPTION
        "Represents the keepalive interval between AP and client."
    ::= { ibDot11ApBriefInfoEntry 7 }

ibDot11BrfAPCir OBJECT-TYPE
    SYNTAX      Integer32
    UNITS       "Kbps"
    MAX-ACCESS  read-only
    STATUS      current
    DESCRIPTION
        "Represents the committed information rate between AP and AC."
    ::= { ibDot11ApBriefInfoEntry 8 }

ibDot11BrfAPCbs OBJECT-TYPE
    SYNTAX      Integer32
    UNITS       "Bytes"
    MAX-ACCESS  read-only
    STATUS      current
    DESCRIPTION
        "Represents the committed burst size between AP and AC."
    ::= { ibDot11ApBriefInfoEntry 9 }

ibDot11BrfAPPriorityLevel OBJECT-TYPE
    SYNTAX      Integer32
    MAX-ACCESS  read-only
    STATUS      current
    DESCRIPTION
        "Represents the connection priority of an AP.
        If the connection priority is 7, the AC is considered as the
        primary AC for the AP."
    DEFVAL      { 4 }
    ::= { ibDot11ApBriefInfoEntry 10 }

ibDot11BrfAPElementID OBJECT-TYPE
    SYNTAX      Integer32
    MAX-ACCESS  read-only
    STATUS      current
    DESCRIPTION
        "Represents the AP element ID."
    ::= { ibDot11ApBriefInfoEntry 11 }

ibDot11BrfAPSupportRadioMode OBJECT-TYPE
    SYNTAX      Integer32
    MAX-ACCESS  read-only
    STATUS      current
    DESCRIPTION
        "Represents radio types supported by an AP.
        The WLAN system supports the following radio types:
        dot11b(1),
        dot11a(2),
        dot11g(4),
        dot11gn(8),
        dot11an(16),
        dot11gac(32),
        dot11ac(64),
        dot11gax(128),
        dot11ax(256)
        An AP can support multiple radio types at
        the same time. This field displays the sum of radio type values supported by an AP.
        For example:
        If an AP support both 802.11b and 802.11g, the value is 6, which is 2 plus 4."
    ::= { ibDot11ApBriefInfoEntry 12 }

ibDot11BrfAPControlAddressState OBJECT-TYPE
    SYNTAX      INTEGER
        {
            enable(1),
            disable(2)
        }
    MAX-ACCESS  read-only
    STATUS      current
    DESCRIPTION
        "Represents the status of control address for an AP.
        The following values are supported:
        enable      - AC rediscovery will be enabled.
        disable     - AC rediscovery will be disabled."
        DEFVAL      { disable }
    ::= { ibDot11ApBriefInfoEntry 13 }

ibDot11BrfAPControlAddressIPv4 OBJECT-TYPE
    SYNTAX      IpAddress
    MAX-ACCESS  read-only
    STATUS      current
    DESCRIPTION
        "Represents the AC IPv4 address for AC rediscovery."
    ::= { ibDot11ApBriefInfoEntry 14 }

ibDot11BrfAPLocalACName OBJECT-TYPE
    SYNTAX      OCTET STRING
    MAX-ACCESS  read-only
    STATUS      current
    DESCRIPTION
        "Represents the local AC name for an AP."
    ::= { ibDot11ApBriefInfoEntry 15 }

ibDot11BrfAPIPAddress OBJECT-TYPE
    SYNTAX      IpAddress
    MAX-ACCESS  read-only
    STATUS      current
    DESCRIPTION
        "Represents the IP address of an AP."
    ::= { ibDot11ApBriefInfoEntry 16 }

ibDot11BrfAPMacAddress OBJECT-TYPE
    SYNTAX      MacAddress
    MAX-ACCESS  read-only
    STATUS      current
    DESCRIPTION
        "Represents the MAC address of an AP."
    ::= { ibDot11ApBriefInfoEntry 17 }

ibDot11BrfAPConnectType OBJECT-TYPE
    SYNTAX      INTEGER
        {
            master(1),
            standBy(2),
            notAvailable(3)
        }
    MAX-ACCESS  read-only
    STATUS      current
    DESCRIPTION
        "Represents the current connection type."
    ::= { ibDot11ApBriefInfoEntry 18 }

ibDot11BrfAPIPv6Address OBJECT-TYPE
    SYNTAX      OCTET STRING
    MAX-ACCESS  read-only
    STATUS      current
    DESCRIPTION
        "Represents the IPv6 address of an AP."
    ::= { ibDot11ApBriefInfoEntry 19 }

ibDot11BrfAPACPortIndex OBJECT-TYPE
    SYNTAX      Integer32
    MAX-ACCESS  read-only
    STATUS      current
    DESCRIPTION
        "Represents the port on the AC, through which the traffic of an AP is transmitted.
         NMS might use the value as access information in MIB-2."
    ::= { ibDot11ApBriefInfoEntry 20 }

ibDot11BrfAPStaAssocCount OBJECT-TYPE
    SYNTAX      Integer32
    MAX-ACCESS  read-only
    STATUS      current
    DESCRIPTION
        "Represents the total number of stations associated with an AP."
    ::= { ibDot11ApBriefInfoEntry 21 }

ibDot11BrfAPImageName OBJECT-TYPE
    SYNTAX      OCTET STRING
    MAX-ACCESS  read-only
    STATUS      current
    DESCRIPTION
        "Represents the image file name of an AP."
    ::= { ibDot11ApBriefInfoEntry 22 }

ibDot11BrfAPSoftwareVersion OBJECT-TYPE
    SYNTAX      OCTET STRING
    MAX-ACCESS  read-only
    STATUS      current
    DESCRIPTION
        "Represents the software version of an AP."
    ::= { ibDot11ApBriefInfoEntry 23 }

ibDot11BrfAPIPNetMask OBJECT-TYPE
    SYNTAX      IpAddress
    MAX-ACCESS  read-only
    STATUS      current
    DESCRIPTION
        "Represents the IP address mask of an AP."
    ::= { ibDot11ApBriefInfoEntry 24 }

ibDot11BrfAPOperationStatus OBJECT-TYPE
    SYNTAX      INTEGER
        {
            run(1),
            idle(2)
        }
    MAX-ACCESS  read-only
    STATUS      current
    DESCRIPTION
        "Represent the status of an AP. Options include:
        2: Idle.
        1: Run."
    ::= { ibDot11ApBriefInfoEntry 25 }

-- *****************************************************************************
-- *  End of ibDot11ApBriefInfoTable Definition
-- *****************************************************************************

-- *****************************************************************************
-- *  ibDot11MaxPowerCapaTable Definition
-- *****************************************************************************
ibDot11MaxPowerCapaTable OBJECT-TYPE
    SYNTAX      SEQUENCE OF IbDot11MaxPowerCapaEntry
    MAX-ACCESS  not-accessible
    STATUS      current
    DESCRIPTION
        "The table provides max power capabilities of APs."
    ::= { ibDot11APObjectGroup 13 }

ibDot11MaxPowerCapaEntry OBJECT-TYPE
    SYNTAX      IbDot11MaxPowerCapaEntry
    MAX-ACCESS  not-accessible
    STATUS      current
    DESCRIPTION
        "Each entry of the table provides max power information for an AP."
    INDEX
        {
            ibDot11MaxPowerCapaApName,
            ibDot11MaxPowerCapaRadioId,
            ibDot11MaxPowerCapaRadioType,
            ibDot11MaxPowerCapaChl
        }
    ::= { ibDot11MaxPowerCapaTable 1 }

IbDot11MaxPowerCapaEntry ::= SEQUENCE
    {
        ibDot11MaxPowerCapaApName        OCTET STRING,
        ibDot11MaxPowerCapaRadioId       Integer32,
        ibDot11MaxPowerCapaRadioType     Integer32,
        ibDot11MaxPowerCapaChl           Integer32,
        ibDot11MaxPowerCapability        Integer32
    }

ibDot11MaxPowerCapaApName OBJECT-TYPE
    SYNTAX      OCTET STRING
    MAX-ACCESS  not-accessible
    STATUS      current
    DESCRIPTION
        "Represents the name of an AP."
    ::= { ibDot11MaxPowerCapaEntry 1 }

ibDot11MaxPowerCapaRadioId OBJECT-TYPE
    SYNTAX      Integer32
    MAX-ACCESS  not-accessible
    STATUS      current
    DESCRIPTION
        "Represents radio ID of an AP."
    ::= { ibDot11MaxPowerCapaEntry 2 }

ibDot11MaxPowerCapaRadioType OBJECT-TYPE
    SYNTAX      Integer32
    MAX-ACCESS  not-accessible
    STATUS      current
    DESCRIPTION
        "Represents the radio type."
    ::= { ibDot11MaxPowerCapaEntry 3 }

ibDot11MaxPowerCapaChl OBJECT-TYPE
    SYNTAX      Integer32
    MAX-ACCESS  not-accessible
    STATUS      current
    DESCRIPTION
        "Represents the channel number of an AP."
    ::= { ibDot11MaxPowerCapaEntry 4 }

ibDot11MaxPowerCapability OBJECT-TYPE
    SYNTAX      Integer32
    MAX-ACCESS  read-only
    STATUS      current
    DESCRIPTION
        "Represents the max power."
    ::= { ibDot11MaxPowerCapaEntry 5 }

-- *****************************************************************************
-- *  End of ibDot11MaxPowerTable Definition
-- *****************************************************************************

-- *****************************************************************************
-- *  ibDot11APRxStatisTable Definition
-- *****************************************************************************
ibDot11APRxStatisTable OBJECT-TYPE
    SYNTAX      SEQUENCE OF IbDot11APRxStatisEntry
    MAX-ACCESS  not-accessible
    STATUS      current
    DESCRIPTION
        "The table will provide the receiving statistic for a specific
        radio of AP."
    ::= { ibDot11APStatisGroup 1 }

ibDot11APRxStatisEntry OBJECT-TYPE
    SYNTAX      IbDot11APRxStatisEntry
    MAX-ACCESS  not-accessible
    STATUS      current
    DESCRIPTION
        "Each entry of the table will provide the statistic data for
        each radio of a specific AP."
    INDEX
        {
            ibDot11CurAPID,
            ibDot11RadioID
        }
    ::= { ibDot11APRxStatisTable 1 }

IbDot11APRxStatisEntry ::= SEQUENCE
    {
        ibDot11RxFrameDupCnt          Counter32,
        ibDot11RxFrameCnt             Counter32,
        ibDot11RxUcastFrameCnt        Counter32,
        ibDot11RxBcastFrameCnt        Counter32,
        ibDot11RxMcastFrameCnt        Counter32,
        ibDot11RxDiscardFrameCnt      Counter32,
        ibDot11RxFragCnt              Counter32,
        ibDot11RxFcsErrCnt            Counter32,
        ibDot11RxFrameBytes           Counter32,
        ibDot11RxUcastFrameBytes      Counter32,
        ibDot11RxBcastFrameBytes      Counter32,
        ibDot11RxMcastFrameBytes      Counter32,
        ibDot11RxDiscardFrameBytes    Counter32,
        ibDot11RxMgmtFrameCnt         Counter32,
        ibDot11RxCtrlFrameCnt         Counter32,
        ibDot11RxDataFrameCnt         Counter32,
        ibDot11RxDecryptErrorCnt      Counter32,
        ibDot11RxAuthenFrameCnt       Counter32,
        ibDot11RxAssociateFrameCnt    Counter32,
        ibDot11RxFrameErrorRatio      Integer32,
        ibDot11RxPhyErrorCnt          Counter32,
        ibDot11RxMICErrorCnt          Counter32,
        ibDot11RxDataFrameBytes       Counter32,
        ibDot11RadioRxAverSnr         Integer32,
        ibDot11RxPayloadBytes         Counter32,
        ibDot11RxTrafficSpeed         Integer32,
        ibDot11RxUcastDataFrameCnt    Counter64,
        ibDot11RxNUcastDataFrameCnt   Counter64,
        ibDot11RxTotalDiscardFrameCnt Counter64,
        ibDot11RxTotalIPCheckErrPacketCnt    Counter64,
        ibDot11RxSignalStrengthPacketCntCM   OCTET STRING,
        ibDot11RxDataFrameCntCM              Counter32,
        ibDot11RxTotalFrameCnt               Counter64
    }

ibDot11RxFrameDupCnt OBJECT-TYPE
    SYNTAX      Counter32
    MAX-ACCESS  read-only
    STATUS      current
    DESCRIPTION
        "Represents the number of duplicate frames reception."
    ::= { ibDot11APRxStatisEntry 1 }

ibDot11RxFrameCnt OBJECT-TYPE
    SYNTAX      Counter32
    MAX-ACCESS  read-only
    STATUS      current
    DESCRIPTION
        "Represents the number of frames reception."
    ::= { ibDot11APRxStatisEntry 2 }

ibDot11RxUcastFrameCnt OBJECT-TYPE
    SYNTAX      Counter32
    MAX-ACCESS  read-only
    STATUS      current
    DESCRIPTION
        "Represents the number of unicast frames reception."
    ::= { ibDot11APRxStatisEntry 3 }

ibDot11RxBcastFrameCnt OBJECT-TYPE
    SYNTAX      Counter32
    MAX-ACCESS  read-only
    STATUS      current
    DESCRIPTION
        "Represents the number of broadcast frames reception."
    ::= { ibDot11APRxStatisEntry 4 }

ibDot11RxMcastFrameCnt OBJECT-TYPE
    SYNTAX      Counter32
    MAX-ACCESS  read-only
    STATUS      current
    DESCRIPTION
        "Represents the number of multicast frames reception."
    ::= { ibDot11APRxStatisEntry 5 }

ibDot11RxDiscardFrameCnt OBJECT-TYPE
    SYNTAX      Counter32
    MAX-ACCESS  read-only
    STATUS      current
    DESCRIPTION
        "Represents the number of frames discarded by AP."
    ::= { ibDot11APRxStatisEntry 6 }

ibDot11RxFragCnt OBJECT-TYPE
    SYNTAX      Counter32
    MAX-ACCESS  read-only
    STATUS      current
    DESCRIPTION
        "Represents the number of frame fragments reception."
    ::= { ibDot11APRxStatisEntry 7 }

ibDot11RxFcsErrCnt OBJECT-TYPE
    SYNTAX      Counter32
    MAX-ACCESS  read-only
    STATUS      current
    DESCRIPTION
        "Represents the number of FCS error frames reception."
    ::= { ibDot11APRxStatisEntry 8 }

ibDot11RxFrameBytes OBJECT-TYPE
    SYNTAX      Counter32
    MAX-ACCESS  read-only
    STATUS      current
    DESCRIPTION
        "Represents the bytes of frames reception."
    ::= { ibDot11APRxStatisEntry 9 }

ibDot11RxUcastFrameBytes OBJECT-TYPE
    SYNTAX      Counter32
    MAX-ACCESS  read-only
    STATUS      current
    DESCRIPTION
        "Represents the bytes of unicast frames reception."
    ::= { ibDot11APRxStatisEntry 10 }

ibDot11RxBcastFrameBytes OBJECT-TYPE
    SYNTAX      Counter32
    MAX-ACCESS  read-only
    STATUS      current
    DESCRIPTION
        "Represents the bytes of broadcast frames reception."
    ::= { ibDot11APRxStatisEntry 11 }

ibDot11RxMcastFrameBytes OBJECT-TYPE
    SYNTAX      Counter32
    MAX-ACCESS  read-only
    STATUS      current
    DESCRIPTION
        "Represents the bytes of multicast frames reception."
    ::= { ibDot11APRxStatisEntry 12 }

ibDot11RxDiscardFrameBytes OBJECT-TYPE
    SYNTAX      Counter32
    MAX-ACCESS  read-only
    STATUS      current
    DESCRIPTION
        "Represents the bytes of frames discarded by AP."
    ::= { ibDot11APRxStatisEntry 13 }

ibDot11RxMgmtFrameCnt OBJECT-TYPE
    SYNTAX      Counter32
    MAX-ACCESS  read-only
    STATUS      current
    DESCRIPTION
        "Represents the number of management frames reception."
    ::= { ibDot11APRxStatisEntry 14 }

ibDot11RxCtrlFrameCnt OBJECT-TYPE
    SYNTAX      Counter32
    MAX-ACCESS  read-only
    STATUS      current
    DESCRIPTION
        "Represents the number of control frames reception."
    ::= { ibDot11APRxStatisEntry 15 }

ibDot11RxDataFrameCnt OBJECT-TYPE
    SYNTAX      Counter32
    MAX-ACCESS  read-only
    STATUS      current
    DESCRIPTION
        "Represents the number of data frames reception."
    ::= { ibDot11APRxStatisEntry 16 }

ibDot11RxDecryptErrorCnt OBJECT-TYPE
    SYNTAX      Counter32
    MAX-ACCESS  read-only
    STATUS      current
    DESCRIPTION
        "Represents the number of decryption error."
    ::= { ibDot11APRxStatisEntry 17 }

ibDot11RxAuthenFrameCnt OBJECT-TYPE
    SYNTAX      Counter32
    MAX-ACCESS  read-only
    STATUS      current
    DESCRIPTION
        "Represents the number of authentication frame reception."
    ::= { ibDot11APRxStatisEntry 18 }

ibDot11RxAssociateFrameCnt OBJECT-TYPE
    SYNTAX      Counter32
    MAX-ACCESS  read-only
    STATUS      current
    DESCRIPTION
        "Represents the number of associate frame reception."
    ::= { ibDot11APRxStatisEntry 19 }

ibDot11RxFrameErrorRatio OBJECT-TYPE
    SYNTAX      Integer32
    UNITS       "onepercent"
    MAX-ACCESS  read-only
    STATUS      current
    DESCRIPTION
        "Represents the ratio of error frame."
    ::= { ibDot11APRxStatisEntry 20 }

ibDot11RxPhyErrorCnt OBJECT-TYPE
    SYNTAX      Counter32
    MAX-ACCESS  read-only
    STATUS      current
    DESCRIPTION
        "Represents the number of physical reception error."
    ::= { ibDot11APRxStatisEntry 21 }

ibDot11RxMICErrorCnt OBJECT-TYPE
    SYNTAX      Counter32
    MAX-ACCESS  read-only
    STATUS      current
    DESCRIPTION
        "Represents the number of MIC verification error."
    ::= { ibDot11APRxStatisEntry 22 }

ibDot11RxDataFrameBytes OBJECT-TYPE
    SYNTAX      Counter32
    MAX-ACCESS  read-only
    STATUS      current
    DESCRIPTION
        "Represents the bytes of data frames reception."
    ::= { ibDot11APRxStatisEntry 23 }

ibDot11RadioRxAverSnr OBJECT-TYPE
    SYNTAX      Integer32
    MAX-ACCESS  read-only
    STATUS      current
    DESCRIPTION
        "Represents the average signal noise rate of this radio."
    ::= { ibDot11APRxStatisEntry 24 }

ibDot11RxPayloadBytes OBJECT-TYPE
    SYNTAX      Counter32
    MAX-ACCESS  read-only
    STATUS      current
    DESCRIPTION
        "Represents the payload bytes of data frames reception."
    ::= { ibDot11APRxStatisEntry 25 }

ibDot11RxTrafficSpeed OBJECT-TYPE
    SYNTAX      Integer32
    UNITS       "byte/s"
    MAX-ACCESS  read-only
    STATUS      current
    DESCRIPTION
        "Represents the bytes of frames reception per second."
    ::= { ibDot11APRxStatisEntry 26 }

ibDot11RxUcastDataFrameCnt OBJECT-TYPE
    SYNTAX      Counter64
    MAX-ACCESS  read-only
    STATUS      current
    DESCRIPTION
        "Represents the number of unicast data frames reception."
    ::= { ibDot11APRxStatisEntry 27 }

ibDot11RxNUcastDataFrameCnt OBJECT-TYPE
    SYNTAX      Counter64
    MAX-ACCESS  read-only
    STATUS      current
    DESCRIPTION
        "Represents the number of non-unicast data frames reception."
    ::= { ibDot11APRxStatisEntry 28 }

ibDot11RxTotalDiscardFrameCnt OBJECT-TYPE
    SYNTAX      Counter64
    MAX-ACCESS  read-only
    STATUS      current
    DESCRIPTION
        "Represents the number of total frames discarded by radio."
    ::= { ibDot11APRxStatisEntry 29 }

ibDot11RxTotalIPCheckErrPacketCnt OBJECT-TYPE
    SYNTAX      Counter64
    MAX-ACCESS  read-only
    STATUS      current
    DESCRIPTION
        "Represents the total number of IP checksum error packets
        received through the current radio."
    ::= { ibDot11APRxStatisEntry 30 }

ibDot11RxSignalStrengthPacketCntCM OBJECT-TYPE
    SYNTAX      OCTET STRING
    MAX-ACCESS  read-only
    STATUS      current
    DESCRIPTION
        "Represents the count of received packets according to signal strength."
    ::= { ibDot11APRxStatisEntry 31 }

ibDot11RxDataFrameCntCM OBJECT-TYPE
    SYNTAX      Counter32
    MAX-ACCESS  read-only
    STATUS      current
    DESCRIPTION
        "Represents the number of received data frames, excluding retransmitted
        frames."
    ::= { ibDot11APRxStatisEntry 32 }

ibDot11RxTotalFrameCnt OBJECT-TYPE
    SYNTAX      Counter64
    MAX-ACCESS  read-only
    STATUS      current
    DESCRIPTION
        "Represents the total number of packets
        received through the current radio."
    ::= { ibDot11APRxStatisEntry 33 }

-- *****************************************************************************
-- *  End of ibDot11APRxStatisTable Definition
-- *****************************************************************************

-- *****************************************************************************
-- *  ibDot11APTxStatisTable Definition
-- *****************************************************************************
ibDot11APTxStatisTable OBJECT-TYPE
    SYNTAX      SEQUENCE OF IbDot11APTxStatisEntry
    MAX-ACCESS  not-accessible
    STATUS      current
    DESCRIPTION
        "The table will provide the transmission statistic for a
        specific radio of AP."
    ::= { ibDot11APStatisGroup 2 }

ibDot11APTxStatisEntry OBJECT-TYPE
    SYNTAX      IbDot11APTxStatisEntry
    MAX-ACCESS  not-accessible
    STATUS      current
    DESCRIPTION
        "Each entry of the table will provide the statistic data for
        each radio of a specific AP."
    INDEX
        {
            ibDot11CurAPID,
            ibDot11RadioID
        }
    ::= { ibDot11APTxStatisTable 1 }

IbDot11APTxStatisEntry ::= SEQUENCE
    {
        ibDot11TxFragCnt              Counter32,
        ibDot11FailedCnt              Counter32,
        ibDot11RetryCnt               Counter32,
        ibDot11MultiRetryCnt          Counter32,
        ibDot11RtsSuccessCnt          Counter32,
        ibDot11RtsFailCnt             Counter32,
        ibDot11AckFailCnt             Counter32,
        ibDot11TxFrameCnt             Counter32,
        ibDot11TxUcastFrameCnt        Counter32,
        ibDot11TxBcastFrameCnt        Counter32,
        ibDot11TxMcastFrameCnt        Counter32,
        ibDot11TxDiscardFrameCnt      Counter32,
        ibDot11TxFrameBytes           Counter32,
        ibDot11TxUcastFrameBytes      Counter32,
        ibDot11TxBcastFrameBytes      Counter32,
        ibDot11TxMcastFrameBytes      Counter32,
        ibDot11TxDiscardFrameBytes    Counter32,
        ibDot11TxAuthenFrameCnt       Counter32,
        ibDot11TxAssociateFrameCnt    Counter32,
        ibDot11TxFrameRetryRatio      Integer32,
        ibDot11TxDataFrameCnt         Counter32,
        ibDot11TxDataFrameBytes       Counter32,
        ibDot11TxMSDUCnt              Counter32,
        ibDot11TxDiscardMSDUCnt       Counter32,
        ibDot11RetryMSDUCnt           Counter32,
        ibDot11TxPayloadBytes         Counter32,
        ibDot11TxTrafficSpeed         Integer32,
        ibDot11TxErrFrameRatio        Integer32,
        ibDot11TxFrameRate            Integer32,
        ibDot11TxMgtFrameCnt          Counter32,
        ibDot11TxCtrlFrameCnt         Counter32,
        ibDot11TxMACErrCnt            Counter32,
        ibDot11TxErrFrameCnt          Counter32,
        ibDot11TxUcastDataFrameCnt    Counter64,
        ibDot11TxNUcastDataFrameCnt   Counter64,
        ibDot11TxTotalFrameCnt        Counter64
    }

ibDot11TxFragCnt OBJECT-TYPE
    SYNTAX      Counter32
    MAX-ACCESS  read-only
    STATUS      current
    DESCRIPTION
        "Represents the number of fragmented frames transmission."
    ::= { ibDot11APTxStatisEntry 1 }

ibDot11FailedCnt OBJECT-TYPE
    SYNTAX      Counter32
    MAX-ACCESS  read-only
    STATUS      current
    DESCRIPTION
        "Represents the number of transmission failures."
    ::= { ibDot11APTxStatisEntry 2 }

ibDot11RetryCnt OBJECT-TYPE
    SYNTAX      Counter32
    MAX-ACCESS  read-only
    STATUS      current
    DESCRIPTION
        "Represents the number of transmit retries."
    ::= { ibDot11APTxStatisEntry 3 }

ibDot11MultiRetryCnt OBJECT-TYPE
    SYNTAX      Counter32
    MAX-ACCESS  read-only
    STATUS      current
    DESCRIPTION
        "Represents the number of transmits that required more than
        one retry."
    ::= { ibDot11APTxStatisEntry 4 }

ibDot11RtsSuccessCnt OBJECT-TYPE
    SYNTAX      Counter32
    MAX-ACCESS  read-only
    STATUS      current
    DESCRIPTION
        "Represents the number of successful RTS (Request to send)
        transmission."
    ::= { ibDot11APTxStatisEntry 5 }

ibDot11RtsFailCnt OBJECT-TYPE
    SYNTAX      Counter32
    MAX-ACCESS  read-only
    STATUS      current
    DESCRIPTION
        "Represents the number of RTS transmission failures."
    ::= { ibDot11APTxStatisEntry 6 }

ibDot11AckFailCnt OBJECT-TYPE
    SYNTAX      Counter32
    MAX-ACCESS  read-only
    STATUS      current
    DESCRIPTION
        "Represents the number of acknowledgement failures."
    ::= { ibDot11APTxStatisEntry 7 }

ibDot11TxFrameCnt OBJECT-TYPE
    SYNTAX      Counter32
    MAX-ACCESS  read-only
    STATUS      current
    DESCRIPTION
        "Represents the total number of frames transmission."
    ::= { ibDot11APTxStatisEntry 8 }

ibDot11TxUcastFrameCnt OBJECT-TYPE
    SYNTAX      Counter32
    MAX-ACCESS  read-only
    STATUS      current
    DESCRIPTION
        "Represents the number of unicast frames transmission."
    ::= { ibDot11APTxStatisEntry 9 }

ibDot11TxBcastFrameCnt OBJECT-TYPE
    SYNTAX      Counter32
    MAX-ACCESS  read-only
    STATUS      current
    DESCRIPTION
        "Represents the number of broadcast frames transmission."
    ::= { ibDot11APTxStatisEntry 10 }

ibDot11TxMcastFrameCnt OBJECT-TYPE
    SYNTAX      Counter32
    MAX-ACCESS  read-only
    STATUS      current
    DESCRIPTION
        "Represents the number of multicast frames transmission."
    ::= { ibDot11APTxStatisEntry 11 }

ibDot11TxDiscardFrameCnt OBJECT-TYPE
    SYNTAX      Counter32
    MAX-ACCESS  read-only
    STATUS      current
    DESCRIPTION
        "Represents the number of frames discarded by AP."
    ::= { ibDot11APTxStatisEntry 12 }

ibDot11TxFrameBytes OBJECT-TYPE
    SYNTAX      Counter32
    MAX-ACCESS  read-only
    STATUS      current
    DESCRIPTION
        "Represents the total bytes of frames transmission."
    ::= { ibDot11APTxStatisEntry 13 }

ibDot11TxUcastFrameBytes OBJECT-TYPE
    SYNTAX      Counter32
    MAX-ACCESS  read-only
    STATUS      current
    DESCRIPTION
        "Represents the bytes of unicast frames transmission."
    ::= { ibDot11APTxStatisEntry 14 }

ibDot11TxBcastFrameBytes OBJECT-TYPE
    SYNTAX      Counter32
    MAX-ACCESS  read-only
    STATUS      current
    DESCRIPTION
        "Represents the bytes of broadcast frames transmission."
    ::= { ibDot11APTxStatisEntry 15 }

ibDot11TxMcastFrameBytes OBJECT-TYPE
    SYNTAX      Counter32
    MAX-ACCESS  read-only
    STATUS      current
    DESCRIPTION
        "Represents the bytes of multicast frames transmission."
    ::= { ibDot11APTxStatisEntry 16 }

ibDot11TxDiscardFrameBytes OBJECT-TYPE
    SYNTAX      Counter32
    MAX-ACCESS  read-only
    STATUS      current
    DESCRIPTION
        "Represents the bytes of discarded frames transmission."
    ::= { ibDot11APTxStatisEntry 17 }

ibDot11TxAuthenFrameCnt OBJECT-TYPE
    SYNTAX      Counter32
    MAX-ACCESS  read-only
    STATUS      current
    DESCRIPTION
        "Represents the number of authentication frame transmission."
    ::= { ibDot11APTxStatisEntry 18 }

ibDot11TxAssociateFrameCnt OBJECT-TYPE
    SYNTAX      Counter32
    MAX-ACCESS  read-only
    STATUS      current
    DESCRIPTION
        "Represents the number of associate frame transmission."
    ::= { ibDot11APTxStatisEntry 19 }

ibDot11TxFrameRetryRatio OBJECT-TYPE
    SYNTAX      Integer32
    UNITS       "onepercent"
    MAX-ACCESS  read-only
    STATUS      current
    DESCRIPTION
        "Represents the ratio of retry frame."
    ::= { ibDot11APTxStatisEntry 20 }

ibDot11TxDataFrameCnt OBJECT-TYPE
    SYNTAX      Counter32
    MAX-ACCESS  read-only
    STATUS      current
    DESCRIPTION
        "Represents the number of data frame transmission."
    ::= { ibDot11APTxStatisEntry 21 }

ibDot11TxDataFrameBytes OBJECT-TYPE
    SYNTAX      Counter32
    MAX-ACCESS  read-only
    STATUS      current
    DESCRIPTION
        "Represents the bytes of data frame transmission."
    ::= { ibDot11APTxStatisEntry 22 }

ibDot11TxMSDUCnt OBJECT-TYPE
    SYNTAX      Counter32
    MAX-ACCESS  read-only
    STATUS      current
    DESCRIPTION
        "Represents the total number of MSDU transmission."
    ::= { ibDot11APTxStatisEntry 23 }

ibDot11TxDiscardMSDUCnt OBJECT-TYPE
    SYNTAX      Counter32
    MAX-ACCESS  read-only
    STATUS      current
    DESCRIPTION
        "Represents the number of discarded MSDU transmission."
    ::= { ibDot11APTxStatisEntry 24 }

ibDot11RetryMSDUCnt OBJECT-TYPE
    SYNTAX      Counter32
    MAX-ACCESS  read-only
    STATUS      current
    DESCRIPTION
        "Represents the number of retransfer MSDU."
    ::= { ibDot11APTxStatisEntry 25 }

ibDot11TxPayloadBytes OBJECT-TYPE
    SYNTAX      Counter32
    MAX-ACCESS  read-only
    STATUS      current
    DESCRIPTION
        "Represents the payload bytes of data frames transmission."
    ::= { ibDot11APTxStatisEntry 26 }

ibDot11TxTrafficSpeed OBJECT-TYPE
    SYNTAX      Integer32
    UNITS       "byte/s"
    MAX-ACCESS  read-only
    STATUS      current
    DESCRIPTION
        "Represents the bytes of frames transmission per second."
    ::= { ibDot11APTxStatisEntry 27 }

ibDot11TxErrFrameRatio OBJECT-TYPE
    SYNTAX      Integer32
    UNITS       "onepercent"
    MAX-ACCESS  read-only
    STATUS      current
    DESCRIPTION
        "Represents the ratio of error frame."
    ::= { ibDot11APTxStatisEntry 28 }

ibDot11TxFrameRate OBJECT-TYPE
    SYNTAX      Integer32
    MAX-ACCESS  read-only
    STATUS      current
    DESCRIPTION
        "Represents the count of frames transmission per second."
    ::= { ibDot11APTxStatisEntry 29 }

ibDot11TxMgtFrameCnt OBJECT-TYPE
    SYNTAX      Counter32
    MAX-ACCESS  read-only
    STATUS      current
    DESCRIPTION
        "Represents the number of transmitted management frames."
    ::= { ibDot11APTxStatisEntry 30 }

ibDot11TxCtrlFrameCnt OBJECT-TYPE
    SYNTAX      Counter32
    MAX-ACCESS  read-only
    STATUS      current
    DESCRIPTION
        "Represents the number of transmission control frames."
    ::= { ibDot11APTxStatisEntry 31 }
ibDot11TxMACErrCnt OBJECT-TYPE
    SYNTAX      Counter32
    MAX-ACCESS  read-only
    STATUS      current
    DESCRIPTION
        "Represents the count of MAC error frame."
    ::= { ibDot11APTxStatisEntry 32 }

ibDot11TxErrFrameCnt OBJECT-TYPE
    SYNTAX      Counter32
    MAX-ACCESS  read-only
    STATUS      current
    DESCRIPTION
        "Represents the count of error frame."
    ::= { ibDot11APTxStatisEntry 33 }

ibDot11TxUcastDataFrameCnt OBJECT-TYPE
    SYNTAX      Counter64
    MAX-ACCESS  read-only
    STATUS      current
    DESCRIPTION
        "Represents the number of unicast data frames transmission."
    ::= { ibDot11APTxStatisEntry 34 }

ibDot11TxNUcastDataFrameCnt OBJECT-TYPE
    SYNTAX      Counter64
    MAX-ACCESS  read-only
    STATUS      current
    DESCRIPTION
        "Represents the number of non-unicast data frames transmission."
    ::= { ibDot11APTxStatisEntry 35 }

ibDot11TxTotalFrameCnt OBJECT-TYPE
    SYNTAX      Counter64
    MAX-ACCESS  read-only
    STATUS      current
    DESCRIPTION
        "Represents the number of total frames transmission."
    ::= { ibDot11APTxStatisEntry 36 }

-- *****************************************************************************
-- *  End of ibDot11APTxStatisTable Definition
-- *****************************************************************************

-- *****************************************************************************
-- *  ibDot11APAssocStatisTable Definition
-- *****************************************************************************
ibDot11APAssocStatisTable OBJECT-TYPE
    SYNTAX      SEQUENCE OF IbDot11APAssocStatisEntry
    MAX-ACCESS  not-accessible
    STATUS      current
    DESCRIPTION
        "The table will provide the station association statistic for AP."
    ::= { ibDot11APStatisGroup 3 }

ibDot11APAssocStatisEntry OBJECT-TYPE
    SYNTAX      IbDot11APAssocStatisEntry
    MAX-ACCESS  not-accessible
    STATUS      current
    DESCRIPTION
        "Each entry of the table will provide the statistic data of station
        association for AP."
    INDEX
        {
            ibDot11CurAPID
        }
    ::= { ibDot11APAssocStatisTable 1 }

IbDot11APAssocStatisEntry ::= SEQUENCE
    {
        ibDot11ApStationAssocSum          Counter32,
        ibDot11ApStationAssocFailSum      Counter32,
        ibDot11ApStationReassocSum        Counter32,
        ibDot11ApStationAssocRejectSum    Counter32,
        ibDot11ApStationExDeAuthenSum     Counter32,
        ibDot11ApStationCurAssocSum       Integer32,
        ibDot11ApStaCurAuthSuccSum        Integer32,
        ibDot11AllStationUpSumTime        Counter32,
        ibDot11ApStationAssocReqSum       Counter32,
        ibDot11AllStationUpSumTimeTicks   TimeTicks,
        ibDot11ApStationReassocReqSum     Counter32,
        ibDot11ApStationReassocFailSum    Counter32,
        ibDot11ApStationAssocRespSum       Counter32
    }

ibDot11ApStationAssocSum OBJECT-TYPE
    SYNTAX      Counter32
    MAX-ACCESS  read-only
    STATUS      current
    DESCRIPTION
        "Represents the total number of station association
        with this AP."
    ::= { ibDot11APAssocStatisEntry 1 }

ibDot11ApStationAssocFailSum OBJECT-TYPE
    SYNTAX      Counter32
    MAX-ACCESS  read-only
    STATUS      current
    DESCRIPTION
        "Represents the total number of station
        association failure with this AP."
    ::= { ibDot11APAssocStatisEntry 2 }

ibDot11ApStationReassocSum OBJECT-TYPE
    SYNTAX      Counter32
    MAX-ACCESS  read-only
    STATUS      current
    DESCRIPTION
        "Represents the total number of station reassociation with this AP."
    ::= { ibDot11APAssocStatisEntry 3 }

ibDot11ApStationAssocRejectSum OBJECT-TYPE
    SYNTAX      Counter32
    MAX-ACCESS  read-only
    STATUS      current
    DESCRIPTION
        "Represents the total number of station association rejected
        on account of resource limit with this AP."
    ::= { ibDot11APAssocStatisEntry 4 }

ibDot11ApStationExDeAuthenSum OBJECT-TYPE
    SYNTAX      Counter32
    MAX-ACCESS  read-only
    STATUS      current
    DESCRIPTION
        "Represents the total number of exceptional station deauthentication
        (Without sending a deauthentication to AP) with this AP."
    ::= { ibDot11APAssocStatisEntry 5 }

ibDot11ApStationCurAssocSum OBJECT-TYPE
    SYNTAX      Integer32
    MAX-ACCESS  read-only
    STATUS      current
    DESCRIPTION
        "Represents the total number of current associated stations
        with this AP."
    ::= { ibDot11APAssocStatisEntry 6 }

ibDot11ApStaCurAuthSuccSum OBJECT-TYPE
    SYNTAX      Integer32
    MAX-ACCESS  read-only
    STATUS      current
    DESCRIPTION
        "Represents the successful number of station authentication
        with this AP."
    ::= { ibDot11APAssocStatisEntry 7 }

ibDot11AllStationUpSumTime OBJECT-TYPE
    SYNTAX      Counter32
    UNITS       "minute"
    MAX-ACCESS  read-only
    STATUS      current
    DESCRIPTION
        "Represents the sum of duration of all stations which associate with
         this AP."
    ::= { ibDot11APAssocStatisEntry 8 }

ibDot11ApStationAssocReqSum OBJECT-TYPE
    SYNTAX      Counter32
    MAX-ACCESS  read-only
    STATUS      current
    DESCRIPTION
        "Represents the number of station association request with this AP."
    ::= { ibDot11APAssocStatisEntry 9 }

ibDot11AllStationUpSumTimeTicks OBJECT-TYPE
    SYNTAX      TimeTicks
    MAX-ACCESS  read-only
    STATUS      current
    DESCRIPTION
        "Represents the sum of duration of all stations which associate with
         this AP."
    ::= { ibDot11APAssocStatisEntry 10 }

ibDot11ApStationReassocReqSum OBJECT-TYPE
    SYNTAX      Counter32
    MAX-ACCESS  read-only
    STATUS      current
    DESCRIPTION
        "Represents the total number of station reassociation request
        with this AP."
    ::= { ibDot11APAssocStatisEntry 11 }

ibDot11ApStationReassocFailSum OBJECT-TYPE
    SYNTAX      Counter32
    MAX-ACCESS  read-only
    STATUS      current
    DESCRIPTION
        "Represents the total number of station reassociation failure
        with this AP."
    ::= { ibDot11APAssocStatisEntry 12 }

ibDot11ApStationAssocRespSum OBJECT-TYPE
    SYNTAX      Counter32
    MAX-ACCESS  read-only
    STATUS      current
    DESCRIPTION
        "Represents the number of this AP response with station association."
    ::= { ibDot11APAssocStatisEntry 13 }

-- *****************************************************************************
-- *  End of ibDot11APAssocStatisTable Definition
-- *****************************************************************************

-- *****************************************************************************
-- *  ibDot11BSSRxStatisTable Definition
-- *****************************************************************************
ibDot11BSSRxStatisTable OBJECT-TYPE
    SYNTAX      SEQUENCE OF IbDot11BSSRxStatisEntry
    MAX-ACCESS  not-accessible
    STATUS      current
    DESCRIPTION
        "The table will provide the reception statistic for a
        specific BSS on a radio."
    ::= { ibDot11APStatisGroup 4 }

ibDot11BSSRxStatisEntry OBJECT-TYPE
    SYNTAX      IbDot11BSSRxStatisEntry
    MAX-ACCESS  not-accessible
    STATUS      current
    DESCRIPTION
        "Each entry of the table will provide the statistic data for
        each BSS on a specific radio."
    INDEX
        {
            ibDot11CurAPID,
            ibDot11RadioID,
            ibDot11WlanID
        }
    ::= { ibDot11BSSRxStatisTable 1 }

IbDot11BSSRxStatisEntry ::= SEQUENCE
    {
        ibDot11BSSRxFrameCnt             Counter32,
        ibDot11BSSRxFrameBytes           Counter32,
        ibDot11BSSRxDataFrameCnt         Counter32,
        ibDot11BSSRxDataFrameBytes       Counter32,
        ibDot11BSSRxAssociateFrameCnt    Counter32,
        ibDot11BSSRxFrameErrorRatio      Integer32,
        ibDot11BSSRxPayloadBytes         Counter32,
        ibDot11BSSRxUniFrameCnt          Counter32,
        ibDot11BSSRxNonUniFrameCnt       Integer32,
        ibDot11BSSRxAuthenFrameCnt       Counter32,
        ibDot11BSSRxFrameErrCntCM        Counter32
    }

ibDot11BSSRxFrameCnt OBJECT-TYPE
    SYNTAX      Counter32
    MAX-ACCESS  read-only
    STATUS      current
    DESCRIPTION
        "Represents the number of frames reception with this BSS."
    ::= { ibDot11BSSRxStatisEntry 1 }

ibDot11BSSRxFrameBytes OBJECT-TYPE
    SYNTAX      Counter32
    MAX-ACCESS  read-only
    STATUS      current
    DESCRIPTION
        "Represents the bytes of frames reception with this BSS."
    ::= { ibDot11BSSRxStatisEntry 2 }

ibDot11BSSRxDataFrameCnt OBJECT-TYPE
    SYNTAX      Counter32
    MAX-ACCESS  read-only
    STATUS      current
    DESCRIPTION
        "Represents the number of data frames reception with this BSS."
    ::= { ibDot11BSSRxStatisEntry 3 }

ibDot11BSSRxDataFrameBytes OBJECT-TYPE
    SYNTAX      Counter32
    MAX-ACCESS  read-only
    STATUS      current
    DESCRIPTION
        "Represents the bytes of data frames reception with this BSS."
    ::= { ibDot11BSSRxStatisEntry 4 }

ibDot11BSSRxAssociateFrameCnt OBJECT-TYPE
    SYNTAX      Counter32
    MAX-ACCESS  read-only
    STATUS      current
    DESCRIPTION
        "Represents the number of associate frames reception with this BSS."
    ::= { ibDot11BSSRxStatisEntry 5 }

ibDot11BSSRxFrameErrorRatio OBJECT-TYPE
    SYNTAX      Integer32
    UNITS       "percent"
    MAX-ACCESS  read-only
    STATUS      current
    DESCRIPTION
        "Represents the ratio of error frames reception with this BSS."
    ::= { ibDot11BSSRxStatisEntry 6 }

ibDot11BSSRxPayloadBytes OBJECT-TYPE
    SYNTAX      Counter32
    MAX-ACCESS  read-only
    STATUS      current
    DESCRIPTION
        "Represents the payload bytes of data frames reception with this BSS."
    ::= { ibDot11BSSRxStatisEntry 7 }

ibDot11BSSRxUniFrameCnt OBJECT-TYPE
    SYNTAX      Counter32
    MAX-ACCESS  read-only
    STATUS      current
    DESCRIPTION
        "Represents the count of unicast frames received."
    ::= { ibDot11BSSRxStatisEntry 8 }

ibDot11BSSRxNonUniFrameCnt  OBJECT-TYPE
    SYNTAX      Integer32
    MAX-ACCESS  read-only
    STATUS      current
    DESCRIPTION
        "Represents the count of non-unicast frames received."
    ::= { ibDot11BSSRxStatisEntry 9 }

ibDot11BSSRxAuthenFrameCnt OBJECT-TYPE
    SYNTAX      Counter32
    MAX-ACCESS  read-only
    STATUS      current
    DESCRIPTION
        "Represents the count of authentication frames received."
    ::= { ibDot11BSSRxStatisEntry 10 }

ibDot11BSSRxFrameErrCntCM OBJECT-TYPE
    SYNTAX      Counter32
    MAX-ACCESS  read-only
    STATUS      current
    DESCRIPTION
        "Represents the count of error authentication frames received."
    ::= { ibDot11BSSRxStatisEntry 11 }

-- *****************************************************************************
-- *  End of ibDot11BSSRxStatisTable Definition
-- *****************************************************************************

-- *****************************************************************************
-- *  ibDot11BSSTxStatisTable Definition
-- *****************************************************************************
ibDot11BSSTxStatisTable OBJECT-TYPE
    SYNTAX      SEQUENCE OF IbDot11BSSTxStatisEntry
    MAX-ACCESS  not-accessible
    STATUS      current
    DESCRIPTION
        "The table will provide the transmission statistic for a
        specific BSS on a radio."
    ::= { ibDot11APStatisGroup 5 }

ibDot11BSSTxStatisEntry OBJECT-TYPE
    SYNTAX      IbDot11BSSTxStatisEntry
    MAX-ACCESS  not-accessible
    STATUS      current
    DESCRIPTION
        "Each entry of the table will provide the statistic data for
        each BSS on a specific radio."
    INDEX
        {
            ibDot11CurAPID,
            ibDot11RadioID,
            ibDot11WlanID
        }
    ::= { ibDot11BSSTxStatisTable 1 }

IbDot11BSSTxStatisEntry ::= SEQUENCE
    {
        ibDot11BSSTxFrameCnt             Counter32,
        ibDot11BSSTxFrameBytes           Counter32,
        ibDot11BSSTxDataFrameCnt         Counter32,
        ibDot11BSSTxDataFrameBytes       Counter32,
        ibDot11BSSTxAssociateFrameCnt    Counter32,
        ibDot11BSSTxPayloadBytes         Counter32,
        ibDot11BSSTxRetryCnt             Counter32,
        ibDot11BSSTxUniFrameCnt          Counter32,
        ibDot11BSSTxNonUniFrameCnt       Integer32,
        ibDot11BSSTxAuthenFrameCnt       Counter32,
        ibDot11BSSTxFrameErrCntCM        Counter32
    }

ibDot11BSSTxFrameCnt OBJECT-TYPE
    SYNTAX      Counter32
    MAX-ACCESS  read-only
    STATUS      current
    DESCRIPTION
        "Represents the total number of frames transmission with this BSS."
    ::= { ibDot11BSSTxStatisEntry 1 }

ibDot11BSSTxFrameBytes OBJECT-TYPE
    SYNTAX      Counter32
    MAX-ACCESS  read-only
    STATUS      current
    DESCRIPTION
        "Represents the total number of bytes transmission with this BSS."
    ::= { ibDot11BSSTxStatisEntry 2 }

ibDot11BSSTxDataFrameCnt OBJECT-TYPE
    SYNTAX      Counter32
    MAX-ACCESS  read-only
    STATUS      current
    DESCRIPTION
        "Represents the number of data frame transmission with this BSS."
    ::= { ibDot11BSSTxStatisEntry 3 }

ibDot11BSSTxDataFrameBytes OBJECT-TYPE
    SYNTAX      Counter32
    MAX-ACCESS  read-only
    STATUS      current
    DESCRIPTION
        "Represents the bytes of data frame transmission with this BSS."
    ::= { ibDot11BSSTxStatisEntry 4 }

ibDot11BSSTxAssociateFrameCnt OBJECT-TYPE
    SYNTAX      Counter32
    MAX-ACCESS  read-only
    STATUS      current
    DESCRIPTION
        "Represents the number of associate frame transmission with this BSS."
    ::= { ibDot11BSSTxStatisEntry 5 }

ibDot11BSSTxPayloadBytes OBJECT-TYPE
    SYNTAX      Counter32
    MAX-ACCESS  read-only
    STATUS      current
    DESCRIPTION
        "Represents the payload bytes of data frame transmission with this BSS."
    ::= { ibDot11BSSTxStatisEntry 6 }

ibDot11BSSTxRetryCnt   OBJECT-TYPE
    SYNTAX      Counter32
    MAX-ACCESS  read-only
    STATUS      current
    DESCRIPTION
        "Represents the count of bytes retransmitted with this BSS."
    ::= { ibDot11BSSTxStatisEntry 7 }

ibDot11BSSTxUniFrameCnt OBJECT-TYPE
    SYNTAX      Counter32
    MAX-ACCESS  read-only
    STATUS      current
    DESCRIPTION
        "Represents the count of unicast frames transmission with this BSS."
    ::= { ibDot11BSSTxStatisEntry 8 }

ibDot11BSSTxNonUniFrameCnt OBJECT-TYPE
    SYNTAX      Integer32
    MAX-ACCESS  read-only
    STATUS      current
    DESCRIPTION
        "Represents the number of non-unicast frames transmission with this BSS."
    ::= { ibDot11BSSTxStatisEntry 9 }

ibDot11BSSTxAuthenFrameCnt OBJECT-TYPE
    SYNTAX      Counter32
    MAX-ACCESS  read-only
    STATUS      current
    DESCRIPTION
        "Represents the count of authentication frames transmission with this BSS."
    ::= { ibDot11BSSTxStatisEntry 10 }

ibDot11BSSTxFrameErrCntCM OBJECT-TYPE
    SYNTAX      Counter32
    MAX-ACCESS  read-only
    STATUS      current
    DESCRIPTION
        "Represents the count of error authentication frames transmission with this BSS."
    ::= { ibDot11BSSTxStatisEntry 11 }

-- *****************************************************************************
-- *  End of ibDot11BSSTxStatisTable Definition
-- *****************************************************************************

-- *****************************************************************************
-- *  ibDot11BSSAssocStatisTable Definition
-- *****************************************************************************
ibDot11BSSAssocStatisTable OBJECT-TYPE
    SYNTAX      SEQUENCE OF IbDot11BSSAssocStatisEntry
    MAX-ACCESS  not-accessible
    STATUS      current
    DESCRIPTION
        "The table will provide the station association statistic for BSS."
    ::= { ibDot11APStatisGroup 6 }

ibDot11BSSAssocStatisEntry OBJECT-TYPE
    SYNTAX      IbDot11BSSAssocStatisEntry
    MAX-ACCESS  not-accessible
    STATUS      current
    DESCRIPTION
        "Each entry of the table will provide the statistic data of station
        association for BSS."
    INDEX
        {
            ibDot11CurAPID,
            ibDot11RadioID,
            ibDot11WlanID
        }
    ::= { ibDot11BSSAssocStatisTable 1 }

IbDot11BSSAssocStatisEntry ::= SEQUENCE
    {
        ibDot11BSSStationAssocSum          Counter32,
        ibDot11BSSStationAssocFailSum      Counter32,
        ibDot11BSSStationReassocSum        Counter32,
        ibDot11BSSStationAssocRejectSum    Counter32,
        ibDot11BSSStationExDeAssocSum      Counter32,
        ibDot11BSSStationCurAssocSum       Integer32,
        ibDot11BSSStationAssocReqSum       Counter32,
        ibDot11BSSStationCurAuthSum        Integer32
    }

ibDot11BSSStationAssocSum OBJECT-TYPE
    SYNTAX      Counter32
    MAX-ACCESS  read-only
    STATUS      current
    DESCRIPTION
        "Represents the total number of station association
        with this BSS."
    ::= { ibDot11BSSAssocStatisEntry 1 }

ibDot11BSSStationAssocFailSum OBJECT-TYPE
    SYNTAX      Counter32
    MAX-ACCESS  read-only
    STATUS      current
    DESCRIPTION
        "Represents the total number of station
        association failure with this BSS."
    ::= { ibDot11BSSAssocStatisEntry 2 }

ibDot11BSSStationReassocSum OBJECT-TYPE
    SYNTAX      Counter32
    MAX-ACCESS  read-only
    STATUS      current
    DESCRIPTION
        "Represents the total number of station reassociation
        with this BSS."
    ::= { ibDot11BSSAssocStatisEntry 3 }

ibDot11BSSStationAssocRejectSum OBJECT-TYPE
    SYNTAX      Counter32
    MAX-ACCESS  read-only
    STATUS      current
    DESCRIPTION
        "Represents the total number of station association rejected
        on account of resource limit with this BSS."
    ::= { ibDot11BSSAssocStatisEntry 4 }

ibDot11BSSStationExDeAssocSum OBJECT-TYPE
    SYNTAX      Counter32
    MAX-ACCESS  read-only
    STATUS      current
    DESCRIPTION
        "Represents the total number of exceptional station deauthentication
        (Without sending a deauthentication to AP) with this BSS."
    ::= { ibDot11BSSAssocStatisEntry 5 }

ibDot11BSSStationCurAssocSum OBJECT-TYPE
    SYNTAX      Integer32
    MAX-ACCESS  read-only
    STATUS      current
    DESCRIPTION
        "Represents the total number of current associated stations
        with this BSS."
    ::= { ibDot11BSSAssocStatisEntry 6 }

ibDot11BSSStationAssocReqSum OBJECT-TYPE
    SYNTAX      Counter32
    MAX-ACCESS  read-only
    STATUS      current
    DESCRIPTION
        "Represents the total number of station association request with
         this BSS."
    ::= { ibDot11BSSAssocStatisEntry 7 }

ibDot11BSSStationCurAuthSum OBJECT-TYPE
    SYNTAX      Integer32
    MAX-ACCESS  read-only
    STATUS      current
    DESCRIPTION
        "Represents the total number of current associated stations which have
        passed portal or 1x authentication with this BSS."
    ::= { ibDot11BSSAssocStatisEntry 8 }

-- *****************************************************************************
-- *  End of ibDot11BSSAssocStatisTable Definition
-- *****************************************************************************

-- *****************************************************************************
-- *  ibDot11APLinkStatisTable Definition
-- *****************************************************************************
ibDot11APLinkStatisTable OBJECT-TYPE
    SYNTAX      SEQUENCE OF IbDot11APLinkStatisEntry
    MAX-ACCESS  not-accessible
    STATUS      current
    DESCRIPTION
        "The table will provide the link statistic for AP."
    ::= { ibDot11APStatisGroup 7 }

ibDot11APLinkStatisEntry OBJECT-TYPE
    SYNTAX      IbDot11APLinkStatisEntry
    MAX-ACCESS  not-accessible
    STATUS      current
    DESCRIPTION
        "Each entry provides the link statistic of the AP."
    INDEX
        {
            ibDot11CurAPID
        }
    ::= { ibDot11APLinkStatisTable 1 }

IbDot11APLinkStatisEntry ::= SEQUENCE
    {
        ibDot11UpLinkUpDownTimes          Counter32,
        ibDot11DownLinkUpDownTimes        Counter32,
        ibDot11PrivateSrvRxFrameBytes     Counter64,
        ibDot11PrivateSrvTxFrameBytes     Counter64,
        ibDot11APInternetAllRxBytes       Counter64,
        ibDot11APInternetAllTxBytes       Counter64,
        ibDot11APLocalAllRxBytes          Counter64,
        ibDot11APLocalAllTxBytes          Counter64
    }

ibDot11UpLinkUpDownTimes OBJECT-TYPE
    SYNTAX      Counter32
    MAX-ACCESS  read-only
    STATUS      current
    DESCRIPTION
        "Represents up/down times of uplink interface of the AP."
    ::= { ibDot11APLinkStatisEntry 1 }

ibDot11DownLinkUpDownTimes OBJECT-TYPE
    SYNTAX      Counter32
    MAX-ACCESS  read-only
    STATUS      current
    DESCRIPTION
        "Represents up/down times of downlink interface of the AP."
    ::= { ibDot11APLinkStatisEntry 2 }

ibDot11PrivateSrvRxFrameBytes OBJECT-TYPE
    SYNTAX      Counter64
    MAX-ACCESS  read-only
    STATUS      current
    DESCRIPTION
        "Traffic bytes received from private services."
    ::= { ibDot11APLinkStatisEntry 3 }

ibDot11PrivateSrvTxFrameBytes OBJECT-TYPE
    SYNTAX      Counter64
    MAX-ACCESS  read-only
    STATUS      current
    DESCRIPTION
        "Traffic bytes sent to private services."
    ::= { ibDot11APLinkStatisEntry 4 }

ibDot11APInternetAllRxBytes OBJECT-TYPE
    SYNTAX      Counter64
    MAX-ACCESS  read-only
    STATUS      current
    DESCRIPTION
        "Internet traffic bytes received from stations."
    ::= { ibDot11APLinkStatisEntry 5 }

ibDot11APInternetAllTxBytes OBJECT-TYPE
    SYNTAX      Counter64
    MAX-ACCESS  read-only
    STATUS      current
    DESCRIPTION
        "Internet traffic bytes sent to stations."
    ::= { ibDot11APLinkStatisEntry 6 }

ibDot11APLocalAllRxBytes OBJECT-TYPE
    SYNTAX      Counter64
    MAX-ACCESS  read-only
    STATUS      current
    DESCRIPTION
        "Local traffic bytes received from stations."
    ::= { ibDot11APLinkStatisEntry 7 }

ibDot11APLocalAllTxBytes OBJECT-TYPE
    SYNTAX      Counter64
    MAX-ACCESS  read-only
    STATUS      current
    DESCRIPTION
        "Local traffic bytes sent to stations."
    ::= { ibDot11APLinkStatisEntry 8 }
-- *****************************************************************************
-- *  End of ibDot11APLinkStatisTable Definition
-- *****************************************************************************

-- *****************************************************************************
-- *  ibDot11RadioAssocStatisTable Definition
-- *****************************************************************************
ibDot11RadioAssocStatisTable OBJECT-TYPE
    SYNTAX      SEQUENCE OF IbDot11RadioAssocStatisEntry
    MAX-ACCESS  not-accessible
    STATUS      current
    DESCRIPTION
        "The table will provide the station association statistic for radio."
    ::= { ibDot11APStatisGroup 8 }

ibDot11RadioAssocStatisEntry OBJECT-TYPE
    SYNTAX      IbDot11RadioAssocStatisEntry
    MAX-ACCESS  not-accessible
    STATUS      current
    DESCRIPTION
        "Each entry of the table will provide the statistic data of station
        association for radio."
    INDEX
        {
            ibDot11CurAPID,
            ibDot11RadioID
        }
    ::= { ibDot11RadioAssocStatisTable 1 }

IbDot11RadioAssocStatisEntry ::= SEQUENCE
    {
        ibDot11RadioStaAssocSum          Counter32,
        ibDot11RadioStaAssocFailSum      Counter32,
        ibDot11RadioStaReassocSum        Counter32,
        ibDot11RadioStaAssocRejectSum    Counter32,
        ibDot11RadioStaExDeAssocSum      Counter32,
        ibDot11RadioStaCurAssocSum       Integer32
    }

ibDot11RadioStaAssocSum OBJECT-TYPE
    SYNTAX      Counter32
    MAX-ACCESS  read-only
    STATUS      current
    DESCRIPTION
        "Represents the total number of station association
        with this radio."
    ::= { ibDot11RadioAssocStatisEntry 1 }

ibDot11RadioStaAssocFailSum OBJECT-TYPE
    SYNTAX      Counter32
    MAX-ACCESS  read-only
    STATUS      current
    DESCRIPTION
        "Represents the total number of station
        association failure with this radio."
    ::= { ibDot11RadioAssocStatisEntry 2 }

ibDot11RadioStaReassocSum OBJECT-TYPE
    SYNTAX      Counter32
    MAX-ACCESS  read-only
    STATUS      current
    DESCRIPTION
        "Represents the total number of station re-association
        with this radio."
    ::= { ibDot11RadioAssocStatisEntry 3 }

ibDot11RadioStaAssocRejectSum OBJECT-TYPE
    SYNTAX      Counter32
    MAX-ACCESS  read-only
    STATUS      current
    DESCRIPTION
        "Represents the total number of station association rejected
        on account of resource limit with this radio."
    ::= { ibDot11RadioAssocStatisEntry 4 }

ibDot11RadioStaExDeAssocSum OBJECT-TYPE
    SYNTAX      Counter32
    MAX-ACCESS  read-only
    STATUS      current
    DESCRIPTION
        "Represents the total number of exceptional station de-authentication
        (Without sending a de-authentication to AP) with this radio."
    ::= { ibDot11RadioAssocStatisEntry 5 }

ibDot11RadioStaCurAssocSum OBJECT-TYPE
    SYNTAX      Integer32
    MAX-ACCESS  read-only
    STATUS      current
    DESCRIPTION
        "Represents the total number of current associated stations
        with this radio."
    ::= { ibDot11RadioAssocStatisEntry 6 }
-- *****************************************************************************
-- *  End of ibDot11RadioAssocStatisTable Definition
-- *****************************************************************************

-- *****************************************************************************
-- *  ibDot11RadioMngFrameStatisTable Definition
-- *****************************************************************************
ibDot11RadioMngFrameStatisTable OBJECT-TYPE
    SYNTAX      SEQUENCE OF IbDot11RadioMngFrameStatisEntry
    MAX-ACCESS  not-accessible
    STATUS      current
    DESCRIPTION
        "The table will provide the management frame statistic for this radio."
    ::= { ibDot11APStatisGroup 9 }

ibDot11RadioMngFrameStatisEntry OBJECT-TYPE
    SYNTAX      IbDot11RadioMngFrameStatisEntry
    MAX-ACCESS  not-accessible
    STATUS      current
    DESCRIPTION
        "Each entry of the table will provide the management
        frame statistic for this radio."
    INDEX
        {
            ibDot11RadioStatisIndex,
            ibDot11MngFrameType
        }
    ::= { ibDot11RadioMngFrameStatisTable 1 }

IbDot11RadioMngFrameStatisEntry ::= SEQUENCE
    {
        ibDot11RadioStatisIndex            IbDot11RadioElementIndex,
        ibDot11MngFrameType                INTEGER,
        ibDot11MngFrameCnt                 Counter32
    }

ibDot11RadioStatisIndex OBJECT-TYPE
    SYNTAX      IbDot11RadioElementIndex
    MAX-ACCESS  not-accessible
    STATUS      current
    DESCRIPTION
        "Represents index of radio."
    ::= { ibDot11RadioMngFrameStatisEntry 1 }

ibDot11MngFrameType   OBJECT-TYPE
    SYNTAX      INTEGER
        {
            assocReq(1),
            assocResp(2),
            reassocReq(3),
            reassocResp(4),
            probeReq(5),
            probeResp(6),
            beacon(7),
            atim(8),
            disassociation(9),
            authentication(10),
            deauthentication(11),
            action(12)
        }
    MAX-ACCESS  not-accessible
    STATUS      current
    DESCRIPTION
        "Represents the type of the management frame on this radio."
    ::= { ibDot11RadioMngFrameStatisEntry 2 }

ibDot11MngFrameCnt OBJECT-TYPE
    SYNTAX      Counter32
    MAX-ACCESS  read-only
    STATUS      current
    DESCRIPTION
        "Represents the total number of each type for management frame on this
        radio."
    ::= { ibDot11RadioMngFrameStatisEntry 3 }

-- *****************************************************************************
-- *  End of ibDot11RadioMngFrameStatisTable Definition
-- *****************************************************************************

-- *****************************************************************************
-- *  ibDot11APAuthFailStatisTable Definition
-- *****************************************************************************
ibDot11APAuthFailStatisTable OBJECT-TYPE
    SYNTAX      SEQUENCE OF IbDot11APAuthFailStatisEntry
    MAX-ACCESS  not-accessible
    STATUS      current
    DESCRIPTION
        "The table will provide the authentication failure statistic for this
         AP."
    ::= { ibDot11APStatisGroup 10 }

ibDot11APAuthFailStatisEntry OBJECT-TYPE
    SYNTAX      IbDot11APAuthFailStatisEntry
    MAX-ACCESS  not-accessible
    STATUS      current
    DESCRIPTION
        "Each entry of the table will provide the authentication failure
         statistic for this AP."
    INDEX
        {
            ibDot11CurAPID,
            ibDot11APAuthFailStatisType
        }
    ::= { ibDot11APAuthFailStatisTable 1 }

IbDot11APAuthFailStatisEntry ::= SEQUENCE
    {
        ibDot11APAuthFailStatisType                 INTEGER,
        ibDot11APAuthFailStatisCnt                  Counter32
    }

ibDot11APAuthFailStatisType OBJECT-TYPE
    SYNTAX      INTEGER
        {
            invalidation(1),
            overtime(2),
            rejected(3),
            other(4)
        }
    MAX-ACCESS  not-accessible
    STATUS      current
    DESCRIPTION
        "Represents the type of authentication
        failure with this AP."
    ::= { ibDot11APAuthFailStatisEntry 1 }

ibDot11APAuthFailStatisCnt   OBJECT-TYPE
    SYNTAX      Counter32
    MAX-ACCESS  read-only
    STATUS      current
    DESCRIPTION
        "Represents the total number of each type for authentication
        failure on this AP."
    ::= { ibDot11APAuthFailStatisEntry 2 }

-- *****************************************************************************
-- *  End of ibDot11APAuthFailStatisTable Definition
-- *****************************************************************************

-- *****************************************************************************
-- *  ibDot11APAssocFailStatisTable Definition
-- *****************************************************************************
ibDot11APAssocFailStatisTable OBJECT-TYPE
    SYNTAX      SEQUENCE OF IbDot11APAssocFailStatisEntry
    MAX-ACCESS  not-accessible
    STATUS      current
    DESCRIPTION
        "The table will provide the association failure statistic for
        this AP."
    ::= { ibDot11APStatisGroup 11 }

ibDot11APAssocFailStatisEntry OBJECT-TYPE
    SYNTAX      IbDot11APAssocFailStatisEntry
    MAX-ACCESS  not-accessible
    STATUS      current
    DESCRIPTION
        "Each entry of the table will provide the association failure statistic
         for this AP."
    INDEX
        {
            ibDot11CurAPID,
            ibDot11APAssocFailStatisType
        }
    ::= { ibDot11APAssocFailStatisTable 1 }

IbDot11APAssocFailStatisEntry ::= SEQUENCE
    {
        ibDot11APAssocFailStatisType                 INTEGER,
        ibDot11APAssocFailStatisCnt                  Counter32
    }

ibDot11APAssocFailStatisType OBJECT-TYPE
    SYNTAX      INTEGER
        {
            invalidation(1),
            overtime(2),
            rejected(3),
            other(4)
        }
    MAX-ACCESS  not-accessible
    STATUS      current
    DESCRIPTION
        "Represents the type of association failure
        with this AP."
    ::= { ibDot11APAssocFailStatisEntry 1 }

ibDot11APAssocFailStatisCnt   OBJECT-TYPE
    SYNTAX      Counter32
    MAX-ACCESS  read-only
    STATUS      current
    DESCRIPTION
        "Represents the total number of each type for
        association failure on this AP."
    ::= { ibDot11APAssocFailStatisEntry 2 }

-- *****************************************************************************
-- *  End of ibDot11APAssocFailStatisTable Definition
-- *****************************************************************************

-- *****************************************************************************
-- *  ibDot11APReassocStatisTable Definition
-- *****************************************************************************
ibDot11APReassocStatisTable OBJECT-TYPE
    SYNTAX      SEQUENCE OF IbDot11APReassocStatisEntry
    MAX-ACCESS  not-accessible
    STATUS      current
    DESCRIPTION
        "The table will provide the re-association statistic for this AP."
    ::= { ibDot11APStatisGroup 12 }

ibDot11APReassocStatisEntry OBJECT-TYPE
    SYNTAX      IbDot11APReassocStatisEntry
    MAX-ACCESS  not-accessible
    STATUS      current
    DESCRIPTION
        "Each entry of the table will provide the re-association statistic
        for this AP."
    INDEX
        {
            ibDot11CurAPID,
            ibDot11APReassocStatisType
        }
    ::= { ibDot11APReassocStatisTable 1 }

IbDot11APReassocStatisEntry ::= SEQUENCE
    {
        ibDot11APReassocStatisType                 INTEGER,
        ibDot11APReassocStatisCnt                  Counter32
    }

ibDot11APReassocStatisType OBJECT-TYPE
    SYNTAX      INTEGER
        {
            total(1),
            success(2),
            invalidation(3),
            overtime(4),
            rejected(5),
            other(6)
        }
    MAX-ACCESS  not-accessible
    STATUS      current
    DESCRIPTION
        "Represents the type of re-association with this AP."
    ::= { ibDot11APReassocStatisEntry 1 }

ibDot11APReassocStatisCnt   OBJECT-TYPE
    SYNTAX      Counter32
    MAX-ACCESS  read-only
    STATUS      current
    DESCRIPTION
        "Represents the total number of each type for re-association with
        this AP."
    ::= { ibDot11APReassocStatisEntry 2 }

-- *****************************************************************************
-- *  End of ibDot11APReassocStatisTable Definition
-- *****************************************************************************

-- *****************************************************************************
-- *  ibDot11APUserAuthStatisTable Definition
-- *****************************************************************************
ibDot11APUserAuthStatisTable OBJECT-TYPE
    SYNTAX      SEQUENCE OF IbDot11APUserAuthStatisEntry
    MAX-ACCESS  not-accessible
    STATUS      current
    DESCRIPTION
        "The table will provide the user authentication statistic for this AP."
    ::= { ibDot11APStatisGroup 13 }

ibDot11APUserAuthStatisEntry OBJECT-TYPE
    SYNTAX      IbDot11APUserAuthStatisEntry
    MAX-ACCESS  not-accessible
    STATUS      current
    DESCRIPTION
        "Each entry of the table will provide the user authentication statistic
        for this AP."
    INDEX
        {
            ibDot11CurAPID,
            ibDot11UserAuthStatisType
        }
    ::= { ibDot11APUserAuthStatisTable 1 }

IbDot11APUserAuthStatisEntry ::= SEQUENCE
    {
        ibDot11UserAuthStatisType                 INTEGER,
        ibDot11UserAuthStatisCnt                  Counter32
    }

ibDot11UserAuthStatisType OBJECT-TYPE
    SYNTAX      INTEGER
        {
            total(1),
            success(2),
            keyError(3),
            invalidation(4),
            overtime(5),
            rejected(6),
            other(7)
        }
    MAX-ACCESS  not-accessible
    STATUS      current
    DESCRIPTION
        "Represents the type of user authentication with this AP."
    ::= { ibDot11APUserAuthStatisEntry 1 }

ibDot11UserAuthStatisCnt   OBJECT-TYPE
    SYNTAX      Counter32
    MAX-ACCESS  read-only
    STATUS      current
    DESCRIPTION
        "Represents the total number of each type for user authentication with
        this AP."
    ::= { ibDot11APUserAuthStatisEntry 2 }

-- *****************************************************************************
-- *  End of ibDot11APUserAuthStatisTable Definition
-- *****************************************************************************

-- *****************************************************************************
-- *  ibDot11APDeauthStatisTable Definition
-- *****************************************************************************
ibDot11APDeauthStatisTable OBJECT-TYPE
    SYNTAX      SEQUENCE OF IbDot11APDeauthStatisEntry
    MAX-ACCESS  not-accessible
    STATUS      current
    DESCRIPTION
        "The table will provide the de-authentication statistic for this AP."
    ::= { ibDot11APStatisGroup 14 }

ibDot11APDeauthStatisEntry OBJECT-TYPE
    SYNTAX      IbDot11APDeauthStatisEntry
    MAX-ACCESS  not-accessible
    STATUS      current
    DESCRIPTION
        "Each entry of the table will provide the de-authentication statistic
         for this AP."
    INDEX
        {
            ibDot11CurAPID,
            ibDot11APDeauthStatisType
        }
    ::= { ibDot11APDeauthStatisTable 1 }

IbDot11APDeauthStatisEntry ::= SEQUENCE
    {
        ibDot11APDeauthStatisType                 INTEGER,
        ibDot11APDeauthStatisCnt                  Counter32
    }

ibDot11APDeauthStatisType OBJECT-TYPE
    SYNTAX      INTEGER
        {
            total(1),
            stationLeaving(2),
            shortResource(3),
            exception(4),
            other(5)
        }
    MAX-ACCESS  not-accessible
    STATUS      current
    DESCRIPTION
        "Represents the type of de-authentication for this AP."
    ::= { ibDot11APDeauthStatisEntry 1 }

ibDot11APDeauthStatisCnt   OBJECT-TYPE
    SYNTAX      Counter32
    MAX-ACCESS  read-only
    STATUS      current
    DESCRIPTION
        "Represents the total number of each type for de-authentication
         with this AP."
    ::= { ibDot11APDeauthStatisEntry 2 }

-- *****************************************************************************
-- *  End of ibDot11APDeauthStatisTable Definition
-- *****************************************************************************

-- *****************************************************************************
-- *  ibDot11APDeassocStatisTable Definition
-- *****************************************************************************
ibDot11APDeassocStatisTable OBJECT-TYPE
    SYNTAX      SEQUENCE OF IbDot11APDeassocStatisEntry
    MAX-ACCESS  not-accessible
    STATUS      current
    DESCRIPTION
        "The table will provide the de-association statistic for this AP."
    ::= { ibDot11APStatisGroup 15 }

ibDot11APDeassocStatisEntry OBJECT-TYPE
    SYNTAX      IbDot11APDeassocStatisEntry
    MAX-ACCESS  not-accessible
    STATUS      current
    DESCRIPTION
        "Each entry of the table will provide the de-association statistic
         for this AP."
    INDEX
        {
            ibDot11CurAPID,
            ibDot11APDeassocStatisType
        }
    ::= { ibDot11APDeassocStatisTable 1 }

IbDot11APDeassocStatisEntry ::= SEQUENCE
    {
        ibDot11APDeassocStatisType                 INTEGER,
        ibDot11APDeassocStatisCnt                  Counter32
    }

ibDot11APDeassocStatisType OBJECT-TYPE
    SYNTAX      INTEGER
        {
            total(1),
            stationLeaving(2),
            shortResource(3),
            exception(4),
            other(5)
        }
    MAX-ACCESS  not-accessible
    STATUS      current
    DESCRIPTION
        "Represents the type of de-association with this AP."
    ::= { ibDot11APDeassocStatisEntry 1 }

ibDot11APDeassocStatisCnt   OBJECT-TYPE
    SYNTAX      Counter32
    MAX-ACCESS  read-only
    STATUS      current
    DESCRIPTION
        "Represents the total number of each type for de-association
         with this AP."
    ::= { ibDot11APDeassocStatisEntry 2 }

-- *****************************************************************************
-- *  End of ibDot11APDeassocStatisTable Definition
-- *****************************************************************************
-- *****************************************************************************
-- *  ibDot11APAssocFailStatis2Table Definition
-- *****************************************************************************
ibDot11APAssocFailStatis2Table OBJECT-TYPE
    SYNTAX      SEQUENCE OF IbDot11APAssocFailStatis2Entry
    MAX-ACCESS  not-accessible
    STATUS      current
    DESCRIPTION
        "This table will provide statistic of association fails for each ap."
    ::= { ibDot11APStatisGroup 16 }

ibDot11APAssocFailStatis2Entry OBJECT-TYPE
    SYNTAX      IbDot11APAssocFailStatis2Entry
    MAX-ACCESS  not-accessible
    STATUS      current
    DESCRIPTION
        "Each entry will provide statistic of association fails for this ap."
    INDEX
        {
            ibDot11CurAPID,
            ibDot11APAssocFailStatis2Type
        }
    ::= { ibDot11APAssocFailStatis2Table 1 }

IbDot11APAssocFailStatis2Entry ::= SEQUENCE
    {
        ibDot11APAssocFailStatis2Type                 INTEGER,
        ibDot11APAssocFailStatis2Cnt                  Counter32
    }

ibDot11APAssocFailStatis2Type OBJECT-TYPE
    SYNTAX      INTEGER
        {
            shortResource(1),
            notSupportRateSet(2),
            unknownReasonCode(3),
            other(4),
            rssiLowness(5)
        }
    MAX-ACCESS  not-accessible
    STATUS      current
    DESCRIPTION
        "Represents the type of association fails for this AP"
    ::= { ibDot11APAssocFailStatis2Entry 1 }

ibDot11APAssocFailStatis2Cnt   OBJECT-TYPE
    SYNTAX      Counter32
    MAX-ACCESS  read-only
    STATUS      current
    DESCRIPTION
        "Represents the total count of association fails for this AP."
    ::= { ibDot11APAssocFailStatis2Entry 2 }

-- *****************************************************************************
-- *  End of ibDot11APAssocFailStatis2Table Definition
-- *****************************************************************************
-- *****************************************************************************
-- *  ibDot11APIfStatisTable Definition
-- *****************************************************************************
ibDot11APIfStatisTable OBJECT-TYPE
    SYNTAX      SEQUENCE OF IbDot11APIfStatisEntry
    MAX-ACCESS  not-accessible
    STATUS      current
    DESCRIPTION
        "The table will provide the statistics on the interface of the AP."
    ::= { ibDot11APStatisGroup 17 }

ibDot11APIfStatisEntry OBJECT-TYPE
    SYNTAX      IbDot11APIfStatisEntry
    MAX-ACCESS  not-accessible
    STATUS      current
    DESCRIPTION
        "Each entry of the table will provide statistics on the interface of the AP."
    INDEX
        {
            ibDot11APElementIndex,
            ibDot11APIfIndex
        }
    ::= { ibDot11APIfStatisTable 1 }

IbDot11APIfStatisEntry ::= SEQUENCE
    {
        ibDot11APIfInPkts              Counter32,
        ibDot11APIfInNormalPkts        Counter32,
        ibDot11APIfInErrorPkts         Counter32,
        ibDot11APIfOutPkts             Counter32,
        ibDot11APIfInOctets            Counter32,
        ibDot11APIfOutOctets           Counter32,
        ibDot11APIfFlowOut             Unsigned32,
        ibDot11APIfFlowIN              Unsigned32,
        ibDot11APIfInUcastPkts         Counter32,
        ibDot11APIfInNUcastPkts        Counter32,
        ibDot11APIfInDiscardPkts       Counter32,
        ibDot11APIfOutUcastPkts        Counter32,
        ibDot11APIfOutNUcastPkts       Counter32,
        ibDot11APIfOutDiscardPkts      Counter32,
        ibDot11APIfOutErrorPkts        Counter32,
        ibDot11APIfUpdownTimes         Counter32,
        ibDot11APIfStatusKeepTime      TimeTicks,
        ibDot11APIfOperStatus          INTEGER,
        ibDot11APIfInBrdcastPkts       Counter64,
        ibDot11APIfOutBrdcastPkts      Counter64,
        ibDot11APIfInMulcastPkts       Counter64,
        ibDot11APIfOutMulcastPkts      Counter64,
        ibDot11APIfInPayloadOctets     Counter64,
        ibDot11APIfOutPayloadOctets    Counter64
    }

ibDot11APIfInPkts OBJECT-TYPE
    SYNTAX      Counter32
    MAX-ACCESS  read-only
    STATUS      current
    DESCRIPTION
        "Represents the total number of packets received
         on the interface."
    ::= { ibDot11APIfStatisEntry 1 }

ibDot11APIfInNormalPkts OBJECT-TYPE
    SYNTAX      Counter32
    MAX-ACCESS  read-only
    STATUS      current
    DESCRIPTION
        "Represents the total number of correct
         packets received on the interface."
    ::= { ibDot11APIfStatisEntry 2 }

ibDot11APIfInErrorPkts OBJECT-TYPE
    SYNTAX      Counter32
    MAX-ACCESS  read-only
    STATUS      current
    DESCRIPTION
        "Represents the total number of error
         packets received on the interface."
    ::= { ibDot11APIfStatisEntry 3 }

ibDot11APIfOutPkts OBJECT-TYPE
    SYNTAX      Counter32
    MAX-ACCESS  read-only
    STATUS      current
    DESCRIPTION
        "Represents the total number of packets
         sent from the interface."
    ::= { ibDot11APIfStatisEntry 4 }

ibDot11APIfInOctets OBJECT-TYPE
    SYNTAX      Counter32
    MAX-ACCESS  read-only
    STATUS      current
    DESCRIPTION
        "Represents the total number of octets
         received on the interface."
    ::= { ibDot11APIfStatisEntry 5 }

ibDot11APIfOutOctets OBJECT-TYPE
    SYNTAX      Counter32
    MAX-ACCESS  read-only
    STATUS      current
    DESCRIPTION
        "Represents the total number of octets
         sent from the interface."
    ::= { ibDot11APIfStatisEntry 6 }

ibDot11APIfFlowOut OBJECT-TYPE
    SYNTAX      Unsigned32
    MAX-ACCESS  read-only
    STATUS      current
    DESCRIPTION
        "Represents the traffic rate (byte/s) on the uplink interface
         during a sampling period."
    ::= { ibDot11APIfStatisEntry 7 }

ibDot11APIfFlowIN OBJECT-TYPE
    SYNTAX      Unsigned32
    MAX-ACCESS  read-only
    STATUS      current
    DESCRIPTION
        "Represents the traffic rate (byte/s) on the downlink interface
         during a sampling period."
    ::= { ibDot11APIfStatisEntry 8 }

ibDot11APIfInUcastPkts OBJECT-TYPE
    SYNTAX      Counter32
    MAX-ACCESS  read-only
    STATUS      current
    DESCRIPTION
        "Represents the number of unicast packets received on the interface."
    ::= { ibDot11APIfStatisEntry 9 }

ibDot11APIfInNUcastPkts OBJECT-TYPE
    SYNTAX      Counter32
    MAX-ACCESS  read-only
    STATUS      current
    DESCRIPTION
        "Represents the number of non-unicast packets received on the wired
         interface."
    ::= { ibDot11APIfStatisEntry 10 }

ibDot11APIfInDiscardPkts OBJECT-TYPE
    SYNTAX      Counter32
    MAX-ACCESS  read-only
    STATUS      current
    DESCRIPTION
        "Represents the number of unicast packets discarded on the interface."
    ::= { ibDot11APIfStatisEntry 11 }

ibDot11APIfOutUcastPkts OBJECT-TYPE
    SYNTAX      Counter32
    MAX-ACCESS  read-only
    STATUS      current
    DESCRIPTION
        "Represents the number of unicast packets send on the interface."
    ::= { ibDot11APIfStatisEntry 12 }

ibDot11APIfOutNUcastPkts OBJECT-TYPE
    SYNTAX      Counter32
    MAX-ACCESS  read-only
    STATUS      current
    DESCRIPTION
        "Represents the number of non-unicast packets send on the interface."
    ::= { ibDot11APIfStatisEntry 13 }

ibDot11APIfOutDiscardPkts OBJECT-TYPE
    SYNTAX      Counter32
    MAX-ACCESS  read-only
    STATUS      current
    DESCRIPTION
        "Represents the number of discarded packets send on the interface."
    ::= { ibDot11APIfStatisEntry 14 }

ibDot11APIfOutErrorPkts OBJECT-TYPE
    SYNTAX      Counter32
    MAX-ACCESS  read-only
    STATUS      current
    DESCRIPTION
        "Represents the number of error packets send on the interface."
    ::= { ibDot11APIfStatisEntry 15 }

ibDot11APIfUpdownTimes OBJECT-TYPE
    SYNTAX      Counter32
    MAX-ACCESS  read-only
    STATUS      current
    DESCRIPTION
        "Represents the up/down times on the interface."
    ::= { ibDot11APIfStatisEntry 16 }

ibDot11APIfStatusKeepTime OBJECT-TYPE
    SYNTAX      TimeTicks
    MAX-ACCESS  read-only
    STATUS      current
    DESCRIPTION
        "Represents the last change time on the interface."
    ::= { ibDot11APIfStatisEntry 17 }

ibDot11APIfOperStatus OBJECT-TYPE
    SYNTAX  INTEGER {
                       up(1),        -- ready to pass packets
                       down(2),
                       testing(3),   -- in some test mode
                       unknown(4),   -- status can not be determined
                                     -- for some reason.
                       dormant(5),
                       notPresent(6),    -- some component is missing
                       lowerLayerDown(7) -- down due to state of
                                         -- lower-layer interface(s)
                    }
    MAX-ACCESS  read-only
    STATUS      current
    DESCRIPTION
        "Represents the operational state of the interface."
    ::= { ibDot11APIfStatisEntry 18 }

ibDot11APIfInBrdcastPkts OBJECT-TYPE
    SYNTAX      Counter64
    MAX-ACCESS  read-only
    STATUS      current
    DESCRIPTION
        "Represents the number of broadcast packets received on the interface."
    ::= { ibDot11APIfStatisEntry 19 }

ibDot11APIfOutBrdcastPkts OBJECT-TYPE
    SYNTAX      Counter64
    MAX-ACCESS  read-only
    STATUS      current
    DESCRIPTION
        "Represents the number of broadcast packets sent on the interface."
    ::= { ibDot11APIfStatisEntry 20 }

ibDot11APIfInMulcastPkts OBJECT-TYPE
    SYNTAX      Counter64
    MAX-ACCESS  read-only
    STATUS      current
    DESCRIPTION
        "Represents the number of multicast packets received on the interface."
    ::= { ibDot11APIfStatisEntry 21 }

ibDot11APIfOutMulcastPkts OBJECT-TYPE
    SYNTAX      Counter64
    MAX-ACCESS  read-only
    STATUS      current
    DESCRIPTION
        "Represents the number of multicast packets sent on the interface."
    ::= { ibDot11APIfStatisEntry 22 }

ibDot11APIfInPayloadOctets OBJECT-TYPE
    SYNTAX      Counter64
    MAX-ACCESS  read-only
    STATUS      current
    DESCRIPTION
        "Represents the number of actual octets received on the interface."
    ::= { ibDot11APIfStatisEntry 23 }

ibDot11APIfOutPayloadOctets OBJECT-TYPE
    SYNTAX      Counter64
    MAX-ACCESS  read-only
    STATUS      current
    DESCRIPTION
        "Represents the number of actual octets sent on the interface."
    ::= { ibDot11APIfStatisEntry 24 }

-- *****************************************************************************
-- *  End of ibDot11APIfStatisTable Definition
-- *****************************************************************************

-- *****************************************************************************
-- *  ibDot11RadioMngFrmStatisTable Definition
-- *****************************************************************************
ibDot11RadioMngFrmStatisTable OBJECT-TYPE
    SYNTAX      SEQUENCE OF IbDot11RadioMngFrmStatisEntry
    MAX-ACCESS  not-accessible
    STATUS      current
    DESCRIPTION
        "The table will provide the management frame statistic of this radio."
    ::= { ibDot11APStatisGroup 18 }

ibDot11RadioMngFrmStatisEntry OBJECT-TYPE
    SYNTAX      IbDot11RadioMngFrmStatisEntry
    MAX-ACCESS  not-accessible
    STATUS      current
    DESCRIPTION
        "Each entry of the table will provide the management
         frame statistic of this radio."
    INDEX
        {
            ibDot11CurAPID,
            ibDot11RadioID,
            ibDot11MngFrmType
        }
    ::= { ibDot11RadioMngFrmStatisTable 1 }

IbDot11RadioMngFrmStatisEntry ::= SEQUENCE
    {
        ibDot11MngFrmType                 INTEGER,
        ibDot11MngFrmCnt                  Counter32
    }

ibDot11MngFrmType  OBJECT-TYPE
    SYNTAX      INTEGER
        {
            assocReq(1),
            assocResp(2),
            reassocReq(3),
            reassocResp(4),
            probeReq(5),
            probeResp(6),
            beacon(7),
            atim(8),
            disassociation(9),
            authentication(10),
            deauthentication(11),
            action(12)
        }
    MAX-ACCESS  not-accessible
    STATUS      current
    DESCRIPTION
        "Represents the type of the management frame on this radio."
    ::= { ibDot11RadioMngFrmStatisEntry 1 }

ibDot11MngFrmCnt  OBJECT-TYPE
    SYNTAX      Counter32
    MAX-ACCESS  read-only
    STATUS      current
    DESCRIPTION
        "Represents the total number of each type of management frame on this
         radio."
    ::= { ibDot11RadioMngFrmStatisEntry 2 }
-- *****************************************************************************
-- *  End of ibDot11RadioMngFrmStatisTable Definition
-- *****************************************************************************


-- *****************************************************************************
-- *  ibDot11APPacketSizeStatisTable Definition
-- *****************************************************************************
ibDot11APPacketSizeStatisTable  OBJECT-TYPE
        SYNTAX        SEQUENCE OF IbDot11APPacketSizeStatisEntry
        MAX-ACCESS    not-accessible
        STATUS        current
        DESCRIPTION
                "This table provides packets statistic base on size."
        ::= { ibDot11APStatisGroup 19 }

ibDot11APPacketSizeStatisEntry  OBJECT-TYPE
        SYNTAX        IbDot11APPacketSizeStatisEntry
        MAX-ACCESS    not-accessible
        STATUS        current
        DESCRIPTION
                "Each entry provides packets statistic base on size for each radio
                 of a specific AP."
        INDEX
            {
                ibDot11CurAPID,
                ibDot11RadioID,
                ibDot11APPacketSize
            }
        ::= { ibDot11APPacketSizeStatisTable 1 }

IbDot11APPacketSizeStatisEntry    ::=SEQUENCE
        {
            ibDot11APPacketSize          INTEGER,
            ibDot11APRXPacketSizeCount   Counter64,
            ibDot11APTXPacketSizeCount   Counter64
        }

ibDot11APPacketSize    OBJECT-TYPE
        SYNTAX    INTEGER
            {
                sizeLevel1(1),
                sizeLevel2(2),
                sizeLevel3(3),
                sizeLevel4(4)
            }
        MAX-ACCESS    not-accessible
        STATUS        current
        DESCRIPTION
            "This node represents packet size:
                    sizeLevel1 : size <= 128
                    sizeLevel2 : 128 < size <= 512
                    sizeLevel3 : 512 < size <= 1024
                    sizeLevel4 : size > 1024"
    ::= { ibDot11APPacketSizeStatisEntry 1 }

ibDot11APRXPacketSizeCount    OBJECT-TYPE
        SYNTAX        Counter64
        MAX-ACCESS    read-only
        STATUS        current
        DESCRIPTION
                "Represents the count of packets reception base on frame size."
    ::= { ibDot11APPacketSizeStatisEntry 2 }

ibDot11APTXPacketSizeCount    OBJECT-TYPE
        SYNTAX        Counter64
        MAX-ACCESS    read-only
        STATUS        current
        DESCRIPTION
                "Represents the count of packets transmission base on frame size."
    ::= { ibDot11APPacketSizeStatisEntry 3 }
-- *****************************************************************************
-- *  End of ibDot11APPacketSizeStatisTable Definition
-- *****************************************************************************

-- *****************************************************************************
-- *  ibDot11APPacketRateStatisTable Definition
-- *****************************************************************************
ibDot11APPacketRateStatisTable  OBJECT-TYPE
        SYNTAX        SEQUENCE OF IbDot11APPacketRateStatisEntry
        MAX-ACCESS    not-accessible
        STATUS        current
        DESCRIPTION
                "This table provides packets statistic base on rate."
        ::= { ibDot11APStatisGroup 20 }

ibDot11APPacketRateStatisEntry  OBJECT-TYPE
        SYNTAX        IbDot11APPacketRateStatisEntry
        MAX-ACCESS    not-accessible
        STATUS        current
        DESCRIPTION
                "Each entry provides packets statistic base on rate for each radio
                 of a specific AP."
        INDEX
            {
                ibDot11CurAPID,
                ibDot11RadioID,
                ibDot11APPacketRate
            }
        ::= { ibDot11APPacketRateStatisTable 1 }

IbDot11APPacketRateStatisEntry    ::=SEQUENCE
        {
                ibDot11APPacketRate          Integer32,
                ibDot11APRXPacketRateCount   Counter64,
                ibDot11APTXPacketRateCount   Counter64
        }

ibDot11APPacketRate    OBJECT-TYPE
        SYNTAX        Integer32
        MAX-ACCESS    not-accessible
        STATUS        current
        DESCRIPTION
                "Represents transmit data rate(twice as actual rate)."
    ::= { ibDot11APPacketRateStatisEntry 1 }

ibDot11APRXPacketRateCount    OBJECT-TYPE
        SYNTAX        Counter64
        MAX-ACCESS    read-only
        STATUS        current
        DESCRIPTION
                "Represents the count of packets reception base on transmit data rate."
    ::= { ibDot11APPacketRateStatisEntry 2 }

ibDot11APTXPacketRateCount    OBJECT-TYPE
        SYNTAX        Counter64
        MAX-ACCESS    read-only
        STATUS        current
        DESCRIPTION
                "Represents the count of packets transmission base on transmit data rate."
    ::= { ibDot11APPacketRateStatisEntry 3 }

-- *****************************************************************************
-- *  End of ibDot11APPacketRateStatisTable Definition
-- *****************************************************************************

-- *****************************************************************************
-- *  ibDot11APPacketMCSRateStatisTable Definition
-- *****************************************************************************
ibDot11APPacketMCSRateStatisTable  OBJECT-TYPE
        SYNTAX        SEQUENCE OF IbDot11APPacketMCSRateStatisEntry
        MAX-ACCESS    not-accessible
        STATUS        current
        DESCRIPTION
                "This table provides packets statistic base on MCS rate."
        ::= { ibDot11APStatisGroup 21 }

ibDot11APPacketMCSRateStatisEntry  OBJECT-TYPE
        SYNTAX        IbDot11APPacketMCSRateStatisEntry
        MAX-ACCESS    not-accessible
        STATUS        current
        DESCRIPTION
                "Each entry provides packets statistic base on MCS rate for each radio
                 of a specific AP."
        INDEX
            {
                ibDot11CurAPID,
                ibDot11RadioID,
                ibDot11APPacketMCSRate
            }
        ::= { ibDot11APPacketMCSRateStatisTable 1 }

IbDot11APPacketMCSRateStatisEntry  ::=SEQUENCE
        {
            ibDot11APPacketMCSRate          Integer32,
            ibDot11APRXPacketMCSRateCount   Counter64,
            ibDot11APTXPacketMCSRateCount   Counter64
        }

ibDot11APPacketMCSRate    OBJECT-TYPE
        SYNTAX        Integer32
        MAX-ACCESS    not-accessible
        STATUS        current
        DESCRIPTION
            "Represents transmit data rate(twice as actual rate)."
    ::= { ibDot11APPacketMCSRateStatisEntry 1 }

ibDot11APRXPacketMCSRateCount    OBJECT-TYPE
        SYNTAX        Counter64
        MAX-ACCESS    read-only
        STATUS        current
        DESCRIPTION
            "Represents the count of packets reception base on transmit data rate."
    ::= { ibDot11APPacketMCSRateStatisEntry 2 }

ibDot11APTXPacketMCSRateCount    OBJECT-TYPE
        SYNTAX        Counter64
        MAX-ACCESS    read-only
        STATUS        current
        DESCRIPTION
            "Represents the count of packets transmission base on transmit
             data rate."
    ::= { ibDot11APPacketMCSRateStatisEntry 3 }

-- *****************************************************************************
-- *  End of ibDot11APPacketMcsRateStatisTable Definition
-- *****************************************************************************

-- *****************************************************************************
-- *  ibDot11APAssocFailStatis3Table Definition
-- *****************************************************************************
ibDot11APAssocFailStatis3Table OBJECT-TYPE
    SYNTAX      SEQUENCE OF IbDot11APAssocFailStatis3Entry
    MAX-ACCESS  not-accessible
    STATUS      current
    DESCRIPTION
        "This table will provide statistic of association fails for each AP."
    ::= { ibDot11APStatisGroup 22 }

ibDot11APAssocFailStatis3Entry OBJECT-TYPE
    SYNTAX      IbDot11APAssocFailStatis3Entry
    MAX-ACCESS  not-accessible
    STATUS      current
    DESCRIPTION
        "Each entry will provide statistic of association failure with this AP
         because of different reasons."
    INDEX
        {
            ibDot11CurAPID
       }
    ::= { ibDot11APAssocFailStatis3Table 1 }

IbDot11APAssocFailStatis3Entry ::= SEQUENCE
    {
        ibDot11APAssocFailStatis3SRCnt                 Counter32,
        ibDot11APAssocFailStatis3NSRCnt                Counter32,
        ibDot11APAssocFailStatis3URCCnt                Counter32,
        ibDot11APAssocFailStatis3RFCnt                 Counter32,
        ibDot11APAssocFailStatis3OtherCnt              Counter32,
        ibDot11APAssocFailStatis3RSSILowCntCM          Counter32
    }

ibDot11APAssocFailStatis3SRCnt OBJECT-TYPE
    SYNTAX      Counter32
    MAX-ACCESS  read-only
    STATUS      current
    DESCRIPTION
        "This object represents the count of association failure because of
         lack of resource."
    ::= { ibDot11APAssocFailStatis3Entry 1 }

ibDot11APAssocFailStatis3NSRCnt OBJECT-TYPE
    SYNTAX      Counter32
    MAX-ACCESS  read-only
    STATUS      current
    DESCRIPTION
        "This object represents the count of association failure because of
         not support rate set."
    ::= { ibDot11APAssocFailStatis3Entry 2 }

ibDot11APAssocFailStatis3URCCnt OBJECT-TYPE
    SYNTAX      Counter32
    MAX-ACCESS  read-only
    STATUS      current
    DESCRIPTION
        "This object represents the count of association failure because of
         unknown reason code."
    ::= { ibDot11APAssocFailStatis3Entry 3 }

ibDot11APAssocFailStatis3RFCnt OBJECT-TYPE
    SYNTAX      Counter32
    MAX-ACCESS  read-only
    STATUS      current
    DESCRIPTION
        "This object represents the count of association failure because of
         re-associate failed."
    ::= { ibDot11APAssocFailStatis3Entry 4 }

ibDot11APAssocFailStatis3OtherCnt OBJECT-TYPE
    SYNTAX      Counter32
    MAX-ACCESS  read-only
    STATUS      current
    DESCRIPTION
        "This object represents the count of association fails because of
         reason not in 802.11 the protocol."
    ::= { ibDot11APAssocFailStatis3Entry 5 }

ibDot11APAssocFailStatis3RSSILowCntCM OBJECT-TYPE
    SYNTAX      Counter32
    MAX-ACCESS  read-only
    STATUS      current
    DESCRIPTION
        "Represents the count of failed associations due to low RSSI."
    ::= { ibDot11APAssocFailStatis3Entry 6 }

-- *****************************************************************************
-- *  End of ibDot11APAssocFailStatis3Table Definition
-- *****************************************************************************

-- *****************************************************************************
-- *  ibDot11APIfStatisByAPIDTable Definition
-- *****************************************************************************
ibDot11APIfStatisByAPIDTable OBJECT-TYPE
    SYNTAX      SEQUENCE OF IbDot11APIfStatisByAPIDEntry
    MAX-ACCESS  not-accessible
    STATUS      current
    DESCRIPTION
        "The table will provide the statistics on the interface of the AP."
    ::= { ibDot11APStatisGroup 23 }

ibDot11APIfStatisByAPIDEntry OBJECT-TYPE
    SYNTAX      IbDot11APIfStatisByAPIDEntry
    MAX-ACCESS  not-accessible
    STATUS      current
    DESCRIPTION
        "Each entry of the table will provide statistics on the interface of the AP."
    INDEX
        {
            ibDot11CurAPID,
            ibDot11APIfIndex
        }
    ::= { ibDot11APIfStatisByAPIDTable 1 }

IbDot11APIfStatisByAPIDEntry ::= SEQUENCE
    {
        ibDot11APIfInPkts2              Counter64,
        ibDot11APIfInNormalPkts2        Counter64,
        ibDot11APIfInErrorPkts2         Counter64,
        ibDot11APIfOutPkts2             Counter64,
        ibDot11APIfInOctets2            Counter64,
        ibDot11APIfOutOctets2           Counter64,
        ibDot11APIfFlowOut2             Unsigned32,
        ibDot11APIfFlowIN2              Unsigned32,
        ibDot11APIfInUcastPkts2         Counter64,
        ibDot11APIfInNUcastPkts2        Counter64,
        ibDot11APIfInDiscardPkts2       Counter64,
        ibDot11APIfOutUcastPkts2        Counter64,
        ibDot11APIfOutNUcastPkts2       Counter64,
        ibDot11APIfOutDiscardPkts2      Counter64,
        ibDot11APIfOutErrorPkts2        Counter64,
        ibDot11APIfUpdownTimes2         Counter32,
        ibDot11APIfStatusKeepTime2      TimeTicks,
        ibDot11APIfOperStatus2          INTEGER,
        ibDot11APIfInBrdcastPkts2       Counter64,
        ibDot11APIfOutBrdcastPkts2      Counter64,
        ibDot11APIfInMulcastPkts2       Counter64,
        ibDot11APIfOutMulcastPkts2      Counter64,
        ibDot11APIfInPayloadOctets2     Counter64,
        ibDot11APIfOutPayloadOctets2    Counter64,
        ibDot11APIfInDataOctets2        Counter64,
        ibDot11APIfOutDataOctets2       Counter64,
        ibDot11APIfAdminStatus          INTEGER,
        ibDot11APIfOperStatusCM         INTEGER
    }

ibDot11APIfInPkts2 OBJECT-TYPE
    SYNTAX      Counter64
    MAX-ACCESS  read-only
    STATUS      current
    DESCRIPTION
        "Represents the total number of packets received
         on the interface."
    ::= { ibDot11APIfStatisByAPIDEntry 1 }

ibDot11APIfInNormalPkts2 OBJECT-TYPE
    SYNTAX      Counter64
    MAX-ACCESS  read-only
    STATUS      current
    DESCRIPTION
        "Represents the total number of correct
         packets received on the interface."
    ::= { ibDot11APIfStatisByAPIDEntry 2 }

ibDot11APIfInErrorPkts2 OBJECT-TYPE
    SYNTAX      Counter64
    MAX-ACCESS  read-only
    STATUS      current
    DESCRIPTION
        "Represents the total number of error
         packets received on the interface."
    ::= { ibDot11APIfStatisByAPIDEntry 3 }

ibDot11APIfOutPkts2 OBJECT-TYPE
    SYNTAX      Counter64
    MAX-ACCESS  read-only
    STATUS      current
    DESCRIPTION
        "Represents the total number of packets
         sent from the interface."
    ::= { ibDot11APIfStatisByAPIDEntry 4 }

ibDot11APIfInOctets2 OBJECT-TYPE
    SYNTAX      Counter64
    MAX-ACCESS  read-only
    STATUS      current
    DESCRIPTION
        "Represents the total number of octets
         received on the interface."
    ::= { ibDot11APIfStatisByAPIDEntry 5 }

ibDot11APIfOutOctets2 OBJECT-TYPE
    SYNTAX      Counter64
    MAX-ACCESS  read-only
    STATUS      current
    DESCRIPTION
        "Represents the total number of octets
         sent from the interface."
    ::= { ibDot11APIfStatisByAPIDEntry 6 }

ibDot11APIfFlowOut2 OBJECT-TYPE
    SYNTAX      Unsigned32
    MAX-ACCESS  read-only
    STATUS      current
    DESCRIPTION
        "Represents the traffic rate (byte/s) on the uplink interface
         during a sampling period."
    ::= { ibDot11APIfStatisByAPIDEntry 7 }

ibDot11APIfFlowIN2 OBJECT-TYPE
    SYNTAX      Unsigned32
    MAX-ACCESS  read-only
    STATUS      current
    DESCRIPTION
        "Represents the traffic rate (byte/s) on the downlink interface
         during a sampling period."
    ::= { ibDot11APIfStatisByAPIDEntry 8 }

ibDot11APIfInUcastPkts2 OBJECT-TYPE
    SYNTAX      Counter64
    MAX-ACCESS  read-only
    STATUS      current
    DESCRIPTION
        "Represents the number of unicast packets received on the interface."
    ::= { ibDot11APIfStatisByAPIDEntry 9 }

ibDot11APIfInNUcastPkts2 OBJECT-TYPE
    SYNTAX      Counter64
    MAX-ACCESS  read-only
    STATUS      current
    DESCRIPTION
        "Represents the number of non-unicast packets received on the wired
         interface."
    ::= { ibDot11APIfStatisByAPIDEntry 10 }

ibDot11APIfInDiscardPkts2 OBJECT-TYPE
    SYNTAX      Counter64
    MAX-ACCESS  read-only
    STATUS      current
    DESCRIPTION
        "Represents the number of unicast packets discarded on the interface."
    ::= { ibDot11APIfStatisByAPIDEntry 11 }

ibDot11APIfOutUcastPkts2 OBJECT-TYPE
    SYNTAX      Counter64
    MAX-ACCESS  read-only
    STATUS      current
    DESCRIPTION
        "Represents the number of unicast packets send on the interface."
    ::= { ibDot11APIfStatisByAPIDEntry 12 }

ibDot11APIfOutNUcastPkts2 OBJECT-TYPE
    SYNTAX      Counter64
    MAX-ACCESS  read-only
    STATUS      current
    DESCRIPTION
        "Represents the number of non-unicast packets send on the interface."
    ::= { ibDot11APIfStatisByAPIDEntry 13 }

ibDot11APIfOutDiscardPkts2 OBJECT-TYPE
    SYNTAX      Counter64
    MAX-ACCESS  read-only
    STATUS      current
    DESCRIPTION
        "Represents the number of discarded packets send on the interface."
    ::= { ibDot11APIfStatisByAPIDEntry 14 }

ibDot11APIfOutErrorPkts2 OBJECT-TYPE
    SYNTAX      Counter64
    MAX-ACCESS  read-only
    STATUS      current
    DESCRIPTION
        "Represents the number of error packets send on the interface."
    ::= { ibDot11APIfStatisByAPIDEntry 15 }

ibDot11APIfUpdownTimes2 OBJECT-TYPE
    SYNTAX      Counter32
    MAX-ACCESS  read-only
    STATUS      current
    DESCRIPTION
        "Represents the up/down times on the interface."
    ::= { ibDot11APIfStatisByAPIDEntry 16 }

ibDot11APIfStatusKeepTime2 OBJECT-TYPE
    SYNTAX      TimeTicks
    MAX-ACCESS  read-only
    STATUS      current
    DESCRIPTION
        "Represents the last change time on the interface."
    ::= { ibDot11APIfStatisByAPIDEntry 17 }

ibDot11APIfOperStatus2 OBJECT-TYPE
    SYNTAX  INTEGER {
                       up(1),        -- ready to pass packets
                       down(2),
                       testing(3),   -- in some test mode
                       unknown(4),   -- status can not be determined
                                     -- for some reason.
                       dormant(5),
                       notPresent(6),    -- some component is missing
                       lowerLayerDown(7) -- down due to state of
                                         -- lower-layer interface(s)
                    }
    MAX-ACCESS  read-only
    STATUS      current
    DESCRIPTION
        "Represents the operational state of the interface."
    ::= { ibDot11APIfStatisByAPIDEntry 18 }

ibDot11APIfInBrdcastPkts2 OBJECT-TYPE
    SYNTAX      Counter64
    MAX-ACCESS  read-only
    STATUS      current
    DESCRIPTION
        "Represents the number of broadcast packets received on the interface."
    ::= { ibDot11APIfStatisByAPIDEntry 19 }

ibDot11APIfOutBrdcastPkts2 OBJECT-TYPE
    SYNTAX      Counter64
    MAX-ACCESS  read-only
    STATUS      current
    DESCRIPTION
        "Represents the number of broadcast packets sent on the interface."
    ::= { ibDot11APIfStatisByAPIDEntry 20 }

ibDot11APIfInMulcastPkts2 OBJECT-TYPE
    SYNTAX      Counter64
    MAX-ACCESS  read-only
    STATUS      current
    DESCRIPTION
        "Represents the number of multicast packets received on the interface."
    ::= { ibDot11APIfStatisByAPIDEntry 21 }

ibDot11APIfOutMulcastPkts2 OBJECT-TYPE
    SYNTAX      Counter64
    MAX-ACCESS  read-only
    STATUS      current
    DESCRIPTION
        "Represents the number of multicast packets sent on the interface."
    ::= { ibDot11APIfStatisByAPIDEntry 22 }

ibDot11APIfInPayloadOctets2 OBJECT-TYPE
    SYNTAX      Counter64
    MAX-ACCESS  read-only
    STATUS      current
    DESCRIPTION
        "Represents the number of actual octets received on the interface."
    ::= { ibDot11APIfStatisByAPIDEntry 23 }

ibDot11APIfOutPayloadOctets2 OBJECT-TYPE
    SYNTAX      Counter64
    MAX-ACCESS  read-only
    STATUS      current
    DESCRIPTION
        "Represents the number of actual octets sent on the interface."
    ::= { ibDot11APIfStatisByAPIDEntry 24 }

ibDot11APIfInDataOctets2 OBJECT-TYPE
    SYNTAX      Counter64
    MAX-ACCESS  read-only
    STATUS      current
    DESCRIPTION
        "Represents the number of actual data octets received on the interface."
    ::= { ibDot11APIfStatisByAPIDEntry 25 }

ibDot11APIfOutDataOctets2 OBJECT-TYPE
    SYNTAX      Counter64
    MAX-ACCESS  read-only
    STATUS      current
    DESCRIPTION
        "Represents the number of actual data octets sent on the interface."
    ::= { ibDot11APIfStatisByAPIDEntry 26 }

ibDot11APIfAdminStatus OBJECT-TYPE
    SYNTAX  INTEGER {
                up(1),       -- ready to forward packets
                down(2),
                testing(3)   -- in a test mode
            }
    MAX-ACCESS  read-write
    STATUS      current
    DESCRIPTION
            "Expected state of the interface.  In testing state the
            interface does not forward any operational packets.  When
             a managed system is initialized, all interfaces start with
            ibDot11APIfAdminStatus in the down state.  As a result
            of either explicit management action or per configuration
            information retained by the managed system,
            ibDot11APIfAdminStatus is then changed to either the up
             or testing state or remains in the down state."
    ::= { ibDot11APIfStatisByAPIDEntry 27 }

ibDot11APIfOperStatusCM OBJECT-TYPE
    SYNTAX  INTEGER {
                       up(1),        -- ready to forward packets
                       down(2),
                       testing(3),   -- in a test mode
                       admindown(4)  -- shutdown by administrator
                    }
    MAX-ACCESS  read-only
    STATUS      current
    DESCRIPTION
        "Operational status of the interface."
    ::= { ibDot11APIfStatisByAPIDEntry 28 }

-- *****************************************************************************
-- *  End of ibDot11APIfStatisTable1 Definition
-- *****************************************************************************

-- *****************************************************************************
-- *  ibDot11APUserSecAuthStatisTable Definition
-- *****************************************************************************
ibDot11APUserSecAuthStatisTable OBJECT-TYPE
    SYNTAX      SEQUENCE OF IbDot11APUserSecAuthStatisEntry
    MAX-ACCESS  not-accessible
    STATUS      current
    DESCRIPTION
        "The table will provide the user authentication statistic for this AP."
    ::= { ibDot11APStatisGroup 24 }

ibDot11APUserSecAuthStatisEntry OBJECT-TYPE
    SYNTAX      IbDot11APUserSecAuthStatisEntry
    MAX-ACCESS  not-accessible
    STATUS      current
    DESCRIPTION
        "Each entry of the table will provide the user authentication statistic
        for this AP."
    INDEX
        {
            ibDot11CurAPID
       }
    ::= { ibDot11APUserSecAuthStatisTable 1 }

IbDot11APUserSecAuthStatisEntry ::= SEQUENCE
    {
        ibDot11APUserAuthCurNumber             Integer32,
        ibDot11APUserConnFailCnt               Counter32,
        ibDot11APUserAuthReqCnt                Counter32,
        ibDot11APUserAuthSuccCnt               Counter32,
        ibDot11APUserAuthFailCnt               Counter32,
        ibDot11AllUserOnlineTime               TimeTicks
    }

ibDot11APUserAuthCurNumber OBJECT-TYPE
    SYNTAX      Integer32
    MAX-ACCESS  read-only
    STATUS      current
    DESCRIPTION
        "Represents the current number of user authenticated with this AP."
    ::= { ibDot11APUserSecAuthStatisEntry 1 }

ibDot11APUserConnFailCnt OBJECT-TYPE
    SYNTAX      Counter32
    MAX-ACCESS  read-only
    STATUS      current
    DESCRIPTION
        "Represents the total number of user disconnected with this AP."
    ::= { ibDot11APUserSecAuthStatisEntry 2 }

ibDot11APUserAuthReqCnt OBJECT-TYPE
    SYNTAX      Counter32
    MAX-ACCESS  read-only
    STATUS      current
    DESCRIPTION
        "Represents the total number of user authentication request with this AP."
    ::= { ibDot11APUserSecAuthStatisEntry 3 }

ibDot11APUserAuthSuccCnt OBJECT-TYPE
    SYNTAX      Counter32
    MAX-ACCESS  read-only
    STATUS      current
    DESCRIPTION
        "Represents the total number of successful authenticated users with this AP."
    ::= { ibDot11APUserSecAuthStatisEntry 4 }

ibDot11APUserAuthFailCnt OBJECT-TYPE
    SYNTAX      Counter32
    MAX-ACCESS  read-only
    STATUS      current
    DESCRIPTION
        "Represents the total number of user authentication failures with this AP."
    ::= { ibDot11APUserSecAuthStatisEntry 5 }

ibDot11AllUserOnlineTime OBJECT-TYPE
    SYNTAX      TimeTicks
    MAX-ACCESS  read-only
    STATUS      current
    DESCRIPTION
        "Represents the online time of all successful authenticated users with this AP."
    ::= { ibDot11APUserSecAuthStatisEntry 6 }

-- *****************************************************************************
-- *  End of ibDot11APUserSecAuthStatisEntry Definition
-- *****************************************************************************

-- *****************************************************************************
-- *  ibDot11APUserInfoStatisTable Definition
-- *****************************************************************************
ibDot11APUserInfoStatisTable OBJECT-TYPE
    SYNTAX      SEQUENCE OF IbDot11APUserInfoStatisEntry
    MAX-ACCESS  not-accessible
    STATUS      current
    DESCRIPTION
        "The table will provide the user information statistic of this AP."
    ::= { ibDot11APStatisGroup 25 }

ibDot11APUserInfoStatisEntry OBJECT-TYPE
    SYNTAX      IbDot11APUserInfoStatisEntry
    MAX-ACCESS  not-accessible
    STATUS      current
    DESCRIPTION
        "Each entry of the table will provide the user information statistic
        of this AP."
    INDEX
        {
            ibDot11CurAPID,
            ibDot11APUserMacAddr
        }
    ::= { ibDot11APUserInfoStatisTable 1 }

IbDot11APUserInfoStatisEntry ::= SEQUENCE
    {
        ibDot11APUserMacAddr                  MacAddress,
        ibDot11APUserIpAddr                   IpAddress,
        ibDot11APUserLoginName                OCTET STRING,
        ibDot11APUserLoginTime                OCTET STRING,
        ibDot11APUserOnlineTime               TimeTicks,
        ibDot11APUserLoginNameCM              OCTET STRING,
        ibDot11APUserAuthTypeCM               INTEGER,
        ibDot11APUserTxPacketCntCM            Counter32,
        ibDot11APUserTxBytesCM                Counter64,
        ibDot11APUserRxPacketCntCM            Counter32,
        ibDot11APUserRxBytesCM                Counter64
    }

ibDot11APUserMacAddr OBJECT-TYPE
    SYNTAX      MacAddress
    MAX-ACCESS  not-accessible
    STATUS      current
    DESCRIPTION
        "Represents the mac address of user logging to this AP."
    ::= { ibDot11APUserInfoStatisEntry 1 }

ibDot11APUserIpAddr OBJECT-TYPE
    SYNTAX      IpAddress
    MAX-ACCESS  read-only
    STATUS      current
    DESCRIPTION
        "Represents the ip address of user logging to this AP."
    ::= { ibDot11APUserInfoStatisEntry 2 }

ibDot11APUserLoginName OBJECT-TYPE
    SYNTAX      OCTET STRING
    MAX-ACCESS  read-only
    STATUS      current
    DESCRIPTION
        "Represents the login name of user logging to this AP."
    ::= { ibDot11APUserInfoStatisEntry 3 }

ibDot11APUserLoginTime OBJECT-TYPE
    SYNTAX      OCTET STRING
    MAX-ACCESS  read-only
    STATUS      current
    DESCRIPTION
        "Represents the login time of user with this AP."
    ::= { ibDot11APUserInfoStatisEntry 4 }

ibDot11APUserOnlineTime OBJECT-TYPE
    SYNTAX      TimeTicks
    MAX-ACCESS  read-only
    STATUS      current
    DESCRIPTION
        "Represents the online time of user with this AP."
    ::= { ibDot11APUserInfoStatisEntry 5 }

ibDot11APUserLoginNameCM OBJECT-TYPE
    SYNTAX      OCTET STRING
    MAX-ACCESS  read-only
    STATUS      current
    DESCRIPTION
        "Represents the login name of user logging to this AP."
    ::= { ibDot11APUserInfoStatisEntry 6 }

ibDot11APUserAuthTypeCM OBJECT-TYPE
    SYNTAX      INTEGER
        {
            authFree(1),
            associateAuth(2),
            portalAuth(3),
            autoAuth(4)
        }
    MAX-ACCESS  read-only
    STATUS      current
    DESCRIPTION
        "Represents the authentication type of user with this AP.
        authFree       - There is no need others authentiaction, user will
        surf internet after association.
        associateAuth  - Include WEP PSK authentication.
        portalAuth     - The authentication lunched by portal pop-up program.
        autoAuth       - 802.1X authentication."
    ::= { ibDot11APUserInfoStatisEntry 7 }

ibDot11APUserTxPacketCntCM OBJECT-TYPE
    SYNTAX      Counter32
    MAX-ACCESS  read-only
    STATUS      current
    DESCRIPTION
        "Represents the total count of packets sent to online users."
    ::= { ibDot11APUserInfoStatisEntry 8 }

ibDot11APUserTxBytesCM OBJECT-TYPE
    SYNTAX      Counter64
    MAX-ACCESS  read-only
    STATUS      current
    DESCRIPTION
        "Represents the total bytes sent to online users."
    ::= { ibDot11APUserInfoStatisEntry 9 }

ibDot11APUserRxPacketCntCM OBJECT-TYPE
    SYNTAX      Counter32
    MAX-ACCESS  read-only
    STATUS      current
    DESCRIPTION
        "Represents the total count of packets received from online users."
    ::= { ibDot11APUserInfoStatisEntry 10 }

ibDot11APUserRxBytesCM OBJECT-TYPE
    SYNTAX      Counter64
    MAX-ACCESS  read-only
    STATUS      current
    DESCRIPTION
        "Represents the total bytes received from online users."
    ::= { ibDot11APUserInfoStatisEntry 11 }

-- *****************************************************************************
-- *  End of ibDot11APUserInfoStatisTable Definition
-- *****************************************************************************

-- *****************************************************************************
-- *  ibDot11APReassocStatis2Table Definition
-- *****************************************************************************
ibDot11APReassocStatis2Table OBJECT-TYPE
    SYNTAX      SEQUENCE OF IbDot11APReassocStatis2Entry
    MAX-ACCESS  not-accessible
    STATUS      current
    DESCRIPTION
        "This table will provide statistic of reassociation for each AP."
    ::= { ibDot11APStatisGroup 26 }

ibDot11APReassocStatis2Entry OBJECT-TYPE
    SYNTAX      IbDot11APReassocStatis2Entry
    MAX-ACCESS  not-accessible
    STATUS      current
    DESCRIPTION
        "Each entry will provide statistic of reassociation with this AP
         because of different reasons."
    INDEX
        {
            ibDot11CurAPID
        }
    ::= { ibDot11APReassocStatis2Table 1 }

IbDot11APReassocStatis2Entry ::= SEQUENCE
    {
        ibDot11APReassocFailStatis2Cnt                 Counter32
    }

ibDot11APReassocFailStatis2Cnt OBJECT-TYPE
    SYNTAX      Counter32
    MAX-ACCESS  read-only
    STATUS      current
    DESCRIPTION
        "This object represents the count of reassociation failure because of
         lack of resource."
    ::= { ibDot11APReassocStatis2Entry 1 }

-- *****************************************************************************
-- *  End of ibDot11APReassocStatis2Table Definition
-- *****************************************************************************

-- *****************************************************************************
-- *  ibDot11TrafficTable Definition
-- *****************************************************************************
ibDot11TrafficTable OBJECT-TYPE
    SYNTAX      SEQUENCE OF IbDot11TrafficEntry
    MAX-ACCESS  not-accessible
    STATUS      current
    DESCRIPTION
        "The table describes user's traffic based on ssid"
    ::= { ibDot11APStatisGroup 27 }

ibDot11TrafficEntry OBJECT-TYPE
    SYNTAX      IbDot11TrafficEntry
    MAX-ACCESS  not-accessible
    STATUS      current
    DESCRIPTION
        "Each entry contains the traffc information of a ssid."
    INDEX
        {
            ibDot11SSIDIndex
        }
    ::= { ibDot11TrafficTable 1 }

IbDot11TrafficEntry ::= SEQUENCE
    {
        ibDot11SSIDIndex             OCTET STRING,
        ibDot11UpPacketNumber        Counter64,
        ibDot11UpByteNumber          Counter64,
        ibDot11DownPacketNumber      Counter64,
        ibDot11DownByteNumber        Counter64
    }

ibDot11SSIDIndex OBJECT-TYPE
    SYNTAX      OCTET STRING
    MAX-ACCESS  not-accessible
    STATUS      current
    DESCRIPTION
        "Represents the SSID."
    ::= { ibDot11TrafficEntry 1 }

ibDot11UpPacketNumber OBJECT-TYPE
    SYNTAX      Counter64
    MAX-ACCESS  read-only
    STATUS      current
    DESCRIPTION
        "Represents the packet count of up link."
    ::= { ibDot11TrafficEntry 2 }

ibDot11UpByteNumber OBJECT-TYPE
    SYNTAX      Counter64
    MAX-ACCESS  read-only
    STATUS      current
    DESCRIPTION
        "Represents the byte count of up link."
    ::= { ibDot11TrafficEntry 3 }

ibDot11DownPacketNumber OBJECT-TYPE
    SYNTAX      Counter64
    MAX-ACCESS  read-only
    STATUS      current
    DESCRIPTION
        "Represents the packet count of down link."
    ::= { ibDot11TrafficEntry 4 }

ibDot11DownByteNumber OBJECT-TYPE
    SYNTAX      Counter64
    MAX-ACCESS  read-only
    STATUS      current
    DESCRIPTION
        "Represents the byte count of down link."
    ::= { ibDot11TrafficEntry 5 }

-- *****************************************************************************
-- *  End of ibDot11TrafficTable Definition
-- *****************************************************************************

-- *****************************************************************************
-- *  ibDot11APEchoStatisTable Definition
-- *****************************************************************************
ibDot11APEchoStatisTable OBJECT-TYPE
    SYNTAX      SEQUENCE OF IbDot11APEchoInfoStatisEntry
    MAX-ACCESS  not-accessible
    STATUS      current
    DESCRIPTION
        "The table will provide the Echo statistic of this AP."
    ::= { ibDot11APStatisGroup 28 }

ibDot11APEchoInfoStatisEntry OBJECT-TYPE
    SYNTAX      IbDot11APEchoInfoStatisEntry
    MAX-ACCESS  not-accessible
    STATUS      current
    DESCRIPTION
        "Each entry of the table will provide the Echo statistic
        of this AP."
    INDEX
        {
            ibDot11CurAPID
        }
    ::= { ibDot11APEchoStatisTable 1 }

IbDot11APEchoInfoStatisEntry ::= SEQUENCE
    {
        ibDot11APEchoAvgDelay                 Integer32,
        ibDot11APEchoRequestCnt               Counter64,
        ibDot11APEchoRespLossCnt              Counter64
    }

ibDot11APEchoAvgDelay OBJECT-TYPE
    SYNTAX      Integer32
    UNITS       "millisecond"
    MAX-ACCESS  read-only
    STATUS      current
    DESCRIPTION
        "This object represents the average time delay of heart beat in this AP."
    ::= { ibDot11APEchoInfoStatisEntry 1 }

ibDot11APEchoRequestCnt OBJECT-TYPE
    SYNTAX      Counter64
    MAX-ACCESS  read-only
    STATUS      current
    DESCRIPTION
        "This object represents the count of echo request in this AP."
    ::= { ibDot11APEchoInfoStatisEntry 2 }

ibDot11APEchoRespLossCnt OBJECT-TYPE
    SYNTAX      Counter64
    MAX-ACCESS  read-only
    STATUS      current
    DESCRIPTION
        "This object represents the loss count of echo response in this AP."
    ::= { ibDot11APEchoInfoStatisEntry 3 }

-- *****************************************************************************
-- *  End of ibDot11APEchoStatisTable Definition
-- *****************************************************************************

-- *****************************************************************************
-- *  ibDot11APUserSecAuthTypeStatisTable Definition
-- *****************************************************************************
ibDot11APUserSecAuthTypeStatisTable OBJECT-TYPE
    SYNTAX      SEQUENCE OF IbDot11APUserSecAuthTypeStatisEntry
    MAX-ACCESS  not-accessible
    STATUS      current
    DESCRIPTION
        "The table will provide the user authentication type statistic for this AP."
    ::= { ibDot11APStatisGroup 29 }

ibDot11APUserSecAuthTypeStatisEntry OBJECT-TYPE
    SYNTAX      IbDot11APUserSecAuthTypeStatisEntry
    MAX-ACCESS  not-accessible
    STATUS      current
    DESCRIPTION
        "Each entry of the table will provide the user authentication type statistic
        for this AP."
    INDEX
        {
            ibDot11CurAPID
        }
    ::= { ibDot11APUserSecAuthTypeStatisTable 1 }

IbDot11APUserSecAuthTypeStatisEntry ::= SEQUENCE
    {
        ibDot11APPortalOnlineUserNum          Integer32,
        ibDot11APAuthFreeOnlineUserNum        Integer32,
        ibDot11APAssocAuthOnlineUserNum       Integer32,
        ibDot11APMacAuthOnlineUserNum         Integer32,
        ibDot11APAllPortalUserOnlineTime      TimeTicks,
        ibDot11APAllAuthFreeUserOnlineTime    TimeTicks,
        ibDot11APAllAssocAuthUserOnlineTime   TimeTicks,
        ibDot11APAllMacAuthUserOnlineTime     TimeTicks,
        ibDot11APPortalUserLostCnntCnt        Counter32,
        ibDot11APAuthFreeUserLostCnntCnt      Counter32,
        ibDot11APAssocAuthUserLostCnntCnt     Counter32,
        ibDot11APMacAuthUserLostCnntCnt       Counter32,
        ibDot11APPortalAuthReqCnt             Counter32,
        ibDot11APAssocAuthReqCnt              Counter32,
        ibDot11APMacAuthReqCnt                Counter32,
        ibDot11APPortalAuthSucCnt             Counter32,
        ibDot11APAssocAuthSucCnt              Counter32,
        ibDot11APMacAuthSucCnt                Counter32,
        ibDot11APPortalAuthReqFailCnt         Counter32,
        ibDot11APAssocAuthReqFailCnt          Counter32,
        ibDot11APMacAuthReqFailCnt            Counter32,
        ibDot11APAutoAuthOnlineUserNumCM      Integer32,
        ibDot11APAllAutoAuthUserOnlineTimeCM  TimeTicks,
        ibDot11APAutoAuthUserLostCnntCntCM    Counter32,
        ibDot11APAutoAuthReqCntCM             Counter32,
        ibDot11APAutoAuthSucCntCM             Counter32,
        ibDot11APAutoAuthReqFailCntCM         Counter32
    }

ibDot11APPortalOnlineUserNum OBJECT-TYPE
    SYNTAX      Integer32
    MAX-ACCESS  read-only
    STATUS      current
    DESCRIPTION
        "Represents the number of online portal users of this AP, including
        MAC-trigger and IMSIAuth users."
    ::= { ibDot11APUserSecAuthTypeStatisEntry 1 }

ibDot11APAuthFreeOnlineUserNum OBJECT-TYPE
    SYNTAX      Integer32
    MAX-ACCESS  read-only
    STATUS      current
    DESCRIPTION
        "Represents the online number of user free authenticated with this AP."
    ::= { ibDot11APUserSecAuthTypeStatisEntry 2 }

ibDot11APAssocAuthOnlineUserNum OBJECT-TYPE
    SYNTAX      Integer32
    MAX-ACCESS  read-only
    STATUS      current
    DESCRIPTION
        "Represents the number of online users authenticated by associated
        authentication with this AP, excluding AutoAuth users."
    ::= { ibDot11APUserSecAuthTypeStatisEntry 3 }

ibDot11APMacAuthOnlineUserNum OBJECT-TYPE
    SYNTAX      Integer32
    MAX-ACCESS  read-only
    STATUS      current
    DESCRIPTION
        "Represents the online number of user MAC address authenticated with this AP."
    ::= { ibDot11APUserSecAuthTypeStatisEntry 4 }

ibDot11APAllPortalUserOnlineTime OBJECT-TYPE
    SYNTAX      TimeTicks
    MAX-ACCESS  read-only
    STATUS      current
    DESCRIPTION
        "Represents the online time of all user portal authenticated with this AP."
    ::= { ibDot11APUserSecAuthTypeStatisEntry 5 }

ibDot11APAllAuthFreeUserOnlineTime OBJECT-TYPE
    SYNTAX      TimeTicks
    MAX-ACCESS  read-only
    STATUS      current
    DESCRIPTION
        "Represents the online time of all user free authenticated with this AP."
    ::= { ibDot11APUserSecAuthTypeStatisEntry 6 }

ibDot11APAllAssocAuthUserOnlineTime OBJECT-TYPE
    SYNTAX      TimeTicks
    MAX-ACCESS  read-only
    STATUS      current
    DESCRIPTION
        "Represents the online time of all user associated authenticated with this AP."
    ::= { ibDot11APUserSecAuthTypeStatisEntry 7 }

ibDot11APAllMacAuthUserOnlineTime OBJECT-TYPE
    SYNTAX      TimeTicks
    MAX-ACCESS  read-only
    STATUS      current
    DESCRIPTION
        "Represents the online time of all user MAC address authenticated with this AP."
    ::= { ibDot11APUserSecAuthTypeStatisEntry 8 }

ibDot11APPortalUserLostCnntCnt OBJECT-TYPE
    SYNTAX      Counter32
    MAX-ACCESS  read-only
    STATUS      current
    DESCRIPTION
        "Represents the lost connective count of user portal authenticated with this AP."
    ::= { ibDot11APUserSecAuthTypeStatisEntry 9 }

ibDot11APAuthFreeUserLostCnntCnt OBJECT-TYPE
    SYNTAX      Counter32
    MAX-ACCESS  read-only
    STATUS      current
    DESCRIPTION
        "Represents the lost connective count of user free authenticated with this AP."
    ::= { ibDot11APUserSecAuthTypeStatisEntry 10 }

ibDot11APAssocAuthUserLostCnntCnt OBJECT-TYPE
    SYNTAX      Counter32
    MAX-ACCESS  read-only
    STATUS      current
    DESCRIPTION
        "Represents the lost connective count of user associate authenticated with this AP."
    ::= { ibDot11APUserSecAuthTypeStatisEntry 11 }

ibDot11APMacAuthUserLostCnntCnt OBJECT-TYPE
    SYNTAX      Counter32
    MAX-ACCESS  read-only
    STATUS      current
    DESCRIPTION
        "Represents the lost connective count of user MAC address authenticated with this AP."
    ::= { ibDot11APUserSecAuthTypeStatisEntry 12 }

ibDot11APPortalAuthReqCnt OBJECT-TYPE
    SYNTAX      Counter32
    MAX-ACCESS  read-only
    STATUS      current
    DESCRIPTION
        "Represents the request count of user portal authenticated with this AP."
    ::= { ibDot11APUserSecAuthTypeStatisEntry 13 }

ibDot11APAssocAuthReqCnt OBJECT-TYPE
    SYNTAX      Counter32
    MAX-ACCESS  read-only
    STATUS      current
    DESCRIPTION
        "Represents the request count of user associate authenticated with this AP."
    ::= { ibDot11APUserSecAuthTypeStatisEntry 14 }

ibDot11APMacAuthReqCnt OBJECT-TYPE
    SYNTAX      Counter32
    MAX-ACCESS  read-only
    STATUS      current
    DESCRIPTION
        "Represents the request count of user MAC address authenticated with this AP."
    ::= { ibDot11APUserSecAuthTypeStatisEntry 15 }

ibDot11APPortalAuthSucCnt OBJECT-TYPE
    SYNTAX      Counter32
    MAX-ACCESS  read-only
    STATUS      current
    DESCRIPTION
        "Represents the count of user portal authenticated successed with this AP."
    ::= { ibDot11APUserSecAuthTypeStatisEntry 16 }

ibDot11APAssocAuthSucCnt OBJECT-TYPE
    SYNTAX      Counter32
    MAX-ACCESS  read-only
    STATUS      current
    DESCRIPTION
        "Represents the count of user associate authenticated successed with this AP."
    ::= { ibDot11APUserSecAuthTypeStatisEntry 17 }

ibDot11APMacAuthSucCnt OBJECT-TYPE
    SYNTAX      Counter32
    MAX-ACCESS  read-only
    STATUS      current
    DESCRIPTION
        "Represents the count of user MAC address authenticated successed with this AP."
    ::= { ibDot11APUserSecAuthTypeStatisEntry 18 }

ibDot11APPortalAuthReqFailCnt OBJECT-TYPE
    SYNTAX      Counter32
    MAX-ACCESS  read-only
    STATUS      current
    DESCRIPTION
        "Represents the count of user portal authenticated failed with this AP."
    ::= { ibDot11APUserSecAuthTypeStatisEntry 19 }

ibDot11APAssocAuthReqFailCnt OBJECT-TYPE
    SYNTAX      Counter32
    MAX-ACCESS  read-only
    STATUS      current
    DESCRIPTION
        "Represents the count of user associate authenticated failed with this AP."
    ::= { ibDot11APUserSecAuthTypeStatisEntry 20 }

ibDot11APMacAuthReqFailCnt OBJECT-TYPE
    SYNTAX      Counter32
    MAX-ACCESS  read-only
    STATUS      current
    DESCRIPTION
        "Represents the count of user MAC address authenticated failed with this AP."
    ::= { ibDot11APUserSecAuthTypeStatisEntry 21 }

ibDot11APAutoAuthOnlineUserNumCM OBJECT-TYPE
    SYNTAX      Integer32
    MAX-ACCESS  read-only
    STATUS      current
    DESCRIPTION
        "Represents the number of online users authenticated by auto authentication
        with this AP."
    ::= { ibDot11APUserSecAuthTypeStatisEntry 22 }

ibDot11APAllAutoAuthUserOnlineTimeCM OBJECT-TYPE
    SYNTAX      TimeTicks
    MAX-ACCESS  read-only
    STATUS      current
    DESCRIPTION
        "Represents the online time of users authenticated by auto authentication
        with this AP."
    ::= { ibDot11APUserSecAuthTypeStatisEntry 23 }

ibDot11APAutoAuthUserLostCnntCntCM OBJECT-TYPE
    SYNTAX      Counter32
    MAX-ACCESS  read-only
    STATUS      current
    DESCRIPTION
        "Represents the disconnection count of AutoAuth users."
    ::= { ibDot11APUserSecAuthTypeStatisEntry 24 }

ibDot11APAutoAuthReqCntCM OBJECT-TYPE
    SYNTAX      Counter32
    MAX-ACCESS  read-only
    STATUS      current
    DESCRIPTION
        "Represents the count of AutoAuth requests with this AP."
    ::= { ibDot11APUserSecAuthTypeStatisEntry 25 }

ibDot11APAutoAuthSucCntCM OBJECT-TYPE
    SYNTAX      Counter32
    MAX-ACCESS  read-only
    STATUS      current
    DESCRIPTION
        "Represents the count of successful AutoAuth authentications with this AP."
    ::= { ibDot11APUserSecAuthTypeStatisEntry 26 }

ibDot11APAutoAuthReqFailCntCM OBJECT-TYPE
    SYNTAX      Counter32
    MAX-ACCESS  read-only
    STATUS      current
    DESCRIPTION
        "Represents the count of failed AutoAuth requests with this AP."
    ::= { ibDot11APUserSecAuthTypeStatisEntry 27 }

-- *****************************************************************************
-- *  End of ibDot11APUserSecAuthTypeStatisTable Definition
-- *****************************************************************************

-- *****************************************************************************
-- *  ibDot11RadioRxStatis64Table Definition
-- *****************************************************************************
ibDot11RadioRxStatis64Table OBJECT-TYPE
    SYNTAX      SEQUENCE OF IbDot11RadioRxStatis64Entry
    MAX-ACCESS  not-accessible
    STATUS      current
    DESCRIPTION
        "The table will provide the reception statistic for a specific
        radio of AP."
    ::= { ibDot11APStatisGroup 30 }

ibDot11RadioRxStatis64Entry OBJECT-TYPE
    SYNTAX      IbDot11RadioRxStatis64Entry
    MAX-ACCESS  not-accessible
    STATUS      current
    DESCRIPTION
        "Each entry of the table will provide the reception statistic
        data for each radio of a specific AP."
    INDEX
        {
            ibDot11CurAPID,
            ibDot11RadioID
        }
    ::= { ibDot11RadioRxStatis64Table 1 }

IbDot11RadioRxStatis64Entry ::= SEQUENCE
    {
        ibDot11Rx64FrameDupCnt          Counter64,
        ibDot11Rx64FrameCnt             Counter64,
        ibDot11Rx64UcastFrameCnt        Counter64,
        ibDot11Rx64BcastFrameCnt        Counter64,
        ibDot11Rx64McastFrameCnt        Counter64,
        ibDot11Rx64DiscardFrameCnt      Counter64,
        ibDot11Rx64FragCnt              Counter64,
        ibDot11Rx64FcsErrCnt            Counter64,
        ibDot11Rx64FrameBytes           Counter64,
        ibDot11Rx64UcastFrameBytes      Counter64,
        ibDot11Rx64BcastFrameBytes      Counter64,
        ibDot11Rx64McastFrameBytes      Counter64,
        ibDot11Rx64DiscardFrameBytes    Counter64,
        ibDot11Rx64MgmtFrameCnt         Counter64,
        ibDot11Rx64CtrlFrameCnt         Counter64,
        ibDot11Rx64DataFrameCnt         Counter64,
        ibDot11Rx64DecryptErrorCnt      Counter64,
        ibDot11Rx64AuthenFrameCnt       Counter64,
        ibDot11Rx64AssociateFrameCnt    Counter64,
        ibDot11Rx64PhyErrorCnt          Counter64,
        ibDot11Rx64MICErrorCnt          Counter64,
        ibDot11Rx64DataFrameBytes       Counter64,
        ibDot11Rx64PayloadBytes         Counter64,
        ibDot11Rx64DataFrameBytesCM     Counter64
    }

ibDot11Rx64FrameDupCnt OBJECT-TYPE
    SYNTAX      Counter64
    MAX-ACCESS  read-only
    STATUS      current
    DESCRIPTION
        "Represents the number of duplicate frames reception."
    ::= { ibDot11RadioRxStatis64Entry 1 }

ibDot11Rx64FrameCnt OBJECT-TYPE
    SYNTAX      Counter64
    MAX-ACCESS  read-only
    STATUS      current
    DESCRIPTION
        "Represents the number of frames reception."
    ::= { ibDot11RadioRxStatis64Entry 2 }

ibDot11Rx64UcastFrameCnt OBJECT-TYPE
    SYNTAX      Counter64
    MAX-ACCESS  read-only
    STATUS      current
    DESCRIPTION
        "Represents the number of unicast frames reception."
    ::= { ibDot11RadioRxStatis64Entry 3 }

ibDot11Rx64BcastFrameCnt OBJECT-TYPE
    SYNTAX      Counter64
    MAX-ACCESS  read-only
    STATUS      current
    DESCRIPTION
        "Represents the number of broadcast frames reception."
    ::= { ibDot11RadioRxStatis64Entry 4 }

ibDot11Rx64McastFrameCnt OBJECT-TYPE
    SYNTAX      Counter64
    MAX-ACCESS  read-only
    STATUS      current
    DESCRIPTION
        "Represents the number of multicast frames reception."
    ::= { ibDot11RadioRxStatis64Entry 5 }

ibDot11Rx64DiscardFrameCnt OBJECT-TYPE
    SYNTAX      Counter64
    MAX-ACCESS  read-only
    STATUS      current
    DESCRIPTION
        "Represents the number of discarded frames reception."
    ::= { ibDot11RadioRxStatis64Entry 6 }

ibDot11Rx64FragCnt OBJECT-TYPE
    SYNTAX      Counter64
    MAX-ACCESS  read-only
    STATUS      current
    DESCRIPTION
        "Represents the number of frame fragments reception."
    ::= { ibDot11RadioRxStatis64Entry 7 }

ibDot11Rx64FcsErrCnt OBJECT-TYPE
    SYNTAX      Counter64
    MAX-ACCESS  read-only
    STATUS      current
    DESCRIPTION
        "Represents the number of FCS error frames reception."
    ::= { ibDot11RadioRxStatis64Entry 8 }

ibDot11Rx64FrameBytes OBJECT-TYPE
    SYNTAX      Counter64
    MAX-ACCESS  read-only
    STATUS      current
    DESCRIPTION
        "Represents the bytes of frames reception."
    ::= { ibDot11RadioRxStatis64Entry 9 }

ibDot11Rx64UcastFrameBytes OBJECT-TYPE
    SYNTAX      Counter64
    MAX-ACCESS  read-only
    STATUS      current
    DESCRIPTION
        "Represents the bytes of unicast frames reception."
    ::= { ibDot11RadioRxStatis64Entry 10 }

ibDot11Rx64BcastFrameBytes OBJECT-TYPE
    SYNTAX      Counter64
    MAX-ACCESS  read-only
    STATUS      current
    DESCRIPTION
        "Represents the bytes of broadcast frames reception."
    ::= { ibDot11RadioRxStatis64Entry 11 }

ibDot11Rx64McastFrameBytes OBJECT-TYPE
    SYNTAX      Counter64
    MAX-ACCESS  read-only
    STATUS      current
    DESCRIPTION
        "Represents the bytes of multicast frames reception."
    ::= { ibDot11RadioRxStatis64Entry 12 }

ibDot11Rx64DiscardFrameBytes OBJECT-TYPE
    SYNTAX      Counter64
    MAX-ACCESS  read-only
    STATUS      current
    DESCRIPTION
        "Represents the bytes of discarded frames reception."
    ::= { ibDot11RadioRxStatis64Entry 13 }

ibDot11Rx64MgmtFrameCnt OBJECT-TYPE
    SYNTAX      Counter64
    MAX-ACCESS  read-only
    STATUS      current
    DESCRIPTION
        "Represents the number of management frames reception."
    ::= { ibDot11RadioRxStatis64Entry 14 }

ibDot11Rx64CtrlFrameCnt OBJECT-TYPE
    SYNTAX      Counter64
    MAX-ACCESS  read-only
    STATUS      current
    DESCRIPTION
        "Represents the number of control frames reception."
    ::= { ibDot11RadioRxStatis64Entry 15 }

ibDot11Rx64DataFrameCnt OBJECT-TYPE
    SYNTAX      Counter64
    MAX-ACCESS  read-only
    STATUS      current
    DESCRIPTION
        "Represents the number of data frames reception."
    ::= { ibDot11RadioRxStatis64Entry 16 }

ibDot11Rx64DecryptErrorCnt OBJECT-TYPE
    SYNTAX      Counter64
    MAX-ACCESS  read-only
    STATUS      current
    DESCRIPTION
        "Represents the number of decryption error reception."
    ::= { ibDot11RadioRxStatis64Entry 17 }

ibDot11Rx64AuthenFrameCnt OBJECT-TYPE
    SYNTAX      Counter64
    MAX-ACCESS  read-only
    STATUS      current
    DESCRIPTION
        "Represents the number of authentication frame reception."
    ::= { ibDot11RadioRxStatis64Entry 18 }

ibDot11Rx64AssociateFrameCnt OBJECT-TYPE
    SYNTAX      Counter64
    MAX-ACCESS  read-only
    STATUS      current
    DESCRIPTION
        "Represents the number of associate frame reception."
    ::= { ibDot11RadioRxStatis64Entry 19 }

ibDot11Rx64PhyErrorCnt OBJECT-TYPE
    SYNTAX      Counter64
    MAX-ACCESS  read-only
    STATUS      current
    DESCRIPTION
        "Represents the number of physical error reception."
    ::= { ibDot11RadioRxStatis64Entry 20 }

ibDot11Rx64MICErrorCnt OBJECT-TYPE
    SYNTAX      Counter64
    MAX-ACCESS  read-only
    STATUS      current
    DESCRIPTION
        "Represents the number of MIC verification error reception."
    ::= { ibDot11RadioRxStatis64Entry 21 }

ibDot11Rx64DataFrameBytes OBJECT-TYPE
    SYNTAX      Counter64
    MAX-ACCESS  read-only
    STATUS      current
    DESCRIPTION
        "Represents the bytes of data frames reception."
    ::= { ibDot11RadioRxStatis64Entry 22 }

ibDot11Rx64PayloadBytes OBJECT-TYPE
    SYNTAX      Counter64
    MAX-ACCESS  read-only
    STATUS      current
    DESCRIPTION
        "Represents the payload bytes of data frames reception."
    ::= { ibDot11RadioRxStatis64Entry 23 }

ibDot11Rx64DataFrameBytesCM OBJECT-TYPE
    SYNTAX      Counter64
    MAX-ACCESS  read-only
    STATUS      current
    DESCRIPTION
        "Represents the number of received data frames, excluding retransmitted
        frames."
    ::= { ibDot11RadioRxStatis64Entry 24 }

-- *****************************************************************************
-- *  End of ibDot11RadioRxStatis64Table Definition
-- *****************************************************************************

-- *****************************************************************************
-- *  ibDot11RadioTxStatis64Table Definition
-- *****************************************************************************
ibDot11RadioTxStatis64Table OBJECT-TYPE
    SYNTAX      SEQUENCE OF IbDot11RadioTxStatis64Entry
    MAX-ACCESS  not-accessible
    STATUS      current
    DESCRIPTION
        "The table will provide the transmission statistic for a
        specific radio of AP."
    ::= { ibDot11APStatisGroup 31 }

ibDot11RadioTxStatis64Entry OBJECT-TYPE
    SYNTAX      IbDot11RadioTxStatis64Entry
    MAX-ACCESS  not-accessible
    STATUS      current
    DESCRIPTION
        "Each entry of the table will provide the transmission
        statistic data for each radio of a specific AP."
    INDEX
        {
            ibDot11CurAPID,
            ibDot11RadioID
        }
    ::= { ibDot11RadioTxStatis64Table 1 }

IbDot11RadioTxStatis64Entry ::= SEQUENCE
    {
        ibDot11Tx64FragCnt              Counter64,
        ibDot11Tx64FailedCnt            Counter64,
        ibDot11Tx64RetryCnt             Counter64,
        ibDot11Tx64MultiRetryCnt        Counter64,
        ibDot11Tx64RtsSuccessCnt        Counter64,
        ibDot11Tx64RtsFailCnt           Counter64,
        ibDot11Tx64AckFailCnt           Counter64,
        ibDot11Tx64FrameCnt             Counter64,
        ibDot11Tx64UcastFrameCnt        Counter64,
        ibDot11Tx64BcastFrameCnt        Counter64,
        ibDot11Tx64McastFrameCnt        Counter64,
        ibDot11Tx64DiscardFrameCnt      Counter64,
        ibDot11Tx64FrameBytes           Counter64,
        ibDot11Tx64UcastFrameBytes      Counter64,
        ibDot11Tx64BcastFrameBytes      Counter64,
        ibDot11Tx64McastFrameBytes      Counter64,
        ibDot11Tx64DiscardFrameBytes    Counter64,
        ibDot11Tx64AuthenFrameCnt       Counter64,
        ibDot11Tx64AssociateFrameCnt    Counter64,
        ibDot11Tx64DataFrameCnt         Counter64,
        ibDot11Tx64DataFrameBytes       Counter64,
        ibDot11Tx64MSDUCnt              Counter64,
        ibDot11Tx64DiscardMSDUCnt       Counter64,
        ibDot11Tx64RetryMSDUCnt         Counter64,
        ibDot11Tx64PayloadBytes         Counter64,
        ibDot11Tx64MgtFrameCnt          Counter64,
        ibDot11Tx64CtrlFrameCnt         Counter64,
        ibDot11Tx64MACErrCnt            Counter64,
        ibDot11Tx64ErrFrameCnt          Counter64
    }

ibDot11Tx64FragCnt OBJECT-TYPE
    SYNTAX      Counter64
    MAX-ACCESS  read-only
    STATUS      current
    DESCRIPTION
        "Represents the number of fragmented frames transmission."
    ::= { ibDot11RadioTxStatis64Entry 1 }

ibDot11Tx64FailedCnt OBJECT-TYPE
    SYNTAX      Counter64
    MAX-ACCESS  read-only
    STATUS      current
    DESCRIPTION
        "Represents the number of failures transmission."
    ::= { ibDot11RadioTxStatis64Entry 2 }

ibDot11Tx64RetryCnt OBJECT-TYPE
    SYNTAX      Counter64
    MAX-ACCESS  read-only
    STATUS      current
    DESCRIPTION
        "Represents the number of retries transmission."
    ::= { ibDot11RadioTxStatis64Entry 3 }

ibDot11Tx64MultiRetryCnt OBJECT-TYPE
    SYNTAX      Counter64
    MAX-ACCESS  read-only
    STATUS      current
    DESCRIPTION
        "Represents the number of transmits that required more than
        one retry transmission."
    ::= { ibDot11RadioTxStatis64Entry 4 }

ibDot11Tx64RtsSuccessCnt OBJECT-TYPE
    SYNTAX      Counter64
    MAX-ACCESS  read-only
    STATUS      current
    DESCRIPTION
        "Represents the number of successful RTS (Request to send)
        transmission."
    ::= { ibDot11RadioTxStatis64Entry 5 }

ibDot11Tx64RtsFailCnt OBJECT-TYPE
    SYNTAX      Counter64
    MAX-ACCESS  read-only
    STATUS      current
    DESCRIPTION
        "Represents the number of RTS failures transmission."
    ::= { ibDot11RadioTxStatis64Entry 6 }

ibDot11Tx64AckFailCnt OBJECT-TYPE
    SYNTAX      Counter64
    MAX-ACCESS  read-only
    STATUS      current
    DESCRIPTION
        "Represents the number of acknowledgement failures transmission."
    ::= { ibDot11RadioTxStatis64Entry 7 }

ibDot11Tx64FrameCnt OBJECT-TYPE
    SYNTAX      Counter64
    MAX-ACCESS  read-only
    STATUS      current
    DESCRIPTION
        "Represents the total number of frames transmission."
    ::= { ibDot11RadioTxStatis64Entry 8 }

ibDot11Tx64UcastFrameCnt OBJECT-TYPE
    SYNTAX      Counter64
    MAX-ACCESS  read-only
    STATUS      current
    DESCRIPTION
        "Represents the number of unicast frames transmission."
    ::= { ibDot11RadioTxStatis64Entry 9 }

ibDot11Tx64BcastFrameCnt OBJECT-TYPE
    SYNTAX      Counter64
    MAX-ACCESS  read-only
    STATUS      current
    DESCRIPTION
        "Represents the number of broadcast frames transmission."
    ::= { ibDot11RadioTxStatis64Entry 10 }

ibDot11Tx64McastFrameCnt OBJECT-TYPE
    SYNTAX      Counter64
    MAX-ACCESS  read-only
    STATUS      current
    DESCRIPTION
        "Represents the number of multicast frames transmission."
    ::= { ibDot11RadioTxStatis64Entry 11 }

ibDot11Tx64DiscardFrameCnt OBJECT-TYPE
    SYNTAX      Counter64
    MAX-ACCESS  read-only
    STATUS      current
    DESCRIPTION
        "Represents the number of discarded frames transmission."
    ::= { ibDot11RadioTxStatis64Entry 12 }

ibDot11Tx64FrameBytes OBJECT-TYPE
    SYNTAX      Counter64
    MAX-ACCESS  read-only
    STATUS      current
    DESCRIPTION
        "Represents the total bytes of frames transmission."
    ::= { ibDot11RadioTxStatis64Entry 13 }

ibDot11Tx64UcastFrameBytes OBJECT-TYPE
    SYNTAX      Counter64
    MAX-ACCESS  read-only
    STATUS      current
    DESCRIPTION
        "Represents the bytes of unicast frames transmission."
    ::= { ibDot11RadioTxStatis64Entry 14 }

ibDot11Tx64BcastFrameBytes OBJECT-TYPE
    SYNTAX      Counter64
    MAX-ACCESS  read-only
    STATUS      current
    DESCRIPTION
        "Represents the bytes of broadcast frames transmission."
    ::= { ibDot11RadioTxStatis64Entry 15 }

ibDot11Tx64McastFrameBytes OBJECT-TYPE
    SYNTAX      Counter64
    MAX-ACCESS  read-only
    STATUS      current
    DESCRIPTION
        "Represents the bytes of multicast frames transmission."
    ::= { ibDot11RadioTxStatis64Entry 16 }

ibDot11Tx64DiscardFrameBytes OBJECT-TYPE
    SYNTAX      Counter64
    MAX-ACCESS  read-only
    STATUS      current
    DESCRIPTION
        "Represents the bytes of discarded frames transmission."
    ::= { ibDot11RadioTxStatis64Entry 17 }

ibDot11Tx64AuthenFrameCnt OBJECT-TYPE
    SYNTAX      Counter64
    MAX-ACCESS  read-only
    STATUS      current
    DESCRIPTION
        "Represents the number of authentication frame transmission."
    ::= { ibDot11RadioTxStatis64Entry 18 }

ibDot11Tx64AssociateFrameCnt OBJECT-TYPE
    SYNTAX      Counter64
    MAX-ACCESS  read-only
    STATUS      current
    DESCRIPTION
        "Represents the number of associate frame transmission."
    ::= { ibDot11RadioTxStatis64Entry 19 }

ibDot11Tx64DataFrameCnt OBJECT-TYPE
    SYNTAX      Counter64
    MAX-ACCESS  read-only
    STATUS      current
    DESCRIPTION
        "Represents the number of data frame transmission."
    ::= { ibDot11RadioTxStatis64Entry 20 }

ibDot11Tx64DataFrameBytes OBJECT-TYPE
    SYNTAX      Counter64
    MAX-ACCESS  read-only
    STATUS      current
    DESCRIPTION
        "Represents the bytes of data frame transmission."
    ::= { ibDot11RadioTxStatis64Entry 21 }

ibDot11Tx64MSDUCnt OBJECT-TYPE
    SYNTAX      Counter64
    MAX-ACCESS  read-only
    STATUS      current
    DESCRIPTION
        "Represents the total number of MSDU transmission."
    ::= { ibDot11RadioTxStatis64Entry 22 }

ibDot11Tx64DiscardMSDUCnt OBJECT-TYPE
    SYNTAX      Counter64
    MAX-ACCESS  read-only
    STATUS      current
    DESCRIPTION
        "Represents the number of discarded MSDU transmission."
    ::= { ibDot11RadioTxStatis64Entry 23 }

ibDot11Tx64RetryMSDUCnt OBJECT-TYPE
    SYNTAX      Counter64
    MAX-ACCESS  read-only
    STATUS      current
    DESCRIPTION
        "Represents the number of retransfer MSDU transmission."
    ::= { ibDot11RadioTxStatis64Entry 24 }

ibDot11Tx64PayloadBytes OBJECT-TYPE
    SYNTAX      Counter64
    MAX-ACCESS  read-only
    STATUS      current
    DESCRIPTION
        "Represents the payload bytes of data frames transmission."
    ::= { ibDot11RadioTxStatis64Entry 25 }

ibDot11Tx64MgtFrameCnt OBJECT-TYPE
    SYNTAX      Counter64
    MAX-ACCESS  read-only
    STATUS      current
    DESCRIPTION
        "Represents the number of management frames transmission."
    ::= { ibDot11RadioTxStatis64Entry 26 }

ibDot11Tx64CtrlFrameCnt OBJECT-TYPE
    SYNTAX      Counter64
    MAX-ACCESS  read-only
    STATUS      current
    DESCRIPTION
        "Represents the number of control frames transmission."
    ::= { ibDot11RadioTxStatis64Entry 27 }
ibDot11Tx64MACErrCnt OBJECT-TYPE
    SYNTAX      Counter64
    MAX-ACCESS  read-only
    STATUS      current
    DESCRIPTION
        "Represents the number of MAC error frame transmission."
    ::= { ibDot11RadioTxStatis64Entry 28 }

ibDot11Tx64ErrFrameCnt OBJECT-TYPE
    SYNTAX      Counter64
    MAX-ACCESS  read-only
    STATUS      current
    DESCRIPTION
        "Represents the number of error frame transmission."
    ::= { ibDot11RadioTxStatis64Entry 29 }

-- *****************************************************************************
-- *  End of ibDot11RadioTxStatis64Table Definition
-- *****************************************************************************

-- *****************************************************************************
-- *  ibDot11BSSRxStatis64Table Definition
-- *****************************************************************************
ibDot11BSSRxStatis64Table OBJECT-TYPE
    SYNTAX      SEQUENCE OF IbDot11BSSRxStatis64Entry
    MAX-ACCESS  not-accessible
    STATUS      current
    DESCRIPTION
        "The table will provide the reception statistic for a
        specific BSS on a radio."
    ::= { ibDot11APStatisGroup 32 }

ibDot11BSSRxStatis64Entry OBJECT-TYPE
    SYNTAX      IbDot11BSSRxStatis64Entry
    MAX-ACCESS  not-accessible
    STATUS      current
    DESCRIPTION
        "Each entry of the table will provide the reception statistic data for
        each BSS on a specific radio."
    INDEX
        {
            ibDot11CurAPID,
            ibDot11RadioID,
            ibDot11WlanID
        }
    ::= { ibDot11BSSRxStatis64Table 1 }

IbDot11BSSRxStatis64Entry ::= SEQUENCE
    {
        ibDot11BSSRx64FrameCnt             Counter64,
        ibDot11BSSRx64FrameBytes           Counter64,
        ibDot11BSSRx64DataFrameCnt         Counter64,
        ibDot11BSSRx64DataFrameBytes       Counter64,
        ibDot11BSSRx64AssocFrameCnt        Counter64,
        ibDot11BSSRx64PayloadBytes         Counter64,
        ibDot11BSSRx64UniFrameCnt          Counter64,
        ibDot11BSSRx64NonUniFrameCnt       Counter64,
        ibDot11BSSRx64AuthenFrameCnt       Counter64
    }

ibDot11BSSRx64FrameCnt OBJECT-TYPE
    SYNTAX      Counter64
    MAX-ACCESS  read-only
    STATUS      current
    DESCRIPTION
        "Represents the number of frames reception with this BSS."
    ::= { ibDot11BSSRxStatis64Entry 1 }

ibDot11BSSRx64FrameBytes OBJECT-TYPE
    SYNTAX      Counter64
    MAX-ACCESS  read-only
    STATUS      current
    DESCRIPTION
        "Represents the bytes of frames reception with this BSS."
    ::= { ibDot11BSSRxStatis64Entry 2 }

ibDot11BSSRx64DataFrameCnt OBJECT-TYPE
    SYNTAX      Counter64
    MAX-ACCESS  read-only
    STATUS      current
    DESCRIPTION
        "Represents the number of data frames reception with this BSS."
    ::= { ibDot11BSSRxStatis64Entry 3 }

ibDot11BSSRx64DataFrameBytes OBJECT-TYPE
    SYNTAX      Counter64
    MAX-ACCESS  read-only
    STATUS      current
    DESCRIPTION
        "Represents the bytes of data frames reception with this BSS."
    ::= { ibDot11BSSRxStatis64Entry 4 }

ibDot11BSSRx64AssocFrameCnt OBJECT-TYPE
    SYNTAX      Counter64
    MAX-ACCESS  read-only
    STATUS      current
    DESCRIPTION
        "Represents the number of associate frames reception with this BSS."
    ::= { ibDot11BSSRxStatis64Entry 5 }

ibDot11BSSRx64PayloadBytes OBJECT-TYPE
    SYNTAX      Counter64
    MAX-ACCESS  read-only
    STATUS      current
    DESCRIPTION
        "Represents the payload bytes of data frames reception with this BSS."
    ::= { ibDot11BSSRxStatis64Entry 6 }

ibDot11BSSRx64UniFrameCnt OBJECT-TYPE
    SYNTAX      Counter64
    MAX-ACCESS  read-only
    STATUS      current
    DESCRIPTION
        "Represents the number of unicast frames reception with this BSS."
    ::= { ibDot11BSSRxStatis64Entry 7 }

ibDot11BSSRx64NonUniFrameCnt  OBJECT-TYPE
    SYNTAX      Counter64
    MAX-ACCESS  read-only
    STATUS      current
    DESCRIPTION
        "Represents the number of non-unicast frames reception with this BSS."
    ::= { ibDot11BSSRxStatis64Entry 8 }

ibDot11BSSRx64AuthenFrameCnt OBJECT-TYPE
    SYNTAX      Counter64
    MAX-ACCESS  read-only
    STATUS      current
    DESCRIPTION
        "Represents the number of authentication frames reception with this BSS."
    ::= { ibDot11BSSRxStatis64Entry 9 }

-- *****************************************************************************
-- *  End of ibDot11BSSRxStatis64Table Definition
-- *****************************************************************************

-- *****************************************************************************
-- *  ibDot11BSSTxStatis64Table Definition
-- *****************************************************************************
ibDot11BSSTxStatis64Table OBJECT-TYPE
    SYNTAX      SEQUENCE OF IbDot11BSSTxStatis64Entry
    MAX-ACCESS  not-accessible
    STATUS      current
    DESCRIPTION
        "The table will provide the transmission statistic for a
        specific BSS on a radio."
    ::= { ibDot11APStatisGroup 33 }

ibDot11BSSTxStatis64Entry OBJECT-TYPE
    SYNTAX      IbDot11BSSTxStatis64Entry
    MAX-ACCESS  not-accessible
    STATUS      current
    DESCRIPTION
        "Each entry of the table will provide the transmission statistic data for
        each BSS on a specific radio."
    INDEX
        {
            ibDot11CurAPID,
            ibDot11RadioID,
            ibDot11WlanID
        }
    ::= { ibDot11BSSTxStatis64Table 1 }

IbDot11BSSTxStatis64Entry ::= SEQUENCE
    {
        ibDot11BSSTx64FrameCnt             Counter64,
        ibDot11BSSTx64FrameBytes           Counter64,
        ibDot11BSSTx64DataFrameCnt         Counter64,
        ibDot11BSSTx64DataFrameBytes       Counter64,
        ibDot11BSSTx64AssocFrameCnt        Counter64,
        ibDot11BSSTx64PayloadBytes         Counter64,
        ibDot11BSSTx64RetryCnt             Counter64,
        ibDot11BSSTx64UniFrameCnt          Counter64,
        ibDot11BSSTx64NonUniFrameCnt       Counter64,
        ibDot11BSSTx64AuthenFrameCnt       Counter64
    }

ibDot11BSSTx64FrameCnt OBJECT-TYPE
    SYNTAX      Counter64
    MAX-ACCESS  read-only
    STATUS      current
    DESCRIPTION
        "Represents the total number of frames transmission with this BSS."
    ::= { ibDot11BSSTxStatis64Entry 1 }

ibDot11BSSTx64FrameBytes OBJECT-TYPE
    SYNTAX      Counter64
    MAX-ACCESS  read-only
    STATUS      current
    DESCRIPTION
        "Represents the total number of bytes transmission with this BSS."
    ::= { ibDot11BSSTxStatis64Entry 2 }

ibDot11BSSTx64DataFrameCnt OBJECT-TYPE
    SYNTAX      Counter64
    MAX-ACCESS  read-only
    STATUS      current
    DESCRIPTION
        "Represents the number of data frame transmission with this BSS."
    ::= { ibDot11BSSTxStatis64Entry 3 }

ibDot11BSSTx64DataFrameBytes OBJECT-TYPE
    SYNTAX      Counter64
    MAX-ACCESS  read-only
    STATUS      current
    DESCRIPTION
        "Represents the bytes of data frame transmission with this BSS."
    ::= { ibDot11BSSTxStatis64Entry 4 }

ibDot11BSSTx64AssocFrameCnt OBJECT-TYPE
    SYNTAX      Counter64
    MAX-ACCESS  read-only
    STATUS      current
    DESCRIPTION
        "Represents the number of associate frame transmission with this BSS."
    ::= { ibDot11BSSTxStatis64Entry 5 }

ibDot11BSSTx64PayloadBytes OBJECT-TYPE
    SYNTAX      Counter64
    MAX-ACCESS  read-only
    STATUS      current
    DESCRIPTION
        "Represents the payload bytes of data frame transmission with this BSS."
    ::= { ibDot11BSSTxStatis64Entry 6 }

ibDot11BSSTx64RetryCnt   OBJECT-TYPE
    SYNTAX      Counter64
    MAX-ACCESS  read-only
    STATUS      current
    DESCRIPTION
        "Represents the number of bytes retransmitted with this BSS."
    ::= { ibDot11BSSTxStatis64Entry 7 }

ibDot11BSSTx64UniFrameCnt OBJECT-TYPE
    SYNTAX      Counter64
    MAX-ACCESS  read-only
    STATUS      current
    DESCRIPTION
        "Represents the number of unicast frames transmission with this BSS."
    ::= { ibDot11BSSTxStatis64Entry 8 }

ibDot11BSSTx64NonUniFrameCnt OBJECT-TYPE
    SYNTAX      Counter64
    MAX-ACCESS  read-only
    STATUS      current
    DESCRIPTION
        "Represents the number of non-unicast frames transmission with this BSS."
    ::= { ibDot11BSSTxStatis64Entry 9 }

ibDot11BSSTx64AuthenFrameCnt OBJECT-TYPE
    SYNTAX      Counter64
    MAX-ACCESS  read-only
    STATUS      current
    DESCRIPTION
        "Represents the number of authentication frames transmission with this BSS."
    ::= { ibDot11BSSTxStatis64Entry 10 }

-- *****************************************************************************
-- *  End of ibDot11BSSTxStatis64Table Definition
-- *****************************************************************************

-- *****************************************************************************
-- *  ibDot11APPacketMCSRateStatis2Table Definition
-- *****************************************************************************
ibDot11APPacketMCSRateStatis2Table  OBJECT-TYPE
    SYNTAX        SEQUENCE OF IbDot11APPacketMCSRateStatis2Entry
    MAX-ACCESS    not-accessible
    STATUS        current
    DESCRIPTION
        "This table provides packet statistics based on MCS rate."
    ::= { ibDot11APStatisGroup 34 }

ibDot11APPacketMCSRateStatis2Entry  OBJECT-TYPE
    SYNTAX        IbDot11APPacketMCSRateStatis2Entry
    MAX-ACCESS    not-accessible
    STATUS        current
    DESCRIPTION
        "Each entry provides packet statistics based on MCS rate for each radio
        of a specific AP."
    INDEX
        {
            ibDot11CurAPID,
            ibDot11RadioID,
            ibDot11APPacketMCS2Rate
        }
    ::= { ibDot11APPacketMCSRateStatis2Table 1 }

IbDot11APPacketMCSRateStatis2Entry  ::=SEQUENCE
    {
        ibDot11APPacketMCS2Rate          Integer32,
        ibDot11APRXPacketMCSRate2Count   Counter64,
        ibDot11APTXPacketMCSRate2Count   Counter64
    }

ibDot11APPacketMCS2Rate    OBJECT-TYPE
    SYNTAX        Integer32 (1..2000000000)
    MAX-ACCESS    not-accessible
    STATUS        current
    DESCRIPTION
        "Represents data transmission rate(Tenfold as actual rate)."
    ::= { ibDot11APPacketMCSRateStatis2Entry 1 }

ibDot11APRXPacketMCSRate2Count    OBJECT-TYPE
    SYNTAX        Counter64
    MAX-ACCESS    read-only
    STATUS        current
    DESCRIPTION
        "Represents the count of packets received based on data transmission rate."
    ::= { ibDot11APPacketMCSRateStatis2Entry 2 }

ibDot11APTXPacketMCSRate2Count    OBJECT-TYPE
    SYNTAX        Counter64
    MAX-ACCESS    read-only
    STATUS        current
    DESCRIPTION
        "Represents the count of packets transmitted base on data transmission rate."
    ::= { ibDot11APPacketMCSRateStatis2Entry 3 }

-- *****************************************************************************
-- *  End of ibDot11APPacketMcsRateStatis2Table Definition
-- *****************************************************************************

-- *****************************************************************************
-- *  ibDot11APUserSecAuthStatisCMTable Definition
-- *****************************************************************************
ibDot11APUserSecAuthStatisCMTable OBJECT-TYPE
    SYNTAX      SEQUENCE OF IbDot11APUserSecAuthStatisCMEntry
    MAX-ACCESS  not-accessible
    STATUS      current
    DESCRIPTION
        "The table provides the user authentication statistics."
    ::= { ibDot11APStatisGroup 35 }

ibDot11APUserSecAuthStatisCMEntry OBJECT-TYPE
    SYNTAX      IbDot11APUserSecAuthStatisCMEntry
    MAX-ACCESS  not-accessible
    STATUS      current
    DESCRIPTION
        "Each entry of the table provides the user authentication statistics
        of AP."
    INDEX
        {
            ibDot11CurAPID,
            ibDot11RadioID,
            ibDot11WlanID
       }
    ::= { ibDot11APUserSecAuthStatisCMTable 1 }

IbDot11APUserSecAuthStatisCMEntry ::= SEQUENCE
    {
        ibDot11APUserConnFailCntCM              Counter32,
        ibDot11APUserAuthReqCntCM               Counter32,
        ibDot11APUserAuthSuccCntCM              Counter32,
        ibDot11APUserAuthFailCntCM              Counter32,
        ibDot11AllUserOnlineTimeCM              TimeTicks
    }

ibDot11APUserConnFailCntCM OBJECT-TYPE
    SYNTAX      Counter32
    MAX-ACCESS  read-only
    STATUS      current
    DESCRIPTION
        "Represents the failed connection count of users with this AP."
    ::= { ibDot11APUserSecAuthStatisCMEntry 1 }

ibDot11APUserAuthReqCntCM OBJECT-TYPE
    SYNTAX      Counter32
    MAX-ACCESS  read-only
    STATUS      current
    DESCRIPTION
        "Represents the total number of user authentication requests with this AP."
    ::= { ibDot11APUserSecAuthStatisCMEntry 2 }

ibDot11APUserAuthSuccCntCM OBJECT-TYPE
    SYNTAX      Counter32
    MAX-ACCESS  read-only
    STATUS      current
    DESCRIPTION
        "Represents the total number of successful user authentications with this AP."
    ::= { ibDot11APUserSecAuthStatisCMEntry 3 }

ibDot11APUserAuthFailCntCM OBJECT-TYPE
    SYNTAX      Counter32
    MAX-ACCESS  read-only
    STATUS      current
    DESCRIPTION
        "Represents the total number of failed user authentications with this AP."
    ::= { ibDot11APUserSecAuthStatisCMEntry 4 }

ibDot11AllUserOnlineTimeCM OBJECT-TYPE
    SYNTAX      TimeTicks
    MAX-ACCESS  read-only
    STATUS      current
    DESCRIPTION
        "Represents the online time of all users with this AP."
    ::= { ibDot11APUserSecAuthStatisCMEntry 5 }

-- *****************************************************************************
-- *  End of ibDot11APUserSecAuthStatisCMTable Definition
-- *****************************************************************************

-- *****************************************************************************
-- *  ibDot11APUserInfoStatis2CMTable Definition
-- *****************************************************************************
ibDot11APUserInfoStatis2CMTable OBJECT-TYPE
    SYNTAX      SEQUENCE OF IbDot11APUserInfoStatis2CMEntry
    MAX-ACCESS  not-accessible
    STATUS      current
    DESCRIPTION
        "The table will provide the authentication user information statistic
        of this AP."
    ::= { ibDot11APStatisGroup 36 }

ibDot11APUserInfoStatis2CMEntry OBJECT-TYPE
    SYNTAX      IbDot11APUserInfoStatis2CMEntry
    MAX-ACCESS  not-accessible
    STATUS      current
    DESCRIPTION
        "Each entry of the table will provide the authentication user information
        statistic of this AP."
    INDEX
        {
            ibDot11CurAPID,
            ibDot11APUserMacAddr2CM
        }
    ::= { ibDot11APUserInfoStatis2CMTable 1 }

IbDot11APUserInfoStatis2CMEntry ::= SEQUENCE
    {
        ibDot11APUserMacAddr2CM                  MacAddress,
        ibDot11APUserIpAddr2CM                   IpAddress,
        ibDot11APUserLoginName2CM                OCTET STRING,
        ibDot11APUserLoginTime2CM                OCTET STRING,
        ibDot11APUserOnlineTime2CM               TimeTicks,
        ibDot11APUserAuthType2CM                 INTEGER,
        ibDot11APUserTxPacketCnt2CM              Counter32,
        ibDot11APUserTxBytes2CM                  Counter64,
        ibDot11APUserRxPacketCnt2CM              Counter32,
        ibDot11APUserRxBytes2CM                  Counter64,
        ibDot11APUserIPv6Addr2CM                 OCTET STRING,
        ibDot11APUserMac2CM                      MacAddress,
        ibDot11APUserInCirValueCM                Counter32,
        ibDot11APUserOutCirValueCM               Counter32
    }

ibDot11APUserMacAddr2CM OBJECT-TYPE
    SYNTAX      MacAddress
    MAX-ACCESS  not-accessible
    STATUS      current
    DESCRIPTION
        "Represents the mac address of authentication user logging to this AP."
    ::= { ibDot11APUserInfoStatis2CMEntry 1 }

ibDot11APUserIpAddr2CM OBJECT-TYPE
    SYNTAX      IpAddress
    MAX-ACCESS  read-only
    STATUS      current
    DESCRIPTION
        "Represents the ip address of authentication user logging to this AP."
    ::= { ibDot11APUserInfoStatis2CMEntry 2 }

ibDot11APUserLoginName2CM OBJECT-TYPE
    SYNTAX      OCTET STRING
    MAX-ACCESS  read-only
    STATUS      current
    DESCRIPTION
        "Represents the login name of authentication user logging to this AP."
    ::= { ibDot11APUserInfoStatis2CMEntry 3 }

ibDot11APUserLoginTime2CM OBJECT-TYPE
    SYNTAX      OCTET STRING
    MAX-ACCESS  read-only
    STATUS      current
    DESCRIPTION
        "Represents the login time of authentication user with this AP."
    ::= { ibDot11APUserInfoStatis2CMEntry 4 }

ibDot11APUserOnlineTime2CM OBJECT-TYPE
    SYNTAX      TimeTicks
    MAX-ACCESS  read-only
    STATUS      current
    DESCRIPTION
        "Represents how long authentication user has been online."
    ::= { ibDot11APUserInfoStatis2CMEntry 5 }

ibDot11APUserAuthType2CM OBJECT-TYPE
    SYNTAX      INTEGER
        {
            authFree(1),
            associateAuth(2),
            portalAuth(3),
            autoAuth(4)
        }
    MAX-ACCESS  read-only
    STATUS      current
    DESCRIPTION
        "Represents the authentication type of user with this AP.
        authFree       - There is no need others authentiaction, user will
        surf internet after association.
        associateAuth  - Include WEP PSK authentication.
        portalAuth     - The authentication lunched by portal pop-up program.
        autoAuth       - 802.1X authentication."
    ::= { ibDot11APUserInfoStatis2CMEntry 6 }

ibDot11APUserTxPacketCnt2CM OBJECT-TYPE
    SYNTAX      Counter32
    MAX-ACCESS  read-only
    STATUS      current
    DESCRIPTION
        "Represents the total count of packets sent to online users."
    ::= { ibDot11APUserInfoStatis2CMEntry 7 }

ibDot11APUserTxBytes2CM OBJECT-TYPE
    SYNTAX      Counter64
    MAX-ACCESS  read-only
    STATUS      current
    DESCRIPTION
        "Represents the total bytes sent to online users."
    ::= { ibDot11APUserInfoStatis2CMEntry 8 }

ibDot11APUserRxPacketCnt2CM OBJECT-TYPE
    SYNTAX      Counter32
    MAX-ACCESS  read-only
    STATUS      current
    DESCRIPTION
        "Represents the total count of packets received from online users."
    ::= { ibDot11APUserInfoStatis2CMEntry 9 }

ibDot11APUserRxBytes2CM OBJECT-TYPE
    SYNTAX      Counter64
    MAX-ACCESS  read-only
    STATUS      current
    DESCRIPTION
        "Represents the total bytes received from online users."
    ::= { ibDot11APUserInfoStatis2CMEntry 10 }

ibDot11APUserIPv6Addr2CM OBJECT-TYPE
    SYNTAX      OCTET STRING
    MAX-ACCESS  read-only
    STATUS      current
    DESCRIPTION
        "Represents the IPv6 address of online users."
    ::= { ibDot11APUserInfoStatis2CMEntry 11 }

ibDot11APUserMac2CM OBJECT-TYPE
    SYNTAX      MacAddress
    MAX-ACCESS  read-only
    STATUS      current
    DESCRIPTION
        "Represents the mac address of authentication user logging to this AP."
    ::= { ibDot11APUserInfoStatis2CMEntry 12 }

ibDot11APUserInCirValueCM OBJECT-TYPE
    SYNTAX      Counter32
    MAX-ACCESS  read-only
    STATUS      current
    DESCRIPTION
        "Represents the CIR of inbound direction of this user."
    ::= { ibDot11APUserInfoStatis2CMEntry 13 }

ibDot11APUserOutCirValueCM OBJECT-TYPE
    SYNTAX      Counter32
    MAX-ACCESS  read-only
    STATUS      current
    DESCRIPTION
        "Represents the CIR of outbound direction of this user."
    ::= { ibDot11APUserInfoStatis2CMEntry 14 }

-- *****************************************************************************
-- *  End of ibDot11APUserInfoStatis2CMTable Definition
-- *****************************************************************************

-- *****************************************************************************
-- *  AP Management Notifications Definition
-- *****************************************************************************
-- AP Management Notification

        ibDot11APMtTraps OBJECT IDENTIFIER
    ::= { ibDot11APMtNotifyGroup 0 }

ibDot11APMtWorkModeChgTrap NOTIFICATION-TYPE
    OBJECTS
        {
            ibDot11APID,
            ibDot11APChgWorkMode,
            ibDot11APMtTrapAPMacAddress
        }
    STATUS      current
    DESCRIPTION
        "The notification will be sent when AP changes the work mode, and
         ibDot11APWorkMode suggests which work mode will be used by AP."
    ::= { ibDot11APMtTraps 1 }

ibDot11APMtCfgErrorTrap NOTIFICATION-TYPE
    OBJECTS
        {
            ibDot11APID,
            ibDot11RadioID,
            ibDot11APMtTrapCfgErrReason
        }
    STATUS      current
    DESCRIPTION
        "The notification will represent errors caused by the
        configuration operation of AP."
    ::= { ibDot11APMtTraps 2 }

ibDot11APMtRadioFailTrap NOTIFICATION-TYPE
    OBJECTS
        {
            ibDot11APID,
            ibDot11RadioID,
            ibDot11APMtTrapRadioFailReason
        }
    STATUS      current
    DESCRIPTION
        "The notification will notify which the operational status
        of radio becomes down."
    ::= { ibDot11APMtTraps 3 }

ibDot11APMtRadioFailRecoverTrap NOTIFICATION-TYPE
    OBJECTS
        {
            ibDot11APID,
            ibDot11RadioID,
            ibDot11APMtTrapRadioFailReason
        }
    STATUS      current
    DESCRIPTION
        "The notification will notify the operational status of which radio
        becomes up again."
    ::= { ibDot11APMtTraps 4 }

ibDot11APMtRdoChanlChgTrap NOTIFICATION-TYPE
    OBJECTS
        {
            ibDot11APID,
            ibDot11RadioID,
            ibDot11APChannelChgMode,
            ibDot11APMtTrapOldChannel,
            ibDot11APMtTrapNewChannel,
            ibDot11APMtChanlChgCount,
            ibDot11APMtTrapAPMacAddress
        }
    STATUS      current
    DESCRIPTION
        "The notification will represent which radio changes the channel."
    ::= { ibDot11APMtTraps 5 }

ibDot11APMtTimeSynFail NOTIFICATION-TYPE
    OBJECTS
        {
            ibDot11APID
        }
    STATUS      current
    DESCRIPTION
        "The notification will be sent when AC and AP failed to
        synchronize their time."
    ::= { ibDot11APMtTraps 6 }

ibDot11APMtChlIntfDetected NOTIFICATION-TYPE
    OBJECTS
        {
            ibDot11Channel
        }
    STATUS      current
    DESCRIPTION
        "The notification will be sent when some ambient device interferes with
        current channel."
    ::= { ibDot11APMtTraps 7 }

ibDot11APMtIntfAPDetected NOTIFICATION-TYPE
    OBJECTS
        {
            ibDot11Channel,
            ibDot11APIntfDevMACAddress
        }
    STATUS current
    DESCRIPTION
        "The notification will be sent when some ambient AP interferes with
        current channel."
    ::= { ibDot11APMtTraps 8 }

ibDot11APMtIntfStaDetected NOTIFICATION-TYPE
    OBJECTS
        {
            ibDot11Channel,
            ibDot11APIntfDevMACAddress
        }
    STATUS current
    DESCRIPTION
        "The notification will be sent when some ambient station interferes with
        current channel."
    ::= { ibDot11APMtTraps 9 }

ibDot11APMtIPChange NOTIFICATION-TYPE
    OBJECTS
        {
            ibDot11APIPAddress,
            ibDot11APMtTrapOldIPAddr
        }
    STATUS current
    DESCRIPTION
        "The notification will be sent when IP address of the AP changes."
    ::= { ibDot11APMtTraps 10 }

ibDot11APFlashWriteFailure NOTIFICATION-TYPE
    OBJECTS
        {
            ibDot11APID,
            ibDot11APMtFormerApVersion,
            ibDot11APMtTrapAPMacAddress
        }
    STATUS      current
    DESCRIPTION
        "The notification will be sent when AP failed to write data
        into flash."
    ::= { ibDot11APMtTraps 11 }

ibDot11APSysReboot NOTIFICATION-TYPE
    OBJECTS
        {
            ibDot11APID
        }
    STATUS current
    DESCRIPTION
        "The notification will be sent when AP reboots."
    ::= { ibDot11APMtTraps 12 }

ibDot11APMtAvailChlTooLow NOTIFICATION-TYPE
    OBJECTS
        {
            ibDot11RadioID,
            ibDot11APMtAPID,
            ibDot11APMtTrapAPMacAddress
        }
    STATUS current
    DESCRIPTION
        "The notification will be sent when number of available channels is
         too low.
        "
    ::= { ibDot11APMtTraps 13 }

ibDot11APImgDwldSuccess NOTIFICATION-TYPE
    OBJECTS
        {
            ibDot11CurrAPName,
            ibDot11CurrAPIPAddress,
            ibDot11CurrAPSoftwareVersion
        }
    STATUS current
    DESCRIPTION
        "The notification will be sent when AP succeeds to download image from
        AC.
        "
    ::= { ibDot11APMtTraps 14 }

ibDot11APInterfDetectedTrap NOTIFICATION-TYPE
    OBJECTS
        {
            ibDot11Channel,
            ibDot11CurrInterfDetectedNum,
            ibDot11InterfMacList
        }
    STATUS current
    DESCRIPTION
        "This notification will be sent when some ambient AP interferes with
         current channel."
    ::= { ibDot11APMtTraps 15 }

ibDot11APInterfClearTrap NOTIFICATION-TYPE
    OBJECTS
        {
            ibDot11Channel,
            ibDot11APMtAPID,
            ibDot11APMtRadioID,
            ibDot11APMtInterfMacAdd,
            ibDot11APMtFirstTrapTime,
            ibDot11APMtTrapAPMacAddress
        }
    STATUS current
    DESCRIPTION
        "This notification will be sent when interference caused by ambient
         APs on the current channel disappears."
    ::= { ibDot11APMtTraps 16 }

ibDot11StaInterfDetectedTrap NOTIFICATION-TYPE
    OBJECTS
        {
            ibDot11Channel,
            ibDot11CurrInterfDetectedNum,
            ibDot11InterfMacList,
            ibDot11APMtFirstTrapTime
        }
    STATUS current
    DESCRIPTION
        "This notification will be sent when interference caused by ambient
         STAs on the current channel disappears."
    ::= { ibDot11APMtTraps 17 }

ibDot11StaInterfClearTrap NOTIFICATION-TYPE
    OBJECTS
        {
            ibDot11Channel,
            ibDot11APMtAPID,
            ibDot11APMtRadioID,
            ibDot11APMtInterfMacAdd,
            ibDot11APMtFirstTrapTime,
            ibDot11APMtTrapAPMacAddress
        }
    STATUS current
    DESCRIPTION
        "This notification will be sent when interference caused by ambient
         devices on the current channel happens."
    ::= { ibDot11APMtTraps 18 }

ibDot11OtherDevIntDetectedTrap NOTIFICATION-TYPE
    OBJECTS
        {
            ibDot11Channel,
            ibDot11APMtFirstTrapTime
        }
    STATUS      current
    DESCRIPTION
        "This notification will be sent when interference caused by ambient
         devices on the current channel disappears."
    ::= { ibDot11APMtTraps 19 }

ibDot11OtherDevIntClearTrap NOTIFICATION-TYPE
    OBJECTS
        {
            ibDot11Channel,
            ibDot11APMtAPID,
            ibDot11APMtRadioID,
            ibDot11APMtFirstTrapTime,
            ibDot11APMtTrapAPMacAddress
        }
    STATUS      current
    DESCRIPTION
        "This notification will be sent when previous ambient device disappeared with
         the same channel."
    ::= { ibDot11APMtTraps 20 }

ibDot11APModuleTroubleTrap NOTIFICATION-TYPE
    OBJECTS
        {
            ibDot11RadioID,
            ibDot11APMtAPID,
            ibDot11APMtTrapAPMacAddress
        }
    STATUS current
    DESCRIPTION
        "This notification will be sent when WLAN module failed."
    ::= { ibDot11APMtTraps 21 }

ibDot11APModuleTroubleClearTrap NOTIFICATION-TYPE
    OBJECTS
        {
            ibDot11RadioID,
            ibDot11APMtAPID,
            ibDot11APMtTrapAPMacAddress
        }
    STATUS current
    DESCRIPTION
        "The notification will be sent when WLAN module recovered."
    ::= { ibDot11APMtTraps 22 }

ibDot11APRadioDownTrap NOTIFICATION-TYPE
    OBJECTS
        {
            ibDot11RadioID,
            ibDot11APRadioDownReason,
            ibDot11APMtAPID,
            ibDot11APMtFirstTrapTime,
            ibDot11APMtTrapAPMacAddress
        }
    STATUS current
    DESCRIPTION
        "This notification will be sent when WLAN links interrupted."
    ::= { ibDot11APMtTraps 23 }

ibDot11APRadioDownRecovTrap NOTIFICATION-TYPE
    OBJECTS
        {
            ibDot11RadioID,
            ibDot11APMtAPID,
            ibDot11APMtFirstTrapTime,
            ibDot11APMtTrapAPMacAddress
        }
    STATUS current
    DESCRIPTION
        "This notification will be sent when WLAN links recover."
    ::= { ibDot11APMtTraps 24 }

ibDot11APStaFullTrap NOTIFICATION-TYPE
    OBJECTS
        {
            ibDot11APID,
            ibDot11StaLimitNumber,
            ibDot11StaFullReason,
            ibDot11APMtFirstTrapTime,
            ibDot11APMtTrapAPMacAddress
        }
    STATUS current
    DESCRIPTION
        "This notification will be sent when STA number reach limit number."
    ::= { ibDot11APMtTraps 25 }

ibDot11APStaFullRecoverTrap NOTIFICATION-TYPE
    OBJECTS
        {
            ibDot11APID,
            ibDot11StaLimitNumber,
            ibDot11StaFullReason,
            ibDot11APMtFirstTrapTime,
            ibDot11APMtTrapAPMacAddress
        }
    STATUS current
    DESCRIPTION
        "This notification will be sent when STA number recover enough level."
    ::= { ibDot11APMtTraps 26 }

ibDot11DFSFreeCntBelowThrRecov NOTIFICATION-TYPE
    OBJECTS
        {
            ibDot11RadioID,
            ibDot11APMtAPID,
            ibDot11APMtTrapAPMacAddress
        }
    STATUS current
    DESCRIPTION
        "This notification will be sent when available channels number
        recover enough level."
    ::= { ibDot11APMtTraps 27 }

ibDot11APCpuUsageHigh NOTIFICATION-TYPE
    OBJECTS
        {
            ibDot11APID,
            ibDot11APCPURTUsage,
            ibDot11APMtFirstTrapTime,
            ibDot11APMtTrapAPMacAddress
        }
    STATUS current
    DESCRIPTION
        "The notification will be sent when the AP CPU usage exceeds the
         threshold.
        "
    ::= { ibDot11APMtTraps 28 }

ibDot11APCpuUsageHighRecover NOTIFICATION-TYPE
    OBJECTS
        {
            ibDot11APID,
            ibDot11APCPURTUsage,
            ibDot11APMtFirstTrapTime,
            ibDot11APMtTrapAPMacAddress
        }
    STATUS current
    DESCRIPTION
        "The notification will be sent when the AP CPU usage descends the
         threshold.
        "
    ::= { ibDot11APMtTraps 29 }

ibDot11APMemUsageHigh NOTIFICATION-TYPE
    OBJECTS
        {
            ibDot11APID,
            ibDot11APMemRTUsage,
            ibDot11APMtFirstTrapTime,
            ibDot11APMtTrapAPMacAddress
        }
    STATUS current
    DESCRIPTION
        "The notification will be sent when the AP memory usage exceeds the
         threshold.
        "
    ::= { ibDot11APMtTraps 30 }

ibDot11APMemUsageHighRecover NOTIFICATION-TYPE
    OBJECTS
        {
            ibDot11APID,
            ibDot11APMemRTUsage,
            ibDot11APMtFirstTrapTime,
            ibDot11APMtTrapAPMacAddress
        }
    STATUS current
    DESCRIPTION
        "The notification will be sent when the AP memory usage descends the
         threshold.
         "
    ::= { ibDot11APMtTraps 31 }

ibDot11APTrapUserCntExceedThre NOTIFICATION-TYPE
    OBJECTS
        {
            ibDot11APID,
            ibDot11APTrapUserCnt,
            ibDot11APTrapUserThreshold
        }
    STATUS      current
    DESCRIPTION
        "The notification will be sent when the online user counter exceeds
        the threshold."
    ::= { ibDot11APMtTraps 32 }

ibDot11APMtDetectedIntfAP NOTIFICATION-TYPE
    OBJECTS
        {
            ibDot11APMtAPID,
            ibDot11APMtRadioID,
            ibDot11APMtChannel,
            ibDot11APMtInterfMacAdd,
            ibDot11APMtFirstTrapTime,
            ibDot11APMtTrapAPMacAddress
        }
    STATUS current
    DESCRIPTION
        "This notification will be sent when some ambient AP interferes with
         current channel."
    ::= { ibDot11APMtTraps 33 }

ibDot11APMtDetectedIntfSTA NOTIFICATION-TYPE
    OBJECTS
        {
            ibDot11APMtAPID,
            ibDot11APMtRadioID,
            ibDot11APMtChannel,
            ibDot11APMtInterfMacAdd,
            ibDot11APMtFirstTrapTime,
            ibDot11APMtTrapAPMacAddress
        }
    STATUS current
    DESCRIPTION
        "This notification will be sent when some ambient STA interferes with
         current channel."
    ::= { ibDot11APMtTraps 34 }

ibDot11APMtDetectedIntfOtherDev NOTIFICATION-TYPE
    OBJECTS
        {
            ibDot11APMtAPID,
            ibDot11APMtRadioID,
            ibDot11APMtChannel,
            ibDot11APMtTrapAPMacAddress
        }
    STATUS      current
    DESCRIPTION
        "This notification will be sent when other device interferes with
         current channel."
    ::= { ibDot11APMtTraps 35 }

ibDot11DetcAdjChlIntfAP NOTIFICATION-TYPE
    OBJECTS
        {
            ibDot11APMtAPID,
            ibDot11APMtRadioID,
            ibDot11APMtChannel,
            ibDot11APMtAdjChannel,
            ibDot11APMtInterfMacAdd,
            ibDot11APMtFirstTrapTime
        }
    STATUS current
    DESCRIPTION
        "This notification will be sent when some ambient AP interferes with
         adjacent channel."
    ::= { ibDot11APMtTraps 36 }

ibDot11DetcAdjChlIntfAPClear NOTIFICATION-TYPE
    OBJECTS
        {
            ibDot11APMtAPID,
            ibDot11APMtRadioID,
            ibDot11APMtChannel,
            ibDot11APMtAdjChannel,
            ibDot11APMtInterfMacAdd,
            ibDot11APMtFirstTrapTime
        }
    STATUS current
    DESCRIPTION
        "This notification will be sent when interference caused by ambient
         APs on the adjacent channel disappears."
    ::= { ibDot11APMtTraps 37 }

ibDot11APPowerOffTrap NOTIFICATION-TYPE
    OBJECTS
        {
            ibDot11APMtAPID
        }
    STATUS current
    DESCRIPTION
        "This notification will be sent when AP is power-off."
    ::= { ibDot11APMtTraps 38 }

ibDot11APPowerOnTrap NOTIFICATION-TYPE
    OBJECTS
        {
            ibDot11APMtAPID
        }
    STATUS current
    DESCRIPTION
        "This notification will be sent when AP is power-on."
    ::= { ibDot11APMtTraps 39 }

ibDot11UpLinkSwitchTrap NOTIFICATION-TYPE
    OBJECTS
        {
            ibDot11APMtAPID,
            ibDot11APMtUpLinkSwitchInfo,
            ibDot11APMtTrapAPMacAddress,
            ibDot11APMtUpLinkSwitchTime,
            ibDot11APMtOldCellId,
            ibDot11APMtCurCellId,
            ibDot11APMtOldBand,
            ibDot11APMtActiveBand
        }
    STATUS current
    DESCRIPTION
        "This notification will be sent when uplink switches to 3G or 4G."
    ::= { ibDot11APMtTraps 40 }

-- AP Management Notification variable object

ibDot11APMtTrapVarObjects OBJECT IDENTIFIER
    ::= { ibDot11APMtNotifyGroup 1 }

ibDot11APMtTrapCfgErrReason OBJECT-TYPE
    SYNTAX      IbDot11NotifyReasonType
    MAX-ACCESS  accessible-for-notify
    STATUS      current
    DESCRIPTION
        "Represents errors caused by configuration operation."
    ::= { ibDot11APMtTrapVarObjects 1 }

ibDot11APMtTrapRadioFailReason OBJECT-TYPE
    SYNTAX      INTEGER
        {
            config(1),
            iberror(2),
            swerror(3),
            radar(4),
            unknown(8)
        }
    MAX-ACCESS  accessible-for-notify
    STATUS      current
    DESCRIPTION
        "Represents errors caused by configuration operation.
        The following values are supported:
        config     - Configuration error
        iberror  - Hardware error
        swerror    - Software error
        radar      - Radar Detection
        unknown    - Unknown reason"
    ::= { ibDot11APMtTrapVarObjects 2 }

ibDot11APMtTrapOldChannel OBJECT-TYPE
    SYNTAX      IbDot11ChannelScopeType
    MAX-ACCESS  accessible-for-notify
    STATUS      current
    DESCRIPTION
        "Represents which channel the radio used to use."
    ::= { ibDot11APMtTrapVarObjects 3 }

ibDot11APMtTrapNewChannel OBJECT-TYPE
    SYNTAX      IbDot11ChannelScopeType
    MAX-ACCESS  accessible-for-notify
    STATUS      current
    DESCRIPTION
        "Represents which channel the radio will use."
    ::= { ibDot11APMtTrapVarObjects 4 }

ibDot11APChannelChgMode OBJECT-TYPE
    SYNTAX      IbDot11RFModeType
    MAX-ACCESS  accessible-for-notify
    STATUS      current
    DESCRIPTION
        "Represents the channel change mode for a radio."
    ::= { ibDot11APMtTrapVarObjects 5 }

ibDot11APChgWorkMode OBJECT-TYPE
    SYNTAX      INTEGER
        {
            normal(1),
            monitor(2),
            hybrid(3)
        }
    MAX-ACCESS  accessible-for-notify
    STATUS      current
    DESCRIPTION
        "Represents what work mode for AP.
        The following values are supported:
        normal  - AP will supply WLAN service.
        monitor - AP will be a monitor to detect attack.
        hybrid  - AP will supply WLAN service and detect attack."
    ::= { ibDot11APMtTrapVarObjects 6 }

ibDot11APIntfDevMACAddress OBJECT-TYPE
    SYNTAX      MacAddress
    MAX-ACCESS  accessible-for-notify
    STATUS      current
    DESCRIPTION
        "Represents MAC address of the device which triggers the notification."
    ::= { ibDot11APMtTrapVarObjects 7 }

ibDot11APMtTrapOldIPAddr OBJECT-TYPE
    SYNTAX      IpAddress
    MAX-ACCESS  accessible-for-notify
    STATUS      current
    DESCRIPTION
        "Represents the IP address of AP."
    ::= { ibDot11APMtTrapVarObjects 8 }

ibDot11CurrInterfDetectedNum OBJECT-TYPE
    SYNTAX      Integer32
    MAX-ACCESS  accessible-for-notify
    STATUS      current
    DESCRIPTION
        "Represents the number of interfere detected."
    ::= { ibDot11APMtTrapVarObjects 9 }

ibDot11StaFullReason OBJECT-TYPE
    SYNTAX      INTEGER
        {
            ap(1),
            bss(2),
            radio(3),
            radioConcur(4),
            radiopolicy(5),
            ac(6),
            acConcur(7),
            aid(8)
        }
    MAX-ACCESS  accessible-for-notify
    STATUS      current
    DESCRIPTION
        "Reports which kind maximum number of STA
         is reached.  New STA is not able to associate."
    ::= { ibDot11APMtTrapVarObjects 10 }

ibDot11StaLimitNumber OBJECT-TYPE
    SYNTAX      Integer32
    MAX-ACCESS  accessible-for-notify
    STATUS      current
    DESCRIPTION
        "Represents the limit number of STA."
    ::= { ibDot11APMtTrapVarObjects 11 }

ibDot11APRadioDownReason OBJECT-TYPE
    SYNTAX  INTEGER
        {
            phyicalUnusable(1),
            configDisable(2),
            operatinUnusable(3),
            apTunnelDown(4)
        }
    MAX-ACCESS  accessible-for-notify
    STATUS      current
    DESCRIPTION
        "Reports the reason why WLAN links is interrupted."
    ::= { ibDot11APMtTrapVarObjects 12 }

ibDot11InterfMacList OBJECT-TYPE
    SYNTAX      OCTET STRING
    MAX-ACCESS  accessible-for-notify
    STATUS      current
    DESCRIPTION
        "Represents MAC address list of interfere detected."
    ::= { ibDot11APMtTrapVarObjects 13 }

ibDot11APTrapUserCnt OBJECT-TYPE
    SYNTAX      Integer32
    MAX-ACCESS  accessible-for-notify
    STATUS      current
    DESCRIPTION
        "Represents the online user counter of AP."
    ::= { ibDot11APMtTrapVarObjects 14 }

ibDot11APTrapUserThreshold OBJECT-TYPE
    SYNTAX      Integer32
    MAX-ACCESS  accessible-for-notify
    STATUS      current
    DESCRIPTION
        "Represents threshold of AP's online user counter."
    ::= { ibDot11APMtTrapVarObjects 15 }

ibDot11APMtChanlChgCount OBJECT-TYPE
    SYNTAX      Integer32
    MAX-ACCESS  accessible-for-notify
    STATUS      current
    DESCRIPTION
        "Represents how many times that channel changed."
    ::= { ibDot11APMtTrapVarObjects 16 }

ibDot11APMtFormerApVersion OBJECT-TYPE
    SYNTAX      OCTET STRING
    MAX-ACCESS  accessible-for-notify
    STATUS      current
    DESCRIPTION
        "Represents former software version of AP."
    ::= { ibDot11APMtTrapVarObjects 17 }

ibDot11APMtAPID OBJECT-TYPE
    SYNTAX      IbDot11ObjectIDType
    MAX-ACCESS  accessible-for-notify
    STATUS      current
    DESCRIPTION
        "To uniquely identify each AP."
    ::= { ibDot11APMtTrapVarObjects 18 }

ibDot11APMtRadioID OBJECT-TYPE
    SYNTAX      IbDot11RadioScopeType
    MAX-ACCESS  accessible-for-notify
    STATUS      current
    DESCRIPTION
        "Represents each radio."
    ::= { ibDot11APMtTrapVarObjects 19 }

ibDot11APMtChannel OBJECT-TYPE
    SYNTAX      IbDot11ChannelScopeType
    MAX-ACCESS  accessible-for-notify
    STATUS      current
    DESCRIPTION
        "Represents the current channel allocation for radio."
    ::= { ibDot11APMtTrapVarObjects 20 }

ibDot11APMtInterfMacAdd OBJECT-TYPE
    SYNTAX      MacAddress
    MAX-ACCESS  accessible-for-notify
    STATUS      current
    DESCRIPTION
        "Represents the MAC address of an AP."
    ::= { ibDot11APMtTrapVarObjects 21 }

ibDot11APMtAdjChannel OBJECT-TYPE
    SYNTAX      IbDot11ChannelScopeType
    MAX-ACCESS  accessible-for-notify
    STATUS      current
    DESCRIPTION
        "Represents the adjacent channel of radio."
    ::= { ibDot11APMtTrapVarObjects 22 }

ibDot11APMtFirstTrapTime OBJECT-TYPE
    SYNTAX      TimeTicks
    MAX-ACCESS  accessible-for-notify
    STATUS      current
    DESCRIPTION
        "Represents the first trap time."
    ::= { ibDot11APMtTrapVarObjects 23 }

ibDot11APMtTrapAPMacAddress OBJECT-TYPE
    SYNTAX      MacAddress
    MAX-ACCESS  accessible-for-notify
    STATUS      current
    DESCRIPTION
        "Represents the MAC address of an AP."
    ::= {ibDot11APMtTrapVarObjects 24}

ibDot11APMtUpLinkSwitchInfo OBJECT-TYPE
    SYNTAX      INTEGER
        {
            unknown(1),
            tdscdma(2),
            tdlte(3)
        }
    MAX-ACCESS  accessible-for-notify
    STATUS      current
    DESCRIPTION
        "Represents the type which uplink switches to.
        The following values are supported:
        TDSCDMA - The uplink switches to TDSCDMA.
        TDLTE - The uplink switches to TDLTE.
        unknown - Unknown uplink type."
    ::= {ibDot11APMtTrapVarObjects 25}

ibDot11APMtUpLinkSwitchTime OBJECT-TYPE
    SYNTAX      TimeStamp
    MAX-ACCESS  accessible-for-notify
    STATUS      current
    DESCRIPTION
        "Represents the time when uplink switches."
    ::= { ibDot11APMtTrapVarObjects 26 }

ibDot11APMtOldCellId OBJECT-TYPE
    SYNTAX      Integer32
    MAX-ACCESS  accessible-for-notify
    STATUS      current
    DESCRIPTION
        "Represents the cell id before uplink switch."
    ::= { ibDot11APMtTrapVarObjects 27 }

ibDot11APMtCurCellId OBJECT-TYPE
    SYNTAX      Integer32
    MAX-ACCESS  accessible-for-notify
    STATUS      current
    DESCRIPTION
        "Represents the cell id after uplink switch."
    ::= { ibDot11APMtTrapVarObjects 28 }

ibDot11APMtOldBand OBJECT-TYPE
    SYNTAX      OCTET STRING
    MAX-ACCESS  accessible-for-notify
    STATUS      current
    DESCRIPTION
        "Represents the band before uplink switch."
    ::= { ibDot11APMtTrapVarObjects 29 }

ibDot11APMtActiveBand OBJECT-TYPE
    SYNTAX      OCTET STRING
    MAX-ACCESS  accessible-for-notify
    STATUS      current
    DESCRIPTION
        "Represents the band after uplink switch."
    ::= { ibDot11APMtTrapVarObjects 30 }

-- *****************************************************************************
-- *  End of AP Management Notification  Definition
-- *****************************************************************************
END
