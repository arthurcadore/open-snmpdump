--  =============================================================================
-- Copyright (C) 2023 Intelbras S.A. All rights reserved.
--
--  Description: This MIB module contains managed object definitions for
--               Multiprotocol Extensions for BGP (MBGP or MP-BGP).
--  Reference: draft-ietf-idr-bgp4-mibv2-15
--  Version: V1.0
--  History:
--    V1.0 2019-07-04 Initial version Created by Gubin
--  =============================================================================
IB-BGP4V2-MIB DEFINITIONS ::= BEGIN

    IMPORTS
        OBJECT-TYPE, MODULE-IDENTITY, NOTIFICATION-TYPE
            FROM SNMPv2-SMI
        OBJECT-GROUP, MODULE-COMPLIANCE, NOTIFICATION-GROUP
            FROM SNMPv2-CONF
        InetAddressIPv6
            FROM INET-ADDRESS-MIB
        ibCommon
            FROM IB-OID-MIB;

--  =============================================================================
--  module identity part
--  =============================================================================
ibBgp4v2 MODULE-IDENTITY
    LAST-UPDATED "201907040000Z"        -- July 04, 2019 at 00:00 GMT
    ORGANIZATION
        "Intelbras S.A. Industria de Telecomunicacao Eletronica Brasileria."
    CONTACT-INFO
        ""
    DESCRIPTION
        "The MIB module for the BGP4+ protocol."
    REVISION "201907040000Z"            -- July 04, 2019 at 00:00 GMT
    DESCRIPTION
        "This MIB updates the BGP MIB defined in
        RFC 4273."
    ::= { ibCommon 183 }

--  =============================================================================
--  ibBgp4v2Objects definition begin
--  =============================================================================
ibBgp4v2Objects OBJECT IDENTIFIER ::= { ibBgp4v2 1 }

ibBgp4v2PeerTable OBJECT-TYPE
    SYNTAX SEQUENCE OF IbBgp4v2PeerEntry
    MAX-ACCESS not-accessible
    STATUS current
    DESCRIPTION
        "BGP peer table.  This table contains, one entry
        per BGP peer, information about the connections
        with BGP peers."
    ::= { ibBgp4v2Objects 1 }

ibBgp4v2PeerEntry OBJECT-TYPE
    SYNTAX IbBgp4v2PeerEntry
    MAX-ACCESS not-accessible
    STATUS current
    DESCRIPTION
        "Entry containing information about the connection
        with a BGP peer."
    INDEX { ibBgp4v2PeerRemoteAddr }
    ::= { ibBgp4v2PeerTable 1 }

IbBgp4v2PeerEntry ::=
    SEQUENCE {
        ibBgp4v2PeerRemoteAddr
            InetAddressIPv6,
        ibBgp4v2PeerLastError
            OCTET STRING,
        ibBgp4v2PeerState
            INTEGER
     }

ibBgp4v2PeerRemoteAddr OBJECT-TYPE
    SYNTAX InetAddressIPv6
    MAX-ACCESS accessible-for-notify
    STATUS current
    DESCRIPTION
        "The remote IPv6 address of this entry's BGP
        peer."
    ::= { ibBgp4v2PeerEntry 1 }

ibBgp4v2PeerLastError OBJECT-TYPE
    SYNTAX OCTET STRING (SIZE (2))
    MAX-ACCESS read-only
    STATUS current
    DESCRIPTION
        "The last error code and subcode seen by this
        peer on this connection.  If no error has
        occurred, this field is zero.  Otherwise, the
        first byte of this two byte OCTET STRING
        contains the error code, and the second byte
        contains the subcode."
    REFERENCE
        "RFC 4271, Section 4.5."
    ::= { ibBgp4v2PeerEntry 2 }

ibBgp4v2PeerState OBJECT-TYPE
    SYNTAX INTEGER
        {
        idle(1),
        connect(2),
        active(3),
        opensent(4),
        openconfirm(5),
        established(6)
        }
    MAX-ACCESS read-only
    STATUS current
    DESCRIPTION
        "The BGP peer connection state."
    REFERENCE
        "RFC 4271, Section 8.2.2."
    ::= { ibBgp4v2PeerEntry 3 }
--  ============================================================================
--  End of ibBgp4v2Objects Definition
--  ============================================================================

--  ============================================================================
--  Conformance Information
--  ============================================================================
ibBgp4v2Conformance OBJECT IDENTIFIER ::= { ibBgp4v2 2 }
ibBgp4v2Compliances OBJECT IDENTIFIER ::= { ibBgp4v2Conformance 1 }
ibBgp4v2Groups OBJECT IDENTIFIER ::= { ibBgp4v2Conformance 2 }

ibBgp4v2Compliance MODULE-COMPLIANCE
    STATUS current
    DESCRIPTION
        "The compliance statement for entities which implement the BGP4+
        mib."
    MODULE -- this module
        MANDATORY-GROUPS { ibBgp4v2ErrorsGroup, ibBgp4v2PeerGroup }
    GROUP ibBgp4v2NotificationGroup
    DESCRIPTION
        "Implementation of BGP Notifications are completely optional
        in this MIB."
    ::= { ibBgp4v2Compliances 1 }

ibBgp4v2ErrorsGroup OBJECT-GROUP
    OBJECTS { ibBgp4v2PeerLastError }
    STATUS current
    DESCRIPTION
        "Errors received on BGP peering sessions."
    ::= { ibBgp4v2Groups 1 }


ibBgp4v2PeerGroup OBJECT-GROUP
    OBJECTS { ibBgp4v2PeerState, ibBgp4v2PeerRemoteAddr }
    STATUS current
    DESCRIPTION
        "Core object types on BGP peering sessions."
    ::= { ibBgp4v2Groups 2 }


ibBgp4v2NotificationGroup NOTIFICATION-GROUP
    NOTIFICATIONS { ibBgp4v2Established, ibBgp4v2BackwardTransition }
    STATUS current
    DESCRIPTION
        "Notifications in this modules are completely optional."
    ::= { ibBgp4v2Groups 3 }

--  =============================================================================
--  End of Conformance Definition
--  =============================================================================

--  =============================================================================
--  Notifications Definition
--  =============================================================================
ibBgp4v2Notification OBJECT IDENTIFIER ::= { ibBgp4v2 0 }

ibBgp4v2Established NOTIFICATION-TYPE
    OBJECTS { ibBgp4v2PeerRemoteAddr, ibBgp4v2PeerLastError, ibBgp4v2PeerState }
    STATUS current
    DESCRIPTION
        "The ibBgp4v2Established event is generated when the BGP4+
        FSM enters the ESTABLISHED state."
    ::= { ibBgp4v2Notification 1 }

ibBgp4v2BackwardTransition NOTIFICATION-TYPE
    OBJECTS { ibBgp4v2PeerRemoteAddr, ibBgp4v2PeerLastError, ibBgp4v2PeerState }
    STATUS current
    DESCRIPTION
        "The ibBgp4v2BackwardTransition event is generated when
        the BGP4+ FSM moves from a higher numbered state to a lower
        numbered state.

        Due to the nature of the BGP state machine, an
        implementation MAY rate limit the generation of this event.
        An implementation MAY also generate this notification ONLY

        when the state machine moves out of the established state.
        An implementation should document its specific behavior."
    ::= { ibBgp4v2Notification 2 }
--  =============================================================================
--  End of Notifications Definition
--  =============================================================================

--  End of IB-BGP4V2-MIB
END
