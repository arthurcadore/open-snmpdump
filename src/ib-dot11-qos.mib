-- =====================================================================
-- Copyright (C) 2023 Intelbras S.A. All rights reserved.
--
-- Description: The file defines a MIB to provide WLAN QoS configuration.
-- configuration information.
-- Reference:
-- Version: V1.2
-- History:
-- V1.0 2008-7-23 created by heziqi
-- V1.1 2010-03-15 Modified by Wang Lu
--      Add ibDot11RadioWmmEdcaCfg2Table
-- V1.2 2013-02-17 Modified by Xiao min
--      Change SYNTAX of ibDot11RadioCacUserNum
-- =====================================================================
IB-DOT11-QOS-MIB DEFINITIONS ::= BEGIN

IMPORTS
        TruthValue,
        TEXTUAL-CONVENTION
    FROM SNMPv2-TC
        MODULE-IDENTITY,
        OBJECT-TYPE,
        Integer32
    FROM SNMPv2-SMI
        ibDot11,
        IbDot11QosAcType,
        IbDot11RadioElementIndex,
        IbDot11ObjectIDType,
        IbDot11RadioScopeType
    FROM IB-DOT11-REF-MIB;

ibDot11QoS MODULE-IDENTITY
    LAST-UPDATED "200807231200Z"
    ORGANIZATION
        "Intelbras S.A. Industria de Telecomunicacao Eletronica Brasileria."
    CONTACT-INFO
        ""
    DESCRIPTION
        "This MIB provides information about WLAN QoS configuration.

        GLOSSARY

        IEEE 802.11
        Standard to encourage interoperability among
        wireless networking equipment.

        WMM
        WMM is a wireless QoS protocol designed to preferentially
        transmit packets with high priority, thus guaranteeing
        better QoS services for voice and video applications in
        a wireless network.

        EDCA
        Enhanced distributed channel access (EDCA) is a channel
        contention mechanism designed by WMM to preferentially
        transmit packets with high priority and allocate more
        bandwidth to such packets.

        AC
        Access category (AC), is used for channel contention.
        WMM defines four access categories; they are AC-VO (voice),
        AC-VI (video), AC-BE (best-effort), and AC-BK (background)
        in the descending order of priority.  When contending for a
        channel, a high-priority AC preempts a low-priority AC.

        CAC
        Connection admission control (CAC) limits the number of
        clients that are using high-priority ACs (AC-VO and AC-VI)
        to guarantee sufficient bandwidth for existing high-priority
        traffic.

        U-APSD
        Unscheduled automatic power-save delivery (U-APSD) is a new
        power saving mechanism defined by WMM to enhance the power
        saving capability of clients.

        SVP
        SpectraLink voice priority (SVP) is a voice priority protocol
        designed by the Spectralink company to guarantee QoS for voice
        traffic."

    REVISION "200807231200Z"
    DESCRIPTION
            "The initial revision of this MIB module."
    ::= { ibDot11 9 }

-- ==================================================================
-- Textual Conventions
-- ==================================================================
IbDot11WMMSVPMapAC ::=  TEXTUAL-CONVENTION
    STATUS      current
    DESCRIPTION
        "The AC level which SVP packets are assigned to.
         acbk    : for background access category,
         acbe    : for best-effort access category,
         acvi    : for voice access category,
         acvo    : for video access category,
         disable : for disable SVP feature
        "
    SYNTAX      INTEGER
        {
            acbk(1),
            acbe(2),
            acvi(3),
            acvo(4),
            disable(5)
        }

IbDot11WMMCACPolicy ::=  TEXTUAL-CONVENTION
    STATUS      current
    DESCRIPTION
        "The policy of CAC.
         channelUtilization : the channel utilization-based admission policy
                                 for CAC,
         userNumber         : the users-based admission policy for CAC"
    SYNTAX      INTEGER
        {
            channelUtilization(1),
            userNumber(2)
        }



-- ==================================================================
-- Major sections
-- ==================================================================
ibDot11WmmCfgGroup OBJECT IDENTIFIER   ::= { ibDot11QoS 1 }
--  Roaming Configuration Group has the following children:
--  ibDot11RadioWmmCfgTable            ::= { ibDot11WmmCfgGroup 1 }
--  ibDot11RadioWmmEdcaCfgTable        ::= { ibDot11WmmCfgGroup 2 }
--  ibDot11StationWmmEdcaTable         ::= { ibDot11WmmCfgGroup 3 }
--  ibDot11WmmResetGroup               ::= { ibDot11WmmCfgGroup 4 }

-- ==================================================================
-- ibDot11WmmCfgGroup Definition
-- ==================================================================
-- ==================================================================
-- ibDot11RadioWmmCfgTable Definition
-- ==================================================================
ibDot11RadioWmmCfgTable OBJECT-TYPE
    SYNTAX      SEQUENCE OF IbDot11RadioWmmCfgEntry
    MAX-ACCESS  not-accessible
    STATUS      current
    DESCRIPTION
        "The table defines the basic parameters for WMM configuration."
    ::= { ibDot11WmmCfgGroup 1 }

ibDot11RadioWmmCfgEntry OBJECT-TYPE
    SYNTAX      IbDot11RadioWmmCfgEntry
    MAX-ACCESS  not-accessible
    STATUS      current
    DESCRIPTION
        "This entry contains the basic information for WMM configuration."
    INDEX
        {
            ibDot11WmmRadioIndex
        }
    ::= { ibDot11RadioWmmCfgTable 1 }

IbDot11RadioWmmCfgEntry ::= SEQUENCE
    {
        ibDot11WmmRadioIndex           IbDot11RadioElementIndex,
        ibDot11RadioWmmEnabled         TruthValue,
        ibDot11RadioSVPMapToAC         IbDot11WMMSVPMapAC,
        ibDot11RadioCacPolicy          IbDot11WMMCACPolicy,
        ibDot11RadioCacChlUtlValue     Integer32,
        ibDot11RadioCacUserNum         Integer32
    }

ibDot11WmmRadioIndex OBJECT-TYPE
    SYNTAX      IbDot11RadioElementIndex
    MAX-ACCESS  not-accessible
    STATUS      current
    DESCRIPTION
        "Represents index of the radio."
    ::= { ibDot11RadioWmmCfgEntry 1 }

ibDot11RadioWmmEnabled OBJECT-TYPE
    SYNTAX      TruthValue
    MAX-ACCESS  read-write
    STATUS      current
    DESCRIPTION
        "Represents the status of WMM in radio.
         'true' : The WMM function is enabled.
         'false': The WMM function is disabled."
    ::= { ibDot11RadioWmmCfgEntry 2 }

ibDot11RadioSVPMapToAC OBJECT-TYPE
    SYNTAX      IbDot11WMMSVPMapAC
    MAX-ACCESS  read-write
    STATUS      current
    DESCRIPTION
        "Represents the AC level which SVP packets are assigned to.
         'acbk'   : Specifies the AC-BK (background traffic) queue.
         'acbe'   : Specifies the AC-BE (best-effort traffic) queue.
         'acvi'   : Specifies the AC-VI (video traffic) queue.
         'acvo'   : Specifies the AC-VO (voice traffic) queue.
         'disable' : Disable SVP packet mapping."
    ::= { ibDot11RadioWmmCfgEntry 3 }

ibDot11RadioCacPolicy OBJECT-TYPE
    SYNTAX      IbDot11WMMCACPolicy
    MAX-ACCESS  read-write
    STATUS      current
    DESCRIPTION
        "Represents the policy for CAC.
         CAC requires that a client obtain permission of the AP before it can
         use a high-priority AC for transmission, thus guaranteeing bandwidth
         to the clients that have gained access.  CAC controls real time traffic
         (AC-VO and AC-VI traffic) but not common data traffic (AC-BE and AC-BK
         traffic)."
    ::= { ibDot11RadioWmmCfgEntry 4 }

ibDot11RadioCacChlUtlValue OBJECT-TYPE
    SYNTAX      Integer32(0..100)
    UNITS       "percent"
    MAX-ACCESS  read-write
    STATUS      current
    DESCRIPTION
        "Represents Maximum channel utilization rate, that is, the medium
         time of the accepted AC-VO traffic and AC-VI traffic to the valid
         time during the unit time.
         This object can be set only if the value of ibDot11RadioCacPolicy is
         ChannelUtilization."
    ::= { ibDot11RadioWmmCfgEntry 5 }

ibDot11RadioCacUserNum OBJECT-TYPE
    SYNTAX      Integer32(0..124)
    MAX-ACCESS  read-write
    STATUS      current
    DESCRIPTION
        "Represents the users-based admission policy for CAC.
         This object can be set only if the value of ibDot11RadioCacPolicy is
         userNumber."
    ::= { ibDot11RadioWmmCfgEntry 6 }

-- ==================================================================
-- ibDot11RadioWmmEdcaCfgTable Definition
-- ==================================================================
ibDot11RadioWmmEdcaCfgTable OBJECT-TYPE
    SYNTAX      SEQUENCE OF IbDot11RadioWmmEdcaCfgEntry
    MAX-ACCESS  not-accessible
    STATUS      current
    DESCRIPTION
        "The table defines the basic parameters for EDCA configuration of
         radio."
    ::= { ibDot11WmmCfgGroup 2 }

ibDot11RadioWmmEdcaCfgEntry OBJECT-TYPE
    SYNTAX      IbDot11RadioWmmEdcaCfgEntry
    MAX-ACCESS  not-accessible
    STATUS      current
    DESCRIPTION
        "This entry contains the basic information for EDCA configuration of
         radio."
    INDEX
        {
            ibDot11WmmRadioIndex,
            ibDot11RadioWmmAC
        }
    ::= { ibDot11RadioWmmEdcaCfgTable 1 }

IbDot11RadioWmmEdcaCfgEntry ::= SEQUENCE
    {
        ibDot11RadioWmmAC          IbDot11QosAcType,
        ibDot11RadioWmmAifsn       Integer32,
        ibDot11RadioWmmEcwMin      Integer32,
        ibDot11RadioWmmEcwMax      Integer32,
        ibDot11RadioWmmTxoplimit   Integer32,
        ibDot11RadioWmmNoAck       TruthValue
    }

ibDot11RadioWmmAC OBJECT-TYPE
    SYNTAX      IbDot11QosAcType
    MAX-ACCESS  not-accessible
    STATUS      current
    DESCRIPTION
        "Represents the AC level index of EDCA parameters of radio.
         'acbk' : Specifies AC-BK (background traffic).
         'acbe' : Specifies AC-BE (best-effort traffic).
         'acvi' : Specifies AC-VI (video traffic).
         'acvo' : Specifies AC-VO (voice traffic)."
    ::= { ibDot11RadioWmmEdcaCfgEntry 1 }

ibDot11RadioWmmAifsn OBJECT-TYPE
    SYNTAX      Integer32(1..15)
    MAX-ACCESS  read-write
    STATUS      current
    DESCRIPTION
        "Represents AIFSN parameter of EDCA.  The value range of this
         object is limited by the radio chip capability."
    ::= { ibDot11RadioWmmEdcaCfgEntry 2 }

ibDot11RadioWmmEcwMin OBJECT-TYPE
    SYNTAX      Integer32(0..15)
    MAX-ACCESS  read-write
    STATUS      current
    DESCRIPTION
        "Represents ECWmin parameter of EDCA.  The value range of this
         object is limited by the radio chip capability.
         ECWmin parameter of EDCA must be smaller than ECWmax parameter."
    ::= { ibDot11RadioWmmEdcaCfgEntry 3 }

ibDot11RadioWmmEcwMax OBJECT-TYPE
    SYNTAX      Integer32(0..15)
    MAX-ACCESS  read-write
    STATUS      current
    DESCRIPTION
        "Represents ECWmax parameter of EDCA.  The value range of this
         object is limited by the radio chip capability.
         ECWmin parameter of EDCA must be larger than ECWmax parameter."
    ::= { ibDot11RadioWmmEdcaCfgEntry 4 }

ibDot11RadioWmmTxoplimit OBJECT-TYPE
    SYNTAX      Integer32(0..65535)
    MAX-ACCESS  read-write
    STATUS      current
    DESCRIPTION
        "Represents TXOPLimit parameter of EDCA, the value must be
         in the range of 0 to 65535 (in units of 32 microseconds).
         The TXOP value of 0 indicates that only one MPDU can be
         transmitted.  The range of this argument is limited by the
         radio chip capability."
    ::= { ibDot11RadioWmmEdcaCfgEntry 5 }

ibDot11RadioWmmNoAck OBJECT-TYPE
    SYNTAX      TruthValue
    MAX-ACCESS  read-write
    STATUS      current
    DESCRIPTION
        "Represents the AC to adopt the No ACK policy.  The protocol
         defines two ACK policies: Normal ACK and No ACK."
    ::= { ibDot11RadioWmmEdcaCfgEntry 6 }

-- ==================================================================
-- ibDot11StationWmmEdcaTable Definition
-- ==================================================================
ibDot11StationWmmEdcaTable OBJECT-TYPE
    SYNTAX      SEQUENCE OF IbDot11StationWmmEdcaEntry
    MAX-ACCESS  not-accessible
    STATUS      current
    DESCRIPTION
        "The table defines the basic parameters for EDCA configuration of
         station."
    ::= { ibDot11WmmCfgGroup 3 }

ibDot11StationWmmEdcaEntry OBJECT-TYPE
    SYNTAX      IbDot11StationWmmEdcaEntry
    MAX-ACCESS  not-accessible
    STATUS      current
    DESCRIPTION
        "This entry contains the basic information for EDCA configuration of
         client.  If CAC is enabled for an AC, CAC is also enabled for ACs with
         higher priority.  For example, if CAC is enabled for AC-VI, CAC
         is also enabled for AC-VO.  However, enabling CAC for AC-VO does
         not enable CAC for AC-VI."
    INDEX
        {
            ibDot11WmmRadioIndex,
            ibDot11StationWmmAC
        }
    ::= { ibDot11StationWmmEdcaTable 1 }

IbDot11StationWmmEdcaEntry ::= SEQUENCE
    {
        ibDot11StationWmmAC            IbDot11QosAcType,
        ibDot11StationWmmAifsn         Integer32,
        ibDot11StationWmmEcwMin        Integer32,
        ibDot11StationWmmEcwMax        Integer32,
        ibDot11StationWmmTxoplimit     Integer32,
        ibDot11StationWmmCacEnabled    TruthValue
    }

ibDot11StationWmmAC OBJECT-TYPE
    SYNTAX      IbDot11QosAcType
    MAX-ACCESS  not-accessible
    STATUS      current
    DESCRIPTION
        "Represents the AC level index of EDCA parameters of client.
         'acbk' : Specifies AC-BK (background traffic).
         'acbe' : Specifies AC-BE (best-effort traffic).
         'acvi' : Specifies AC-VI (video traffic).
         'acvo' : Specifies AC-VO (voice traffic)."
    ::= { ibDot11StationWmmEdcaEntry 1 }

ibDot11StationWmmAifsn OBJECT-TYPE
    SYNTAX      Integer32(2..15)
    MAX-ACCESS  read-write
    STATUS      current
    DESCRIPTION
        "Represents AIFSN parameter of EDCA."
    ::= { ibDot11StationWmmEdcaEntry 2 }

ibDot11StationWmmEcwMin OBJECT-TYPE
    SYNTAX      Integer32(0..15)
    MAX-ACCESS  read-write
    STATUS      current
    DESCRIPTION
        "Represents ECWmin parameter of EDCA."
    ::= { ibDot11StationWmmEdcaEntry 3 }

ibDot11StationWmmEcwMax OBJECT-TYPE
    SYNTAX      Integer32(0..15)
    MAX-ACCESS  read-write
    STATUS      current
    DESCRIPTION
        "Represents ECWmax parameter of EDCA."
    ::= { ibDot11StationWmmEdcaEntry 4 }

ibDot11StationWmmTxoplimit OBJECT-TYPE
    SYNTAX      Integer32(0..65535)
    MAX-ACCESS  read-write
    STATUS      current
    DESCRIPTION
        "Represents TXOPLimit parameter of EDCA, the value is in units of 32
         microseconds.
         The TXOP value of 0 indicates that only one MPDU can be
         transmitted."
    ::= { ibDot11StationWmmEdcaEntry 5 }

ibDot11StationWmmCacEnabled OBJECT-TYPE
    SYNTAX      TruthValue
    MAX-ACCESS  read-write
    STATUS      current
    DESCRIPTION
        "Represents the AC to adopt the No ACK policy.  The protocol
         defines two ACK policies: Normal ACK and No ACK.  Only if
         the value of ibDot11StationWmmAC is 'acvo' or 'acvi', Cac
         can be set correctly here."
    ::= { ibDot11StationWmmEdcaEntry 6 }

-- ==================================================================
-- end of ibDot11StationWmmEdcaTable Definition
-- ==================================================================
ibDot11WmmResetGroup OBJECT IDENTIFIER  ::= { ibDot11WmmCfgGroup 4 }

ibDot11WmmResetRadioByAP OBJECT-TYPE
    SYNTAX      Integer32
    MAX-ACCESS  read-write
    STATUS      current
    DESCRIPTION
        "Clear the WMM statistics information of the radio of the
         specified AP or all radios.
         The meaning of this object is the same as ibDot11APElementIndex,
         it represents the index of AP element.  If the value of this object
         is set to 0xFFFFFFFF, WMM statistics information of all radios
         will be cleared.
         The value of this object is always 0 with the get operation."
    ::= { ibDot11WmmResetGroup 1 }

ibDot11WmmResetStationByAP OBJECT-TYPE
    SYNTAX      Integer32
    MAX-ACCESS  read-write
    STATUS      current
    DESCRIPTION
        "Clear the WMM statistics information of the clients associated
         with the specified AP, or of all clients.
         The meaning of this object is the same as ibDot11APElementIndex,
         it represents the index of AP element.  If set with the
         0xFFFFFFFF, it will clear the WMM statistics information of all
         clients.
         The value of this object is always 0 with the get operation."
    ::= { ibDot11WmmResetGroup 2 }

ibDot11RadioWmmEdcaCfg2Table OBJECT-TYPE
    SYNTAX      SEQUENCE OF IbDot11RadioWmmEdcaCfg2Entry
    MAX-ACCESS  not-accessible
    STATUS      current
    DESCRIPTION
        "The table defines the basic parameters for EDCA configuration of
         radio."
    ::= { ibDot11WmmCfgGroup 5 }

ibDot11RadioWmmEdcaCfg2Entry OBJECT-TYPE
    SYNTAX      IbDot11RadioWmmEdcaCfg2Entry
    MAX-ACCESS  not-accessible
    STATUS      current
    DESCRIPTION
        "This entry contains the basic information for EDCA configuration of
         radio."
    INDEX
        {
            ibDot11WMMAPSerialID,
            ibDot11WMMRdId,
            ibDot11RdWmmAC
        }
    ::= { ibDot11RadioWmmEdcaCfg2Table 1 }

IbDot11RadioWmmEdcaCfg2Entry ::= SEQUENCE
    {
        ibDot11WMMAPSerialID    IbDot11ObjectIDType,
        ibDot11WMMRdId          IbDot11RadioScopeType,
        ibDot11RdWmmAC          IbDot11QosAcType,
        ibDot11RdWmmAifsn       Integer32,
        ibDot11RdWmmEcwMin      Integer32,
        ibDot11RdWmmEcwMax      Integer32,
        ibDot11RdWmmTxoplimit   Integer32
    }

ibDot11WMMAPSerialID OBJECT-TYPE
    SYNTAX      IbDot11ObjectIDType
    MAX-ACCESS  not-accessible
    STATUS      current
    DESCRIPTION
        "Serial ID of the AP."
    ::= { ibDot11RadioWmmEdcaCfg2Entry 1 }

ibDot11WMMRdId OBJECT-TYPE
    SYNTAX      IbDot11RadioScopeType
    MAX-ACCESS  not-accessible
    STATUS      current
    DESCRIPTION
        "radio ID of the radio."
    ::= { ibDot11RadioWmmEdcaCfg2Entry 2 }


ibDot11RdWmmAC OBJECT-TYPE
    SYNTAX      IbDot11QosAcType
    MAX-ACCESS  not-accessible
    STATUS      current
    DESCRIPTION
        "Represents the AC level index of EDCA parameters of radio.
         'acbk' : Specifies AC-BK (background traffic).
         'acbe' : Specifies AC-BE (best-effort traffic).
         'acvi' : Specifies AC-VI (video traffic).
         'acvo' : Specifies AC-VO (voice traffic)."
    ::= { ibDot11RadioWmmEdcaCfg2Entry 3 }

ibDot11RdWmmAifsn OBJECT-TYPE
    SYNTAX      Integer32(1..15)
    MAX-ACCESS  read-write
    STATUS      current
    DESCRIPTION
        "Represents AIFSN parameter of EDCA.  The value range of this
         object is limited by the radio chip capability."
    ::= { ibDot11RadioWmmEdcaCfg2Entry 4 }

ibDot11RdWmmEcwMin OBJECT-TYPE
    SYNTAX      Integer32(0..15)
    MAX-ACCESS  read-write
    STATUS      current
    DESCRIPTION
        "Represents ECWmin parameter of EDCA.  The value range of this
         object is limited by the radio chip capability.
         ECWmin parameter of EDCA must be smaller than ECWmax parameter."
    ::= { ibDot11RadioWmmEdcaCfg2Entry 5 }

ibDot11RdWmmEcwMax OBJECT-TYPE
    SYNTAX      Integer32(0..15)
    MAX-ACCESS  read-write
    STATUS      current
    DESCRIPTION
        "Represents ECWmax parameter of EDCA.  The value range of this
         object is limited by the radio chip capability.
         ECWmin parameter of EDCA must be larger than ECWmax parameter."
    ::= { ibDot11RadioWmmEdcaCfg2Entry 6 }

ibDot11RdWmmTxoplimit OBJECT-TYPE
    SYNTAX      Integer32(0..65535)
    MAX-ACCESS  read-write
    STATUS      current
    DESCRIPTION
        "Represents TXOPLimit parameter of EDCA, the value must be
         in the range of 0 to 65535 (in units of 32 microseconds).
         The TXOP value of 0 indicates that only one MPDU can be
         transmitted.  The range of this argument is limited by the
         radio chip capability."
    ::= { ibDot11RadioWmmEdcaCfg2Entry 7 }

END
