-- =================================================================
-- Copyright (C) 2023 Intelbras S.A. All rights reserved.
--
-- Description:protocol vlan mib
-- Reference:IEEE 802.1v clause 8.6.4
-- Version: V1.4
-- History:
--     V1.0 Initial version 2004-08-18
--     V1.1 Updated version 2004-08-31
--     V1.2 2004-10-12 updated by gaolong
--          Change value of IbvProtocolVlanProtocolType from underscores to hyphens.
--          Remove ibProtocolVlanVlanId, ibProtocolVlanProtocolIndex from ibProtocolVlanProtocolGroup
--          because they are not-accessible objects.
--          Remove ibProtocolVlanPortIndex, ibProtocolVlanPortVlanId, ibProtocolVlanPortProtocolId
--          from ibProtocolVlanPortGroup because they are not-accessible objects.
--     V1.3 2005-08-31 updated by jiangjun
--          Add ibDifferentProtocolNumAllPort object to support the maximum
--          number of different protocols that can be applied on all ports.
--          Add enum value (ipv6) to IbvProtocolVlanProtocolType.
--          Update file format by gaolong.
--     V1.4 2013-04-23 updated by yangxiaoren
--          Add ibProtocolVlanPortStatus object to support the protocol VLAN
--          status of port applied.
--          Add enum value notConfigured(201) to ibvProtocolVlanProtocolType.
-- =================================================================
IB-PROTOCOL-VLAN-MIB DEFINITIONS ::= BEGIN

    IMPORTS
        ibCommon
            FROM IB-OID-MIB
        OBJECT-GROUP, MODULE-COMPLIANCE
            FROM SNMPv2-CONF
        Integer32, OBJECT-TYPE, MODULE-IDENTITY
            FROM SNMPv2-SMI
        RowStatus, TEXTUAL-CONVENTION
            FROM SNMPv2-TC;


    ibProtocolVlan MODULE-IDENTITY
        LAST-UPDATED "200408311800Z"
        ORGANIZATION
            "Intelbras S.A. Industria de Telecomunicacao Eletronica Brasileria."
        CONTACT-INFO
            ""
        DESCRIPTION
            "This MIB contains the objects for managing the protocol-based
             VLAN configurations."
        REVISION "200408311938Z"        -- August 31, 2004 at 19:38 GMT
        DESCRIPTION
            "The initial revision of this MIB module ."
        ::= { ibCommon 16 }

--
-- Textual conventions
--

    IbvProtocolVlanProtocolType ::= TEXTUAL-CONVENTION
        STATUS current
        DESCRIPTION
            "
            Contains protocols both for Layer 3 and Layer 2.
            "
        SYNTAX INTEGER
        {
            -- Layer 3 protocols
            ip(1),
            ipx(2),
            at(3),
            ipv6(4),

            -- Layer 2 protocols
            mode-llc(101),
            mode-snap(102),
            mode-ethernetii(103),

            -- Protocol no configure
            notConfigure(201)
        }

    IbvProtocolVlanProtocolSubType ::= TEXTUAL-CONVENTION
        STATUS current
        DESCRIPTION
            "
            combine with IbvProtocolVlanProtocolType.

            ethernetii(2), llc(3), raw(4), snap(5) are used when the value
            of IbvProtocolVlanProtocolType is for Layer 3 protocols.
            etype(6) is used when the value of IbvProtocolVlanProtocolType
            is for Layer 2 protocols.
            For detailed information, see the DESCRIPTION part of
            ibProtocolVlanProtocolTypeValue.
            "
        SYNTAX INTEGER
        {
            notused(1),        -- this value indicates the object is not used.

            ethernetii(2),
            llc(3),
            raw(4),
            snap(5),

            etype(6)
        }

--
-- Node definitions
--

    ibProtocolVlanOperate OBJECT IDENTIFIER ::= { ibProtocolVlan 1 }


    ibProtocolNumAllVlan OBJECT-TYPE
        SYNTAX Integer32
        MAX-ACCESS read-only
        STATUS current
        DESCRIPTION
            "The maximum number of protocols that can be configured on all VLANs.
            This number may vary with products."
        ::= { ibProtocolVlanOperate 1 }

    ibProtocolNumPerVlan OBJECT-TYPE
        SYNTAX Integer32
        MAX-ACCESS read-only
        STATUS current
        DESCRIPTION
            "The maximum number of protocols that can be configured per VLAN.
            This number may vary with products."

        ::= { ibProtocolVlanOperate 2 }

    ibProtocolNumAllPort OBJECT-TYPE
        SYNTAX Integer32
        MAX-ACCESS read-only
        STATUS current
        DESCRIPTION
            "The maximum number of protocols that can be applied on all ports.
            This number may vary with products."
        ::= { ibProtocolVlanOperate 3 }

    ibProtocolNumPerPort OBJECT-TYPE
        SYNTAX Integer32
        MAX-ACCESS read-only
        STATUS current
        DESCRIPTION
            "The maximum number of protocols that can be applied to each port.
            This number may vary with products."
        ::= { ibProtocolVlanOperate 4 }

    ibProtocolVlanTable OBJECT-TYPE
        SYNTAX SEQUENCE OF IbProtocolVlanEntry
        MAX-ACCESS not-accessible
        STATUS current
        DESCRIPTION
            "Protocol-based VLAN configuration table."
        ::= { ibProtocolVlanOperate 5 }

    ibProtocolVlanEntry OBJECT-TYPE
        SYNTAX IbProtocolVlanEntry
        MAX-ACCESS not-accessible
        STATUS current
        DESCRIPTION
            "Protocol-based VLAN configuration entry."
        INDEX { ibProtocolVlanVlanId, ibProtocolVlanProtocolIndex }
        ::= { ibProtocolVlanTable 1 }

    IbProtocolVlanEntry ::=
        SEQUENCE {
            ibProtocolVlanVlanId
                Integer32,
            ibProtocolVlanProtocolIndex
                Integer32,
            ibProtocolVlanProtocolType
                IbvProtocolVlanProtocolType,
            ibProtocolVlanProtocolSubType
                IbvProtocolVlanProtocolSubType,
            ibProtocolVlanProtocolTypeValue
                OCTET STRING,
            ibProtocolVlanRowStatus
                RowStatus
         }

    ibProtocolVlanVlanId OBJECT-TYPE
        SYNTAX Integer32
        MAX-ACCESS not-accessible
        STATUS current
        DESCRIPTION
            "Vlan ID."
        ::= { ibProtocolVlanEntry 1 }

    ibProtocolVlanProtocolIndex OBJECT-TYPE
        SYNTAX Integer32
        MAX-ACCESS not-accessible
        STATUS current
        DESCRIPTION
            "The protocol index value of a row in this table is in the range
            of [0..ibProtocolNumPerVlan-1].
            This object may not be provided during creation. In this case,
            a number is assigned by system automatically."
        ::= { ibProtocolVlanEntry 2 }

    ibProtocolVlanProtocolType OBJECT-TYPE
        SYNTAX IbvProtocolVlanProtocolType
        MAX-ACCESS read-create
        STATUS current
        DESCRIPTION
            "
            Specify protocol types supported by a protocol-based VLAN.
            Now protocols supported on Layer 3 include ip, ipx, at, ipv6, etc.
            Now protocols supported on Layer 2 include llc, snap, ethernetii, etc.

            For detailed information, see description of
            ibProtocolVlanProtocolTypeValue.
            "
        ::= { ibProtocolVlanEntry 3 }

    ibProtocolVlanProtocolSubType OBJECT-TYPE
        SYNTAX IbvProtocolVlanProtocolSubType
        MAX-ACCESS read-create
        STATUS current
        DESCRIPTION
            "
            See description of ibProtocolVlanProtocolTypeValue.
            "
        ::= { ibProtocolVlanEntry 4 }

    ibProtocolVlanProtocolTypeValue OBJECT-TYPE
        SYNTAX OCTET STRING(SIZE(0..255))
        MAX-ACCESS read-create
        STATUS current
        DESCRIPTION
            "
            The value of the configured protocol type.
            By default, semicolon(;) is used as a separator between different
            parts in the content of the object.

            The relationship among ibProtocolVlanProtocolType, ibProtocolVlanProtocolSubType
            and ibProtocolVlanProtocolTypeValue is as follows:

            |----------------------------------------------------------------------------------------------|
            | ibProtocolVlan- | ibProtocolVlan- | ibProtocolVlanProtocolTypeValue                    |
            | ProtocolType      | ProtocolSubType   |                                                      |
            |-------------------|-------------------|------------------------------------------------------|
            | ip                | notused           | notused for create operation                         |
            |-------------------|-------------------|------------------------------------------------------|
            | ipv6              | notused           | notused for create operation                         |
            |-------------------|-------------------|------------------------------------------------------|
            | at                | notused           | notused for create operation                         |
            |-------------------|-------------------|------------------------------------------------------|
            | ipx               | ethernetii        | notused for create operation
            |                   | llc               |                                                      |
            |                   | raw               |                                                      |
            |                   | snap              |                                                      |
            |-------------------|-------------------|------------------------------------------------------|
            | mode-snap         | etype             | hex string like '600', which means 0x0600.           |
            |                   |                   | The range is [0x600..0xffff]                         |
            |-------------------|-------------------|------------------------------------------------------|
            | mode-ethernetii   | etype             | hex string like '600', which means 0x0600.           |
            |                   |                   | The range is [0x600..0xffff]                         |
            |-------------------|-------------------|------------------------------------------------------|
            | mode-llc          | notused           | the sequence of different parts is as follows.       |
            |                   |                   | [dsap value][;ssap value][dsap value;ssap value]     |
            |                   |                   | Both range is [0x00..0xff]                           |
            |                   |                   |                                                      |
            |                   |                   | For example. Suppose value of dsap and ssap are 0x09 |
            |                   |                   | and 0x0a.                                            |
            |                   |                   | If neither dsap or ssap, the string length is zero.  |
            |                   |                   | If dsap provided, the string is '09;' or '09'        |
            |                   |                   | If ssap provided, the value is ';0a'                 |
            |                   |                   | If dsap and ssap provided, the value is '09;0a'      |
            |-------------------|-------------------|------------------------------------------------------|
            "
        ::= { ibProtocolVlanEntry 5 }

    ibProtocolVlanRowStatus OBJECT-TYPE
        SYNTAX RowStatus
        MAX-ACCESS read-create
        STATUS current
        DESCRIPTION
            "The row status of this table."
        ::= { ibProtocolVlanEntry 6 }

    ibProtocolVlanPortTable OBJECT-TYPE
        SYNTAX SEQUENCE OF IbProtocolVlanPortEntry
        MAX-ACCESS not-accessible
        STATUS current
        DESCRIPTION
            "Protocol-based VLAN port information table."
        ::= { ibProtocolVlanOperate 6 }

    ibProtocolVlanPortEntry OBJECT-TYPE
        SYNTAX IbProtocolVlanPortEntry
        MAX-ACCESS not-accessible
        STATUS current
        DESCRIPTION
            "Protocol-based VLAN port information entry."
        INDEX { ibProtocolVlanPortIndex, ibProtocolVlanPortVlanId,
                ibProtocolVlanPortProtocolId }
        ::= { ibProtocolVlanPortTable 1 }

    IbProtocolVlanPortEntry ::=
        SEQUENCE {
            ibProtocolVlanPortIndex
                Integer32,
            ibProtocolVlanPortVlanId
                Integer32,
            ibProtocolVlanPortProtocolId
                Integer32,
            ibProtocolVlanPortProtocolType
                IbvProtocolVlanProtocolType,
            ibProtocolVlanPortProtocolSubType
                IbvProtocolVlanProtocolSubType,
            ibProtocolVlanPortTypeValue
                OCTET STRING,
            ibProtocolVlanPortRowStatus
                RowStatus,
            ibProtocolVlanPortStatus
                INTEGER
         }

    ibProtocolVlanPortIndex OBJECT-TYPE
        SYNTAX Integer32
        MAX-ACCESS not-accessible
        STATUS current
        DESCRIPTION
            "
            The maximum number is the total number of ports supported by device.
            "
        REFERENCE
            "ibLswPortIndex in IB-LSW-DEV-ADM-MIB"
        ::= { ibProtocolVlanPortEntry 1 }

    ibProtocolVlanPortVlanId OBJECT-TYPE
        SYNTAX Integer32
        MAX-ACCESS not-accessible
        STATUS current
        DESCRIPTION
            "The protocol-based VLAN ID."
        ::= { ibProtocolVlanPortEntry 2 }

    ibProtocolVlanPortProtocolId OBJECT-TYPE
        SYNTAX Integer32
        MAX-ACCESS not-accessible
        STATUS current
        DESCRIPTION
            "The protocol index."
        ::= { ibProtocolVlanPortEntry 3 }

    ibProtocolVlanPortProtocolType OBJECT-TYPE
        SYNTAX IbvProtocolVlanProtocolType
        MAX-ACCESS read-only
        STATUS current
        DESCRIPTION
            "See the description of ibProtocolVlanProtocolType."
        ::= { ibProtocolVlanPortEntry 4 }

    ibProtocolVlanPortProtocolSubType OBJECT-TYPE
        SYNTAX IbvProtocolVlanProtocolSubType
        MAX-ACCESS read-only
        STATUS current
        DESCRIPTION
            "See the description of ibProtocolVlanProtocolSubType."
        ::= { ibProtocolVlanPortEntry 5 }

    ibProtocolVlanPortTypeValue OBJECT-TYPE
        SYNTAX OCTET STRING
        MAX-ACCESS read-only
        STATUS current
        DESCRIPTION
            "See the description of ibProtocolVlanProtocolTypeValue."
        ::= { ibProtocolVlanPortEntry 6 }

    ibProtocolVlanPortRowStatus OBJECT-TYPE
        SYNTAX RowStatus
        MAX-ACCESS read-create
        STATUS current
        DESCRIPTION
            "The row status of this table."
        ::= { ibProtocolVlanPortEntry 7 }

    ibProtocolVlanPortStatus OBJECT-TYPE
        SYNTAX  INTEGER
        {
            active   (1),
            inactive (2)
        }
        MAX-ACCESS read-only
        STATUS current
        DESCRIPTION
            "The protocol VLAN status on the port.  The value is active only
            when ibProtocolVlanPortProtocolId has the corresponding entry in
            ibProtocolVlanTable, the port link type is hybrid, and the VLAN is
            allowed by the port.

            active:   protocol VLAN has been applied on the port.
            inactive: protocol VLAN is not applied on the port."
        ::= { ibProtocolVlanPortEntry 8 }

    ibDifferentProtocolNumAllPort OBJECT-TYPE
        SYNTAX Integer32
        MAX-ACCESS read-only
        STATUS current
        DESCRIPTION
            "The maximum number of different protocols that can be applied to all ports."
        ::= { ibProtocolVlanOperate 7 }

    ibProtocolVlanConformance OBJECT IDENTIFIER ::= { ibProtocolVlan 2 }


    ibProtocolVlanCompliances OBJECT IDENTIFIER ::= { ibProtocolVlanConformance 1 }


    ibProtocolVlanCompliance MODULE-COMPLIANCE
        STATUS current
        DESCRIPTION
            "The compliance statement for protocol VLAN MIB."
        MODULE -- this module
        MANDATORY-GROUPS {  ibProtocolVlanOperateGroup,
                            ibProtocolVlanProtocolGroup,
                            ibProtocolVlanPortGroup
                         }
        ::= { ibProtocolVlanCompliances 1 }


    ibProtocolVlanGroups OBJECT IDENTIFIER ::= { ibProtocolVlanConformance 2 }

    ibProtocolVlanOperateGroup OBJECT-GROUP
        OBJECTS { ibProtocolNumAllVlan, ibProtocolNumPerVlan,
                  ibProtocolNumAllPort, ibProtocolNumPerPort,
                  ibDifferentProtocolNumAllPort
                }
        STATUS current
        DESCRIPTION
            "A group of scalar objects describing the maximum number."
        ::= { ibProtocolVlanGroups 1 }

    ibProtocolVlanProtocolGroup OBJECT-GROUP
        OBJECTS { ibProtocolVlanProtocolType, ibProtocolVlanProtocolSubType,
                  ibProtocolVlanProtocolTypeValue, ibProtocolVlanRowStatus
                }
        STATUS current
        DESCRIPTION
            "A group of protocol VLAN protocol."
        ::= { ibProtocolVlanGroups 2 }

    ibProtocolVlanPortGroup OBJECT-GROUP
        OBJECTS { ibProtocolVlanPortProtocolType, ibProtocolVlanPortProtocolSubType,
                  ibProtocolVlanPortTypeValue, ibProtocolVlanPortRowStatus
                }
        STATUS current
        DESCRIPTION
            "A group of protocol VLAN port."
        ::= { ibProtocolVlanGroups 3 }

END
