-- =================================================================
-- Copyright (C) 2023 Intelbras S.A. All rights reserved.
--
-- Description: description of entity extend properties.
-- Reference:
-- History V3.6
-- V1.0 Created by weixinzhe, Thursday, April 22, 2004 at 18:26:02
-- V1.1 modified by yelinhui, add ibEntityExtMacAddress
-- V1.2 modified by panxidong, add ibEntityExtErrorStatus
-- V1.3 2004-10-12 updated by gaolong
--      Remove BITS from IMPORTS
-- V1.4 2005-02-25 modified by longyin
--      Add error status stackPortBlocked(22) and stackPortFailed(23)
--      for ibEntityExtErrorStatus
-- V1.5 2006-05-16 modified by wangsihai
--      Add error status sensorError(81) in ibEntityExtErrorStatus
-- V1.6 2006-07-03 modified by lifengguang
--      Add ibEntityExtManuTable
-- V1.7 2007-09-21 modified by lifengguang
--      Add notification object ibEntityExtSFPAlarmOn and ibEntityExtSFPAlarmOff
--      Add ibEntityExtPowerTable
-- V1.8 2007-11-19 modified by jinyi
--      Add ibEntityExtCpuMaxUsage
-- V1.9 2008-02-27 modified by lifengguang
--      Add Trap nodes: ibEntityExtSFPPhony
-- V2.0 2008-07-11 modified by lisong
--      Add ibProcessTable
--      Add notification object ibEntityInsert and ibEntityRemove
-- V2.1 2008-07-14 modified by lifengguang
--      Add error status hardwareFaulty(91) in ibEntityExtErrorStatus
--      Add Trap nodes: ibEntityExtForcedPowerOff and ibEntityExtForcedPowerOn
--      Add Trap nodes: ibEntityExtFaultAlarmOn and ibEntityExtFaultAlarmOff
-- V2.2 2008-10-24 modified by lifengguang
--      Add nodes ibEntityExtLowerTemperatureThreshold and
--      ibEntityExtShutdownTemperatureThreshold in ibEntityExtStateTable
--      Add trap nodes ibEntityExtResourceLack and ibEntityExtResourceEnough
--      in ibEntityExtTrapsPrefix
--      Add trap nodes ibEntityExtTemperatureLower, ibEntityExtTemperatureTooUp
--      and ibEntityExtTemperatureNormal in ibEntityExtTrapsPrefix
-- V2.3 2009-04-07 Added trap nodes ibEntityExternalAlarmOccur and
--      ibEntityExternalAlarmRecover
-- v2.4 2009-05-05 Added ibEntityExtCpuAvgUsage, ibEntityExtMemAvgUsage,
--      ibEntityExtPhyMemSize, ibEntityExtMemType, ibEntityExtPhyCpuFrequency,
--      ibEntityExtFirstUsedDate,
--      ibEntityExtCpuUsageThresholdRecover, ibEntityExtMemUsageThresholdRecover
-- V2.5 2010-08-09
--      Added ibEntityExtShutdownLowerTemperatureThreshold,
--      ibEntityExtCriticalLowerTemperatureThreshold,
--      ibEntityExtCritLowerTempThresholdNotification and
--      ibEntityExtTemperatureTooLow by zhanglei 06807.
--      Added ibEntityExtMemAllocatedFailed, ibEntityExtECCParityAlarm,
--      ibEntityExtTrapDescription, ibEntityExtECCParityAlarmStatus
--      by zhangqingjun 02357.
--      Modified description of ibEntityExtPhyMemSize by haoyan 06611.
-- V2.6 2010-12-06
--      Added ibEntityExtFanDirectionNotPreferred, ibEntityExtFanDirectionNotAccord
--      by lifengguang 03035.
-- V2.7 2011-04-06
--      Added ibEntityExtSFPInvalid, ibEntityExtSFPInvalidNow and
--      ibEntityExtSFPInvalidInDays by songhao 02718.
--      Changed SYNTAX of ibEntityExtMemSize and ibEntityExtPhyMemSize
--      from Integer32 to Unsigned32 by songhao 02718.
-- V2.8 2011-08-30
--      Added ibEntityExtCpuUsageRecoverThreshold;
--      Added ibEntityExtCpuUsageRecoverThreshold to ibEntityExtCpuUsageThresholdNotfication and
--      ibEntityExtCpuUsageThresholdRecover by shuaixiaojuan 04117.
--      Added ibEntityExtFirstTrapTime by duyanbing 04404.
-- V2.9 2013-04-27
--      Added ibEntityExtMemSizeRev by fangliwen 08502.
--      Added trap nodes ibEntityExtMemUsageThresholdOverTrap and
--      ibEntityExtMemUsageThresholdRecoverTrap by fangliwen 08502.
-- V3.0 2013-12-16
--      Added ibEntityExtCpuUsageIn1Minute and ibEntityExtCpuUsageIn5Minutes
--      by fangliwen 08502.
-- V3.1 2014-01-24
--      Added ibEntityExtVoltageObjects by fangliwen 08502.
--      Added trap nodes ibEntityExtVoltageNormal, ibEntityExtVoltageTooLow,
--      ibEntityExtVoltageLower, ibEntityExtVoltageHigher and
--      ibEntityExtVoltageTooHigh by fangliwen 08502.
-- V3.2 2015-01-12
--      Added trap nodes ibEntityExtSFPAlarmOnEx, ibEntityExtSFPAlarmOffEx by fangliwen 08502.
-- V3.3 2021-06-05
--      Added trap nodes ibEntityExtRasTraps  by duyanbing 04404.
-- V3.4 2021-10-12
--      Added the item nearThresholdError to ibEntityExtErrorStatus by hezheng 22749
-- V3.5 2022-11-23
--      Added error status sfpRecvExceedUpperLimit(34), sfpRecvBelowLowerLimit(35),
--      sfpSendExceedUpperLimit(36), sfpSendBelowLowerLimit(37) to ibEntityExtErrorStatus by hezheng 22749
-- V3.6 2022-12-13
--      Added ibEntityExtRelativeLocation and ibEntityExtServiceName by yuhaiyan 04822.
--      Added trap node ibEntityExtBoardServiceMisMatch by yuhaiyan 04822.
-- =================================================================
IB-ENTITY-EXT-MIB DEFINITIONS ::= BEGIN

    IMPORTS
        ibCommon
            FROM IB-OID-MIB
        OBJECT-GROUP, MODULE-COMPLIANCE, NOTIFICATION-GROUP
            FROM SNMPv2-CONF
        OBJECT-TYPE, MODULE-IDENTITY, NOTIFICATION-TYPE, Integer32,
        Unsigned32, Gauge32, TimeTicks
            FROM SNMPv2-SMI
        TEXTUAL-CONVENTION, MacAddress, DateAndTime, DisplayString
            FROM SNMPv2-TC
        SnmpAdminString
            FROM SNMP-FRAMEWORK-MIB
        entPhysicalIndex, entPhysicalName, entPhysicalDescr
            FROM ENTITY-MIB
        CounterBasedGauge64
            FROM HCNUM-TC;

    ibEntityExtend MODULE-IDENTITY
        LAST-UPDATED "202212130000Z"
        ORGANIZATION
            "Intelbras S.A. Industria de Telecomunicacao Eletronica Brasileria."
        CONTACT-INFO
            ""
        DESCRIPTION
            "The private MIB file includes the general extent
            information of the device."
        REVISION "202212130000Z"
        DESCRIPTION
            "Added ibEntityExtRelativeLocation and ibEntityExtServiceName.
            Added trap node ibEntityExtBoardServiceMisMatch."
        REVISION "202211230000Z"
        DESCRIPTION
            "Added error status sfpRecvExceedUpperLimit(34), sfpRecvBelowLowerLimit(35),
             sfpSendExceedUpperLimit(36), sfpSendBelowLowerLimit(37) to ibEntityExtErrorStatus."
        REVISION "202110120000Z"
        DESCRIPTION
            "Added the item nearThresholdError to ibEntityExtErrorStatus."
        REVISION "202106050000Z"
        DESCRIPTION
            "Added trap nodes ibEntityExtRasTraps."
        REVISION "200404220000Z"
        DESCRIPTION
            "The private MIB file includes the general extent
            information of the device."
        ::= { ibCommon 6 }

    IbAdminState  ::=  TEXTUAL-CONVENTION
        STATUS            current
        DESCRIPTION
            "The administrative state for this object, and it is possible to
            set the state when needed.
            A value of locked means the resource is administratively prohibited
            from use. A value of shuttingDown means that usage is
            administratively limited to current instances of use.
            A value of unlocked means the resource is not administratively
            prohibited from use."
        REFERENCE
            "ITU Recommendation X.731, 'Information Technology - Open
            Systems Interconnection - System Management: State
            Management Function', 1992"
        SYNTAX  INTEGER
        {
            notSupported(1),
            locked(2),
            shuttingDown(3),
            unlocked(4)
        }

    IbOperState  ::=  TEXTUAL-CONVENTION
        STATUS            current
        DESCRIPTION
            " Represents the possible values of operational states.
            A value of disabled means the resource is totally
            inoperable. A value of enabled means the resource
            is partially or fully operable."
        REFERENCE
            "ITU Recommendation X.731, 'Information Technology - Open
            Systems Interconnection - System Management: State
            Management Function', 1992"
        SYNTAX  INTEGER
        {
            notSupported (1),
            disabled(2),
            enabled(3),
            dangerous(4)
        }
    IbAlarmStatus  ::=  TEXTUAL-CONVENTION
        STATUS            current
        DESCRIPTION
            "Represents the possible values of alarm status.
            When no bits of this attribute are set, then none of the
            status conditions described below are present. When the
            value of under repair is set, the resource is currently
            being repaired.

            When the value of critical is set, one or more critical
            alarms are active against the resource. When the value of
            major is set, one or more major alarms are active against
            the resource. When the value of minor is set, one or more
            minor alarms are active against the resource. When the
            value of warning is set, one or more warning alarms are
            active against the resource. When the value of
            indeterminate is set, one or more  alarms of indeterminate
            severity are active against the resource.
            When the value of alarm outstanding is set, one or more
            alarms is active against the resource. The fault may or may
            not be disabling."
            REFERENCE
            "ITU Recommendation X.731, 'Information Technology - Open
            Systems Interconnection - System Management: State
            Management Function', 1992"
        SYNTAX           BITS
        {
            notSupported (0),
            underRepair(1),
            critical(2),
            major(3),
            minor(4),
            alarmOutstanding(5),
            warning (6), -- Not defined in X.731
            indeterminate (7) -- Not defined in X.731
        }


    IbStandbyStatus  ::=  TEXTUAL-CONVENTION
        STATUS            current
        DESCRIPTION
                " Represents the possible values of standby status.

                  A value of hotStandby means the resource is not providing
                  service, but is will be immediately able to take over the
                  role of the resource to be backed-up, without the need for
                  initialization activity, and will contain the same
                  information as the resource to be backed up. A value of
                  coldStandy means that the resource is to back-up another
                  resource, but will not be immediately able to take over
                  the role of a resource to be backed up, and will require
                  some initialization activity. A value of providingService
                  means the resource is providing service."
        REFERENCE
            "ITU Recommendation X.731, 'Information Technology - Open
            Systems Interconnection - System Management: State
            Management Function', 1992"
        SYNTAX            INTEGER
        {
            notSupported (1),
            hotStandby(2),
            coldStandby(3),
            providingService(4)
        }


    ibEntityExtObjects OBJECT IDENTIFIER ::= { ibEntityExtend 1 }


--  MIB contains four groups

    ibEntityExtState OBJECT IDENTIFIER ::= { ibEntityExtObjects 1 }

    ibEntityExtStateTable OBJECT-TYPE
        SYNTAX SEQUENCE OF IbEntityExtStateEntry
        MAX-ACCESS not-accessible
        STATUS current
        DESCRIPTION
            "This table contains one row per physical entity, There is
            always at least one row for an 'overall' physical entity.
            The information in each row may be not include all the object
            in this table, because of the entity need not some of the
            information here."
        ::= { ibEntityExtState 1 }

    ibEntityExtStateEntry OBJECT-TYPE
        SYNTAX IbEntityExtStateEntry
        MAX-ACCESS not-accessible
        STATUS current
        DESCRIPTION
            "The information about a particular physical entity."
        INDEX { ibEntityExtPhysicalIndex }
        ::= { ibEntityExtStateTable 1 }

    IbEntityExtStateEntry ::= SEQUENCE {
        ibEntityExtPhysicalIndex
            Integer32,
        ibEntityExtAdminStatus
            IbAdminState,
        ibEntityExtOperStatus
            IbOperState,
        ibEntityExtStandbyStatus
            IbStandbyStatus,
        ibEntityExtAlarmLight
            IbAlarmStatus,
        ibEntityExtCpuUsage
            Integer32,
        ibEntityExtCpuUsageThreshold
            Integer32,
        ibEntityExtMemUsage
            Integer32,
        ibEntityExtMemUsageThreshold
            Integer32,
        ibEntityExtMemSize
            Unsigned32,
        ibEntityExtUpTime
            Integer32,
        ibEntityExtTemperature
            Integer32,
        ibEntityExtTemperatureThreshold
            Integer32,
        ibEntityExtVoltage
            Integer32,
        ibEntityExtVoltageLowThreshold
            Integer32,
        ibEntityExtVoltageHighThreshold
            Integer32,
        ibEntityExtCriticalTemperatureThreshold
            Integer32,
        ibEntityExtMacAddress
            MacAddress,
        ibEntityExtErrorStatus
            INTEGER,
        ibEntityExtCpuMaxUsage
            Integer32,
        ibEntityExtLowerTemperatureThreshold
            Integer32,
        ibEntityExtShutdownTemperatureThreshold
            Integer32,
        ibEntityExtPhyMemSize
            Unsigned32,
        ibEntityExtPhyCpuFrequency
            Integer32,
        ibEntityExtFirstUsedDate
            DateAndTime,
        ibEntityExtCpuAvgUsage
            Integer32,
        ibEntityExtMemAvgUsage
            Integer32,
        ibEntityExtMemType
            OCTET STRING,
        ibEntityExtCriticalLowerTemperatureThreshold
            Integer32,
        ibEntityExtShutdownLowerTemperatureThreshold
            Integer32,
        ibEntityExtCpuUsageRecoverThreshold
            Integer32,
        ibEntityExtMemSizeRev
            CounterBasedGauge64,
        ibEntityExtCpuUsageIn1Minute
            Integer32,
        ibEntityExtCpuUsageIn5Minutes
            Integer32
     }

    ibEntityExtPhysicalIndex OBJECT-TYPE
        SYNTAX Integer32
        MAX-ACCESS accessible-for-notify
        STATUS current
        DESCRIPTION
            "The index of ibEntityExtStateTable.
            This index is identical to entPhysicalIndex in ENTITY-MIB"
        ::= { ibEntityExtStateEntry 1 }

    ibEntityExtAdminStatus OBJECT-TYPE
        SYNTAX IbAdminState
        MAX-ACCESS read-write
        STATUS current
        DESCRIPTION
            "The administrative state for this object."
        ::= { ibEntityExtStateEntry 2 }

    ibEntityExtOperStatus OBJECT-TYPE
        SYNTAX IbOperState
        MAX-ACCESS read-only
        STATUS current
        DESCRIPTION
            "The operate state for this object."
        ::= { ibEntityExtStateEntry 3 }

    ibEntityExtStandbyStatus OBJECT-TYPE
        SYNTAX IbStandbyStatus
        MAX-ACCESS read-only
        STATUS current
        DESCRIPTION
            "This object is used for monitoring standby status.
            Not all entities support this object."
        ::= { ibEntityExtStateEntry 4 }

    ibEntityExtAlarmLight OBJECT-TYPE
        SYNTAX IbAlarmStatus
        MAX-ACCESS read-only
        STATUS current
        DESCRIPTION
            "The alarm status for this entity. It does not include
            the severity of alarms raised on child components. In
            this condition, there will be a alarm light on the entity,
            the object should have the same status with it."
        ::= { ibEntityExtStateEntry 5 }

    ibEntityExtCpuUsage OBJECT-TYPE
        SYNTAX Integer32 (0..100)
        MAX-ACCESS read-only
        STATUS current
        DESCRIPTION
            "The CPU usage for this entity. Generally, the overall
            CPU usage on the entity is calculated, independent of
            the number of CPUs on the entity."
        ::= { ibEntityExtStateEntry 6 }

    ibEntityExtCpuUsageThreshold OBJECT-TYPE
        SYNTAX Integer32 (0..100)
        MAX-ACCESS read-write
        STATUS current
        DESCRIPTION
            "The threshold for the CPU usage. When the CPU usage exceeds
            the threshold, a notification will be sent."
        ::= { ibEntityExtStateEntry 7 }

    ibEntityExtMemUsage OBJECT-TYPE
        SYNTAX Integer32 (0..100)
        MAX-ACCESS read-only
        STATUS current
        DESCRIPTION
            "The memory usage for the entity. This object indicates what
            percent of memory are used."
        ::= { ibEntityExtStateEntry 8 }

    ibEntityExtMemUsageThreshold OBJECT-TYPE
        SYNTAX Integer32 (0..100)
        MAX-ACCESS read-write
        STATUS current
        DESCRIPTION
            "The threshold for the Memory usage, When the memory usage
            exceeds the threshold, a notification will be sent."
        ::= { ibEntityExtStateEntry 9 }

    ibEntityExtMemSize OBJECT-TYPE
        SYNTAX Unsigned32
        UNITS "bytes"
        MAX-ACCESS read-only
        STATUS current
        DESCRIPTION
            "The size of memory for the entity.

            If the amount of memory exceeds 4,294,967,295 bytes,
            the value remains 4,294,967,295 bytes."
        ::= { ibEntityExtStateEntry 10 }

    ibEntityExtUpTime OBJECT-TYPE
        SYNTAX Integer32
        UNITS "seconds"
        MAX-ACCESS read-only
        STATUS current
        DESCRIPTION
            "The uptime for the entity. The meaning of uptime is
            when the entity is up, and the value of the object
            will add 1 seconds while the entity is running."
        ::= { ibEntityExtStateEntry 11 }

    ibEntityExtTemperature OBJECT-TYPE
        SYNTAX Integer32
        MAX-ACCESS read-only
        STATUS current
        DESCRIPTION
            "The temperature for the entity."
        ::= { ibEntityExtStateEntry 12 }

    ibEntityExtTemperatureThreshold OBJECT-TYPE
        SYNTAX Integer32
        MAX-ACCESS read-write
        STATUS current
        DESCRIPTION
            "The threshold for the temperature. When the temperature
            exceeds the threshold, a notification will be sent."
        ::= { ibEntityExtStateEntry 13 }

    ibEntityExtVoltage OBJECT-TYPE
        SYNTAX Integer32
        MAX-ACCESS read-only
        STATUS current
        DESCRIPTION
            "The voltage for the entity."
        ::= { ibEntityExtStateEntry 14 }

    ibEntityExtVoltageLowThreshold OBJECT-TYPE
        SYNTAX Integer32
        MAX-ACCESS read-write
        STATUS current
        DESCRIPTION
            "The low-threshold for the voltage.
            When voltage is lower than low-threshold, a notification will be
            sent."
        ::= { ibEntityExtStateEntry 15 }

    ibEntityExtVoltageHighThreshold OBJECT-TYPE
        SYNTAX Integer32
        MAX-ACCESS read-write
        STATUS current
        DESCRIPTION
            "The high-threshold for the voltage.
            When voltage greater than high-threshold, a notification will be
            sent."
        ::= { ibEntityExtStateEntry 16 }

    ibEntityExtCriticalTemperatureThreshold OBJECT-TYPE
        SYNTAX Integer32
        MAX-ACCESS read-write
        STATUS current
        DESCRIPTION
            " The threshold for the critical Temperature. When temperature
            exceeds the critical temperature, a notification will be sent."
        ::= { ibEntityExtStateEntry 17 }

    ibEntityExtMacAddress OBJECT-TYPE
        SYNTAX MacAddress
        MAX-ACCESS read-only
        STATUS current
        DESCRIPTION
            "MAC Address of the entity."
        ::= { ibEntityExtStateEntry 18 }

    ibEntityExtErrorStatus OBJECT-TYPE
        SYNTAX INTEGER
            {
            notSupported(1),
            normal(2),
            postFailure(3),
            entityAbsent(4),
            nearThresholdError(5),
            poeError(11),
            stackError(21),
            stackPortBlocked(22),
            stackPortFailed(23),
            sfpRecvError(31),
            sfpSendError(32),
            sfpBothError(33),
            sfpRecvExceedUpperLimit(34),
            sfpRecvBelowLowerLimit(35),
            sfpSendExceedUpperLimit(36),
            sfpSendBelowLowerLimit(37),
            fanError (41),
            psuError(51),
            rpsError(61),
            moduleFaulty(71),
            sensorError(81),
            hardwareFaulty(91)
            }
        MAX-ACCESS read-only
        STATUS current
        DESCRIPTION
            "Indicate the error state of this entity object. Now it only
            supports Port, general power supply, RPS power supply and
            board/Subcard. It may have one of these values.
            The following four values  can be used for all kinds of entities.

            notSupported(1) means this entity cannot support this function.
            normal(2) means the statement of this entity is normal. for ports,
            it doesn't differentiate 10M/s, 100M/s, 1000M/s, duplex and
            half-duplex. For fan, power supply and board-Subcard, it means
            their states are normal.
            postFailure(3)  means the entity fails to POST.
            entityAbsent(4) means the entity is absent now.
            nearThresholdError(5) means the transceiver power reaches 3dB to the threshold.


            The following values is depended on the entity.

            For Port entities, it may have the following  values. If its POST
            is failure,
            then the value of the instance will be postFailure(3), otherwise
            the value will be normal(2).

            If enable power supply over Ethernet on this port is failure,
            the value of this instance will be poeError(11), otherwise it will
            be normal(2).

            For stack port, if it connects to another stack port normally, and
            these two units merge into one stack, then the value of this
            instance will be normal(2).
            If something wrong occurs and the unit cannot merge into stack,
            the value of this instance will be stackPortFailed(23).  If the
            stack port forms resilient daisy chain with another stack port
            on the other unit, the value of this instance will be
            stackPortBlocked(22).


            For SFP ports, if it fail to receive, the value of this instance
            will be sfpRecvError(31), if it fail to send, the value is
            sfpSendError(32), if it fail to send and receive, the value is
            sfpBothError(33), otherwise it will be normal(2).
            If the power that sfp received exceeded the upper limit, the value is sfpRecvExceedUpperLimit(34).
            If the power that sfp received exceeded the lower limit, the value is sfpRecvBelowLowerLimit(35).
            If the power that sfp sent exceeded the upper limit, the value is sfpSendExceedUpperLimit(36).
            If the power that sfp sent exceeded the lower limit, the value is sfpSendBelowLowerLimit(37).

            fanError(41) means that the fan stops working.

            psuError(51) means that the Power Supply Unit is in the state of
            fault.

            rpsError(61) means the RPS is in the state of fault.

            moduleFaulty(71) means the Module is in the state of fault.

            sensorError(81) means the sensor is in the state of fault.

            hardwareFaulty(91) means the hardware of specified entity is in the state of fault.

            NMS must be compatible with the states which may be added
            in the future."
        ::= { ibEntityExtStateEntry 19 }

    ibEntityExtCpuMaxUsage OBJECT-TYPE
        SYNTAX Integer32(0..100)
        MAX-ACCESS read-only
        STATUS current
        DESCRIPTION
            "The maximal CPU usage for the entity in the period of time."
        ::= { ibEntityExtStateEntry 20 }

    ibEntityExtLowerTemperatureThreshold OBJECT-TYPE
        SYNTAX Integer32
        MAX-ACCESS read-write
        STATUS current
        DESCRIPTION
            "The threshold for the lower Temperature. When temperature runs
            under the threshold, a notification will be sent."
        ::= { ibEntityExtStateEntry 21 }

    ibEntityExtShutdownTemperatureThreshold OBJECT-TYPE
        SYNTAX Integer32
        MAX-ACCESS read-write
        STATUS current
        DESCRIPTION
            "The threshold for the shutdown Temperature. When temperature
            exceeds the threshold, a notification will be sent and the entity
            will be shutdown."
        ::= { ibEntityExtStateEntry 22 }

    ibEntityExtPhyMemSize OBJECT-TYPE
        SYNTAX Unsigned32
        MAX-ACCESS read-only
        STATUS current
        DESCRIPTION
            "The memory size of entity. This is the physical attribute of entity."
        ::= { ibEntityExtStateEntry 23 }

    ibEntityExtPhyCpuFrequency OBJECT-TYPE
        SYNTAX Integer32
        MAX-ACCESS read-only
        STATUS current
        DESCRIPTION
            "The CPU frequency of entity. Unit of measure is MHZ."
        ::= { ibEntityExtStateEntry 24 }

    ibEntityExtFirstUsedDate OBJECT-TYPE
        SYNTAX DateAndTime (SIZE(8))
        MAX-ACCESS read-only
        STATUS current
        DESCRIPTION
            "The first used date of the entity."
        ::= { ibEntityExtStateEntry 25 }

    ibEntityExtCpuAvgUsage OBJECT-TYPE
        SYNTAX Integer32(0..100)
        MAX-ACCESS read-only
        STATUS current
        DESCRIPTION
            "The average CPU usage for the entity in a period of time."
        ::= { ibEntityExtStateEntry 26 }

    ibEntityExtMemAvgUsage OBJECT-TYPE
        SYNTAX Integer32(0..100)
        MAX-ACCESS read-only
        STATUS current
        DESCRIPTION
            "The average memory usage for the entity in a period of time."
        ::= { ibEntityExtStateEntry 27 }

    ibEntityExtMemType OBJECT-TYPE
        SYNTAX OCTET STRING(SIZE (0..64))
        MAX-ACCESS read-only
        STATUS current
        DESCRIPTION
            "The memory type of entity."
        ::= { ibEntityExtStateEntry 28 }

    ibEntityExtCriticalLowerTemperatureThreshold OBJECT-TYPE
        SYNTAX Integer32
        MAX-ACCESS read-write
        STATUS current
        DESCRIPTION
            "The threshold for the critical Temperature.  When temperature
            exceeds the critical lower temperature, a notification will be sent."
        ::= { ibEntityExtStateEntry 29 }

    ibEntityExtShutdownLowerTemperatureThreshold OBJECT-TYPE
        SYNTAX Integer32
        MAX-ACCESS read-write
        STATUS current
        DESCRIPTION
            "The threshold for the shutdown Temperature.  When temperature
            exceeds the lower threshold, a notification will be sent and the entity
            will be shutdown."
        ::= { ibEntityExtStateEntry 30 }

    ibEntityExtCpuUsageRecoverThreshold OBJECT-TYPE
        SYNTAX Integer32 (0..100)
        MAX-ACCESS read-write
        STATUS current
        DESCRIPTION
            "The recover threshold for the CPU usage.  When the CPU usage falls down to
            the threshold, a notification is sent.  The ibEntityExtCpuUsageRecoverThreshold
            must be less than or equal to the ibEntityExtCpuUsageThreshold."
        DEFVAL      { 100 }
        ::= { ibEntityExtStateEntry 31 }

    ibEntityExtMemSizeRev OBJECT-TYPE
        SYNTAX CounterBasedGauge64
        UNITS "bytes"
        MAX-ACCESS read-only
        STATUS current
        DESCRIPTION
            "Size of memory space for the entity.

            This node is used to replace ibEntityExtMemSize."
        ::= { ibEntityExtStateEntry 32 }

    ibEntityExtCpuUsageIn1Minute OBJECT-TYPE
        SYNTAX Integer32 (0..100)
        MAX-ACCESS read-only
        STATUS current
        DESCRIPTION
            "The CPU usage in last one minute for this entity.
            Generally, the overall CPU usage on the entity is
            calculated, independent of the number of CPUs on
            the entity."
        ::= { ibEntityExtStateEntry 33 }

    ibEntityExtCpuUsageIn5Minutes OBJECT-TYPE
        SYNTAX Integer32 (0..100)
        MAX-ACCESS read-only
        STATUS current
        DESCRIPTION
            "The CPU usage in last five minutes for this entity.
            Generally, the overall CPU usage on the entity is
            calculated, independent of the number of CPUs on
            the entity."
        ::= { ibEntityExtStateEntry 34 }

    ibEntityExtManu OBJECT IDENTIFIER ::= { ibEntityExtObjects 2 }

    ibEntityExtManuTable OBJECT-TYPE
        SYNTAX SEQUENCE OF IbEntityExtManuEntry
        MAX-ACCESS not-accessible
        STATUS current
        DESCRIPTION
            "The table about device manufacture information."
        ::= { ibEntityExtManu 1 }

    ibEntityExtManuEntry OBJECT-TYPE
        SYNTAX IbEntityExtManuEntry
        MAX-ACCESS not-accessible
        STATUS current
        DESCRIPTION
            "The device manufacture information about a particular physical
            entity."
        INDEX { ibEntityExtManuPhysicalIndex }
        ::= { ibEntityExtManuTable 1 }

    IbEntityExtManuEntry ::= SEQUENCE {
        ibEntityExtManuPhysicalIndex
            Integer32,
        ibEntityExtManuSerialNum
            SnmpAdminString,
        ibEntityExtManuBuildInfo
            SnmpAdminString,
        ibEntityExtManuBOM
            SnmpAdminString,
        ibEntityExtMacAddressCount
            Unsigned32
     }

    ibEntityExtManuPhysicalIndex OBJECT-TYPE
        SYNTAX Integer32 (1..2147483647)
        MAX-ACCESS accessible-for-notify
        STATUS current
        DESCRIPTION
            "The index of ibEntityExtManuTable.
            This index is identical to entPhysicalIndex in ENTITY-MIB."
        ::= { ibEntityExtManuEntry 1 }

    ibEntityExtManuSerialNum OBJECT-TYPE
        SYNTAX SnmpAdminString
        MAX-ACCESS read-only
        STATUS current
        DESCRIPTION
            "Manufacture serial number.
            The manufacture serial number of the entity such as chassis,
            module, and so on.  It is got from the device when manufacturing.
            For low level box-device, the manufacture serial number is the
            device-number of System Control Board(SCB for short), it is written
            into the SCB directly; for middle level or high level frame-device,
            the manufacture serial number is the device-numbers of SCB and
            Service Board, because the SCB, Service Board and chassis are
            separate to sale and the device-number of chassis cannot be
            written into board."
        ::= { ibEntityExtManuEntry 2 }

    ibEntityExtManuBuildInfo OBJECT-TYPE
        SYNTAX SnmpAdminString
        MAX-ACCESS read-only
        STATUS current
        DESCRIPTION
            "Device version information.
            The device version information of the entity such as chassis,
            module, and so on.  It consists of software version information
            and hardware version information."
        ::= { ibEntityExtManuEntry 3 }

    ibEntityExtManuBOM OBJECT-TYPE
        SYNTAX SnmpAdminString
        MAX-ACCESS read-only
        STATUS current
        DESCRIPTION
            "Device BOM code.
            The device BOM code of the entity such as chassis, module, and so
            on.  It is the component code of ERP system, which can be
            disassembled from device-number."
        ::= { ibEntityExtManuEntry 4 }

    ibEntityExtMacAddressCount OBJECT-TYPE
        SYNTAX Unsigned32
        MAX-ACCESS read-only
        STATUS current
        DESCRIPTION
            "MAC address count.
            The count of MAC addresses of the entity, such as chassis, module,
            or port, and so on."
        ::= { ibEntityExtManuEntry 5 }

    ibEntityExtPower OBJECT IDENTIFIER ::= { ibEntityExtObjects 3 }

    ibEntityExtPowerTable OBJECT-TYPE
        SYNTAX SEQUENCE OF IbEntityExtPowerEntry
        MAX-ACCESS not-accessible
        STATUS current
        DESCRIPTION
            "This table describes the power information of all the physical
            entity on the device, such as the fans, the subcards, the boards,
            etc."
        ::= { ibEntityExtPower 1 }

    ibEntityExtPowerEntry OBJECT-TYPE
        SYNTAX IbEntityExtPowerEntry
        MAX-ACCESS not-accessible
        STATUS current
        DESCRIPTION
            "The entity power information about a particular physical entity."
        INDEX { ibEntityExtPowerPhysicalIndex }
        ::= { ibEntityExtPowerTable 1 }

    IbEntityExtPowerEntry ::= SEQUENCE {
        ibEntityExtPowerPhysicalIndex
            Integer32,
        ibEntityExtNominalPower
            Gauge32,
        ibEntityExtCurrentPower
            Gauge32,
        ibEntityExtAveragePower
            Integer32,
        ibEntityExtPeakPower
            Integer32
     }

    ibEntityExtPowerPhysicalIndex OBJECT-TYPE
        SYNTAX Integer32 (1..2147483647)
        MAX-ACCESS accessible-for-notify
        STATUS current
        DESCRIPTION
            "The index of ibEntityExtPowerTable.
            This index is identical to entPhysicalIndex in ENTITY-MIB."
        ::= { ibEntityExtPowerEntry 1 }

    ibEntityExtNominalPower OBJECT-TYPE
        SYNTAX Gauge32
        MAX-ACCESS read-only
        STATUS current
        DESCRIPTION
            "The nominal power of the entity expressed in milliWatts."
        ::= { ibEntityExtPowerEntry 2 }

    ibEntityExtCurrentPower OBJECT-TYPE
        SYNTAX Gauge32
        MAX-ACCESS read-only
        STATUS current
        DESCRIPTION
            "The measured usage power of the entity expressed in milliWatts."
        ::= { ibEntityExtPowerEntry 3 }

    ibEntityExtAveragePower OBJECT-TYPE
        SYNTAX Integer32
        MAX-ACCESS read-write
        STATUS current
        DESCRIPTION
            "The average power consumed by the entity expressed in milliWatts.
            Writing a value of zero to this object resets its value to zero.
            Writing any other value to this object has no effect on its value
            and an error is returned."
        ::= { ibEntityExtPowerEntry 4 }

    ibEntityExtPeakPower OBJECT-TYPE
        SYNTAX Integer32
        MAX-ACCESS read-write
        STATUS current
        DESCRIPTION
            "The peak power consumed by the entity expressed in milliWatts.
            Writing a value of zero to this object resets its value to zero.
            Writing any other value to this object has no effect on its value
            and an error is returned."
        ::= { ibEntityExtPowerEntry 5 }

-- Process Table
    ibProcessObjects OBJECT IDENTIFIER ::= { ibEntityExtObjects 4 }

    ibProcessTable OBJECT-TYPE
        SYNTAX SEQUENCE OF IbProcessEntry
        MAX-ACCESS not-accessible
        STATUS current
        DESCRIPTION
            "The Table describes the information about a particular process,
            namely a task."
        ::= { ibProcessObjects 1 }

    ibProcessEntry OBJECT-TYPE
        SYNTAX IbProcessEntry
        MAX-ACCESS not-accessible
        STATUS current
        DESCRIPTION
            "The information about a particular process, namely a task."
        INDEX { ibProcessID }
        ::= { ibProcessTable 1 }

    IbProcessEntry ::= SEQUENCE {
        ibProcessID          Unsigned32,
        ibProcessName        DisplayString,
        ibProcessUtil5Min    Unsigned32
     }

    ibProcessID OBJECT-TYPE
        SYNTAX          Unsigned32
        MAX-ACCESS      read-only
        STATUS          current
        DESCRIPTION
            "This object indicates the identifier of process, namely task ID
            in system."
    ::= { ibProcessEntry 1 }

    ibProcessName OBJECT-TYPE
        SYNTAX          DisplayString(SIZE(1..32))
        MAX-ACCESS      read-only
        STATUS          current
        DESCRIPTION
            "This object indicates the process name."
    ::= { ibProcessEntry 2 }

    ibProcessUtil5Min OBJECT-TYPE
        SYNTAX          Unsigned32(0..100)
        MAX-ACCESS      read-only
        STATUS          current
        DESCRIPTION
            "This object provides a general idea of how busy a process caused
            the processor to be over a 5 minute period.  The ratio is calculated
            by the overall CPU usage caused by the process."
    ::= { ibProcessEntry 3 }

    ibEntityExtVoltageObjects OBJECT IDENTIFIER ::= { ibEntityExtObjects 5 }

    ibEntityExtVoltageTable OBJECT-TYPE
        SYNTAX SEQUENCE OF IbEntityExtVoltageEntry
        MAX-ACCESS not-accessible
        STATUS current
        DESCRIPTION
            "The table describes the voltage information of the voltage sensor
            entities on the device."
        ::= { ibEntityExtVoltageObjects 1 }

    ibEntityExtVoltageEntry OBJECT-TYPE
        SYNTAX IbEntityExtVoltageEntry
        MAX-ACCESS not-accessible
        STATUS current
        DESCRIPTION
            "The voltage information of the voltage sensor entity."
        INDEX { ibEntityExtPhysicalIndex }
        ::= { ibEntityExtVoltageTable 1 }

    IbEntityExtVoltageEntry ::= SEQUENCE {
        ibEntityExtCurrentVoltage
            Integer32,
        ibEntityExtNominalVoltage
            Integer32,
        ibEntityExtVoltageState
            INTEGER,
        ibEntityExtVoltageMajorLowThreshold
            Integer32,
        ibEntityExtVoltageFatalLowThreshold
            Integer32,
        ibEntityExtVoltageMajorHighThreshold
            Integer32,
        ibEntityExtVoltageFatalHighThreshold
            Integer32
     }

    ibEntityExtCurrentVoltage OBJECT-TYPE
        SYNTAX          Integer32
        MAX-ACCESS      read-only
        STATUS          current
        DESCRIPTION
            "The current voltage in millivolts of the voltage
            sensor entity."
    ::= { ibEntityExtVoltageEntry 1 }

    ibEntityExtNominalVoltage OBJECT-TYPE
        SYNTAX          Integer32
        MAX-ACCESS      read-only
        STATUS          current
        DESCRIPTION
            "The nominal voltage in millivolts of the voltage
            sensor entity."
    ::= { ibEntityExtVoltageEntry 2 }

    ibEntityExtVoltageState OBJECT-TYPE
        SYNTAX          INTEGER
        {
             normal   (0),
             low      (1),
             tooLow  (2),
             high     (3),
             tooHigh (4)
        }
        MAX-ACCESS      read-only
        STATUS          current
        DESCRIPTION
            "The voltage state of the voltage sensor entity."
    ::= { ibEntityExtVoltageEntry 3 }

    ibEntityExtVoltageMajorLowThreshold OBJECT-TYPE
        SYNTAX          Integer32
        MAX-ACCESS      read-only
        STATUS          current
        DESCRIPTION
            "The low threshold for the voltage sensor entity.

            When the voltage is lower than the threshold, a notification
            will be sent."
    ::= { ibEntityExtVoltageEntry 4 }

    ibEntityExtVoltageFatalLowThreshold OBJECT-TYPE
        SYNTAX          Integer32
        MAX-ACCESS      read-only
        STATUS          current
        DESCRIPTION
            "The fatal low voltage threshold for the voltage sensor entity.

            When the voltage is lower than the threshold, a notification
            will be sent."
    ::= { ibEntityExtVoltageEntry 5 }

    ibEntityExtVoltageMajorHighThreshold OBJECT-TYPE
        SYNTAX          Integer32
        MAX-ACCESS      read-only
        STATUS          current
        DESCRIPTION
            "The high threshold for the voltage sensor entity.

            When the voltage is higher than the threshold, a notification
            will be sent."
    ::= { ibEntityExtVoltageEntry 6 }

    ibEntityExtVoltageFatalHighThreshold OBJECT-TYPE
        SYNTAX          Integer32
        MAX-ACCESS      read-only
        STATUS          current
        DESCRIPTION
            "The fatal high threshold for the voltage sensor entity.

            When the voltage is higher than the threshold, a notification
            will be sent."
    ::= { ibEntityExtVoltageEntry 7 }

-- End

    ibEntityExtTraps OBJECT IDENTIFIER ::= { ibEntityExtend 2 }

    ibEntityExtTrapsPrefix OBJECT IDENTIFIER ::= { ibEntityExtTraps 0 }
    ibEntityExtTrapsInfor OBJECT IDENTIFIER ::= { ibEntityExtTraps 1 }

    ibEntityExtTemperatureThresholdNotification NOTIFICATION-TYPE
        OBJECTS {
            ibEntityExtPhysicalIndex,
            ibEntityExtTemperature,
            ibEntityExtTemperatureThreshold,
            ibEntityExtAdminStatus,
            ibEntityExtAlarmLight
            }
        STATUS current
        DESCRIPTION
            "The ibEntityExtTemperatureThresholdNotification
            indicates the temperature exceeded the threshold.
            In this condition, user should check the status and the
            environment of the entity, sometimes it happens because
            of the failure of air-condition."
        ::= { ibEntityExtTrapsPrefix 1 }

    ibEntityExtVoltageLowThresholdNotification NOTIFICATION-TYPE
        OBJECTS {
            ibEntityExtPhysicalIndex,
            ibEntityExtVoltage,
            ibEntityExtVoltageLowThreshold,
            ibEntityExtAdminStatus,
            ibEntityExtAlarmLight
            }
        STATUS current
        DESCRIPTION
            "The ibEntityExtVoltageLowThresholdNotification indicates
            the voltage is lower than the threshold.

            If the voltage is lower too much than the entity needs,
            the entity will halt."
        ::= { ibEntityExtTrapsPrefix 2 }

    ibEntityExtVoltageHighThresholdNotification NOTIFICATION-TYPE
        OBJECTS {
            ibEntityExtPhysicalIndex,
            ibEntityExtVoltage,
            ibEntityExtVoltageHighThreshold,
            ibEntityExtAdminStatus,
            ibEntityExtAlarmLight
            }
        STATUS current
        DESCRIPTION
            "The ibEntityExtVoltageHighThresholdNotification indicates
            the voltage is higher than the threshold.

            If the voltage is higher too much than the entity needs,
            The entity may be damaged by the high voltage."
        ::= { ibEntityExtTrapsPrefix 3 }

    ibEntityExtCpuUsageThresholdNotfication NOTIFICATION-TYPE
        OBJECTS {
            ibEntityExtPhysicalIndex,
            ibEntityExtCpuUsage,
            ibEntityExtCpuUsageThreshold,
            ibEntityExtAdminStatus,
            ibEntityExtAlarmLight,
            ibEntityExtCpuUsageRecoverThreshold,
            ibEntityExtFirstTrapTime
            }
        STATUS current
        DESCRIPTION
            "The ibEntityExtCpuUsageThresholdNotfication indicates
            the entity is overloaded."
        ::= { ibEntityExtTrapsPrefix 4 }

    ibEntityExtMemUsageThresholdNotification NOTIFICATION-TYPE
        OBJECTS {
            ibEntityExtPhysicalIndex,
            ibEntityExtMemUsage,
            ibEntityExtMemUsageThreshold,
            ibEntityExtMemSize,
            ibEntityExtAdminStatus,
            ibEntityExtAlarmLight,
            ibEntityExtFirstTrapTime
            }
        STATUS current
        DESCRIPTION
            "The ibEntityExtMemUsageThresholdNotification indicates
            the entity is overloaded."
        ::= { ibEntityExtTrapsPrefix 5 }

    ibEntityExtOperEnabled NOTIFICATION-TYPE
        OBJECTS {
            ibEntityExtPhysicalIndex,
            ibEntityExtAdminStatus,
            ibEntityExtAlarmLight
            }
        STATUS current
        DESCRIPTION
            "The trap indicates the entity is operable at present."
        ::= { ibEntityExtTrapsPrefix 6 }

    ibEntityExtOperDisabled NOTIFICATION-TYPE
        OBJECTS {
            ibEntityExtPhysicalIndex,
            ibEntityExtAdminStatus,
            ibEntityExtAlarmLight
            }
        STATUS current
        DESCRIPTION
            "The trap indicates the entity is not operable at present."
        ::= { ibEntityExtTrapsPrefix 7 }

    ibEntityExtCriticalTemperatureThresholdNotification NOTIFICATION-TYPE
        OBJECTS {
            ibEntityExtPhysicalIndex,
            ibEntityExtTemperature,
            ibEntityExtCriticalTemperatureThreshold,
            ibEntityExtAdminStatus,
            ibEntityExtAlarmLight
            }
        STATUS current
        DESCRIPTION
            "The ibEntityExtCriticalTemperatureThresholdNotification
            indicates the temperature exceeds the critical temperature.
            In this condition, user should check the status and the
            environment of the entity, sometimes it happens because
            of the failure of air-condition."
        ::= { ibEntityExtTrapsPrefix 8 }

    ibEntityExtSFPAlarmOn NOTIFICATION-TYPE
        OBJECTS {
            ibEntityExtPhysicalIndex,
            ibEntityExtErrorStatus,
            ibEntityExtAdminStatus,
            ibEntityExtAlarmLight
            }
        STATUS current
        DESCRIPTION
            "The trap is generated when the SFP module fails
            or runs abnormally for some particular reason."
        ::= { ibEntityExtTrapsPrefix 9 }

    ibEntityExtSFPAlarmOff NOTIFICATION-TYPE
        OBJECTS {
            ibEntityExtPhysicalIndex,
            ibEntityExtErrorStatus,
            ibEntityExtAdminStatus,
            ibEntityExtAlarmLight
            }
        STATUS current
        DESCRIPTION
            "The trap is generated when the SFP module restores to
            normal status."
        ::= { ibEntityExtTrapsPrefix 10 }

    ibEntityExtSFPPhony NOTIFICATION-TYPE
        OBJECTS {
            ibEntityExtPhysicalIndex,
            entPhysicalName,
            ibEntityExtAdminStatus,
            ibEntityExtAlarmLight
            }
        STATUS current
        DESCRIPTION
            "This module is NOT sold by authorized manufacturer.
            The normal function of the device or assume the maintenance
            responsibility thereof will NOT be guaranteed.
            The trap is generated periodically after a phony module has been
            found."
        ::= { ibEntityExtTrapsPrefix 11 }

    ibEntityInsert NOTIFICATION-TYPE
        OBJECTS { entPhysicalDescr, ibEntityExtAdminStatus, ibEntityExtOperStatus }
        STATUS current
        DESCRIPTION
            "The trap is generated when a removable entity inserting to
            device."
        ::= { ibEntityExtTrapsPrefix 12 }

    ibEntityRemove NOTIFICATION-TYPE
        OBJECTS { entPhysicalDescr, ibEntityExtAdminStatus, ibEntityExtOperStatus }
        STATUS current
        DESCRIPTION
            "The trap is generated when a removable entity removing from
            device."
        ::= { ibEntityExtTrapsPrefix 13 }

    ibEntityExtForcedPowerOff NOTIFICATION-TYPE
        OBJECTS {
            ibEntityExtPhysicalIndex,
            entPhysicalName,
            ibEntityExtAdminStatus,
            ibEntityExtAlarmLight
            }
        STATUS current
        DESCRIPTION
            "The trap indicates the entity is forced to power off."
        ::= { ibEntityExtTrapsPrefix 14 }

    ibEntityExtForcedPowerOn NOTIFICATION-TYPE
        OBJECTS {
            ibEntityExtPhysicalIndex,
            entPhysicalName,
            ibEntityExtAdminStatus,
            ibEntityExtAlarmLight
            }
        STATUS current
        DESCRIPTION
            "The trap indicates the entity is forced to power on."
        ::= { ibEntityExtTrapsPrefix 15 }

    ibEntityExtFaultAlarmOn NOTIFICATION-TYPE
        OBJECTS {
            ibEntityExtPhysicalIndex,
            entPhysicalName,
            ibEntityExtErrorStatus,
            ibEntityExtAdminStatus,
            ibEntityExtAlarmLight
            }
        STATUS current
        DESCRIPTION
            "The trap indicates a fault occurs on the specified entity."
        ::= { ibEntityExtTrapsPrefix 16 }

    ibEntityExtFaultAlarmOff NOTIFICATION-TYPE
        OBJECTS {
            ibEntityExtPhysicalIndex,
            entPhysicalName,
            ibEntityExtErrorStatus,
            ibEntityExtAdminStatus,
            ibEntityExtAlarmLight
            }
        STATUS current
        DESCRIPTION
            "The trap indicates a fault disappears on the specified entity."
        ::= { ibEntityExtTrapsPrefix 17 }

    ibEntityExtResourceLack NOTIFICATION-TYPE
        OBJECTS {
            ibEntityExtPhysicalIndex,
            entPhysicalName
            }
        STATUS current
        DESCRIPTION
            "The trap indicates that a kind of resource is not enough on the
            specified entity."
        ::= { ibEntityExtTrapsPrefix 18 }

    ibEntityExtResourceEnough NOTIFICATION-TYPE
        OBJECTS {
            ibEntityExtPhysicalIndex,
            entPhysicalName
            }
        STATUS current
        DESCRIPTION
            "The trap indicates that the entity recovers from the status of no
            enough resource."
        ::= { ibEntityExtTrapsPrefix 19 }

    ibEntityExtTemperatureLower NOTIFICATION-TYPE
        OBJECTS {
            ibEntityExtPhysicalIndex,
            entPhysicalName,
            ibEntityExtTemperature,
            ibEntityExtLowerTemperatureThreshold,
            ibEntityExtAdminStatus
            }
        STATUS current
        DESCRIPTION
            "The trap indicates the temperature of a specified entity is under
            the lower threshold. In this condition, user should check the
            status and the environment of the entity, sometimes it goes wrong
            for some reason."
        ::= { ibEntityExtTrapsPrefix 20 }

    ibEntityExtTemperatureTooUp NOTIFICATION-TYPE
        OBJECTS {
            ibEntityExtPhysicalIndex,
            entPhysicalName,
            ibEntityExtTemperature,
            ibEntityExtShutdownTemperatureThreshold,
            ibEntityExtAdminStatus
            }
        STATUS current
        DESCRIPTION
            "The trap indicates the temperature of a specified entity exceeded
            the shutdown threshold. In this condition, user should check the
            status and the environment of the entity, sometimes it goes wrong
            for some reason."
        ::= { ibEntityExtTrapsPrefix 21 }

    ibEntityExtTemperatureNormal NOTIFICATION-TYPE
        OBJECTS {
            ibEntityExtPhysicalIndex,
            entPhysicalName,
            ibEntityExtTemperature,
            ibEntityExtLowerTemperatureThreshold,
            ibEntityExtTemperatureThreshold,
            ibEntityExtAdminStatus
            }
        STATUS current
        DESCRIPTION
            "The trap indicates the temperature of a specified entity recover
            from abnormal status."
        ::= { ibEntityExtTrapsPrefix 22 }

    ibEntityExternalAlarmOccur NOTIFICATION-TYPE
        OBJECTS {
            ibEntityExtPhysicalIndex,
            entPhysicalName
            }
        STATUS current
        DESCRIPTION
            "The trap is generated when the monitored device connected to the
             specified entity fails."
        ::= { ibEntityExtTrapsPrefix 23 }

    ibEntityExternalAlarmRecover NOTIFICATION-TYPE
        OBJECTS {
            ibEntityExtPhysicalIndex,
            entPhysicalName
            }
        STATUS current
        DESCRIPTION
            "The trap is generated when the failed device connected to the
             specified entity returns to normal."
        ::= { ibEntityExtTrapsPrefix 24 }

    ibEntityExtCpuUsageThresholdRecover NOTIFICATION-TYPE
        OBJECTS {
            ibEntityExtPhysicalIndex,
            ibEntityExtCpuUsage,
            ibEntityExtCpuUsageThreshold,
            ibEntityExtAdminStatus,
            ibEntityExtAlarmLight,
            ibEntityExtCpuUsageRecoverThreshold,
            ibEntityExtFirstTrapTime
            }
        STATUS current
        DESCRIPTION
            "The trap indicates the CPU usage descends the threshold."
        ::= { ibEntityExtTrapsPrefix 25 }

    ibEntityExtMemUsageThresholdRecover NOTIFICATION-TYPE
        OBJECTS {
            ibEntityExtPhysicalIndex,
            ibEntityExtMemUsage,
            ibEntityExtMemUsageThreshold,
            ibEntityExtMemSize,
            ibEntityExtAdminStatus,
            ibEntityExtAlarmLight,
            ibEntityExtFirstTrapTime
            }
        STATUS current
        DESCRIPTION
            "The trap indicates the memory usage descends the threshold."
        ::= { ibEntityExtTrapsPrefix 26 }

    ibEntityExtMemAllocatedFailed NOTIFICATION-TYPE
        OBJECTS {
            ibEntityExtPhysicalIndex,
            ibEntityExtTrapDescription
            }
        STATUS current
        DESCRIPTION
            "The trap indicates the memory allocated failed."
        ::= { ibEntityExtTrapsPrefix 27 }

    ibEntityExtECCParityAlarm NOTIFICATION-TYPE
        OBJECTS {
            ibEntityExtPhysicalIndex,
            ibEntityExtECCParityAlarmStatus,
            ibEntityExtTrapDescription
            }
        STATUS current
        DESCRIPTION
            "The trap indicates the ECC(Error Correction Code) parity error alarm."
        ::= { ibEntityExtTrapsPrefix 28 }

    ibEntityExtCritLowerTempThresholdNotification NOTIFICATION-TYPE
        OBJECTS {
            ibEntityExtPhysicalIndex,
            entPhysicalName,
            ibEntityExtTemperature,
            ibEntityExtCriticalLowerTemperatureThreshold
            }
        STATUS current
        DESCRIPTION
            "The ibEntityExtCritLowerTempThresholdNotification
            indicates the temperature is lower than the threshold.

            If the temperature is lower too much than the entity needs,
            the entity will halt."
        ::= { ibEntityExtTrapsPrefix 29 }

    ibEntityExtTemperatureTooLow NOTIFICATION-TYPE
        OBJECTS {
            ibEntityExtPhysicalIndex,
            entPhysicalName,
            ibEntityExtTemperature,
            ibEntityExtShutdownLowerTemperatureThreshold
            }
        STATUS current
        DESCRIPTION
            "The ibEntityExtTemperatureTooLow indicates the temperature
            is lower than the threshold.

            If the temperature is lower too much than the entity needs,
            the entity halts now."
        ::= { ibEntityExtTrapsPrefix 30 }

    ibEntityExtFanDirectionNotPreferred NOTIFICATION-TYPE
        OBJECTS {
            ibEntityExtPhysicalIndex,
            entPhysicalName
            }
        STATUS current
        DESCRIPTION
            "This trap indicates the specified fan's direction does not
            accord with preferred. The two parameters indicate the entity
            index and physical name of fan."
        ::= { ibEntityExtTrapsPrefix 31 }

    ibEntityExtFanDirectionNotAccord NOTIFICATION-TYPE
        OBJECTS {
            ibEntityExtPhysicalIndex,
            entPhysicalName
            }
        STATUS current
        DESCRIPTION
            "This trap indicates the direction of fans does not accord
            with each other. The two parameters indicate the parent
            entity of the fans."
        ::= { ibEntityExtTrapsPrefix 32 }

    ibEntityExtSFPInvalid NOTIFICATION-TYPE
        OBJECTS {
            ibEntityExtPhysicalIndex,
            entPhysicalName,
            ibEntityExtSFPInvalidInDays
            }
        STATUS current
        DESCRIPTION
            "The transceiver module is not compatible with the interface card.
            The authorized manufacturer therefore shall NOT guarantee
            the normal function of the transceiver.
            The transceiver module will be invalidated in days.
            Please replace it with a compatible one as soon as possible.
            The trap is generated periodically after a phony transceiver module
            has been found."
        ::= { ibEntityExtTrapsPrefix 33 }

    ibEntityExtSFPInvalidNow NOTIFICATION-TYPE
        OBJECTS {
            ibEntityExtPhysicalIndex,
            entPhysicalName
            }
        STATUS current
        DESCRIPTION
            "This transceiver module is not compatible with the interface card.
            The authorized manufacturer therefore shall NOT guarantee
            the normal function of the transceiver.
            The trap is generated after a phony transceiver module
            has been found."
        ::= { ibEntityExtTrapsPrefix 34 }

    ibEntityExtMemUsageThresholdOverTrap NOTIFICATION-TYPE
        OBJECTS {
            ibEntityExtPhysicalIndex,
            ibEntityExtMemUsage,
            ibEntityExtMemUsageThreshold,
            ibEntityExtMemSizeRev,
            ibEntityExtAdminStatus,
            ibEntityExtAlarmLight
            }
        STATUS current
        DESCRIPTION
            "This trap indicates that the memory usage of the entity is
            overloaded.

            This trap is used to replace
            ibEntityExtMemUsageThresholdNotification."
        ::= { ibEntityExtTrapsPrefix 35 }

    ibEntityExtMemUsageThresholdRecoverTrap NOTIFICATION-TYPE
        OBJECTS {
            ibEntityExtPhysicalIndex,
            ibEntityExtMemUsage,
            ibEntityExtMemUsageThreshold,
            ibEntityExtMemSizeRev,
            ibEntityExtAdminStatus,
            ibEntityExtAlarmLight
            }
        STATUS current
        DESCRIPTION
            "This trap indicates that the memory usage decreased below
            the threshold.

            This trap is used to replace
            ibEntityExtMemUsageThresholdRecover."
        ::= { ibEntityExtTrapsPrefix 36 }

    ibEntityExtVoltageNormal NOTIFICATION-TYPE
        OBJECTS {
            ibEntityExtPhysicalIndex,
            ibEntityExtCurrentVoltage,
            ibEntityExtNominalVoltage,
            ibEntityExtVoltageMajorLowThreshold,
            ibEntityExtVoltageMajorHighThreshold
            }
        STATUS current
        DESCRIPTION
            "This trap indicates that the voltage recovers to normal."
        ::= { ibEntityExtTrapsPrefix 37 }

    ibEntityExtVoltageLower NOTIFICATION-TYPE
        OBJECTS {
            ibEntityExtPhysicalIndex,
            ibEntityExtCurrentVoltage,
            ibEntityExtNominalVoltage,
            ibEntityExtVoltageMajorLowThreshold
            }
        STATUS current
        DESCRIPTION
            "This trap indicates that the voltage is lower than the
            low threshold."
        ::= { ibEntityExtTrapsPrefix 38 }

    ibEntityExtVoltageTooLow NOTIFICATION-TYPE
        OBJECTS {
            ibEntityExtPhysicalIndex,
            ibEntityExtCurrentVoltage,
            ibEntityExtNominalVoltage,
            ibEntityExtVoltageFatalLowThreshold
            }
        STATUS current
        DESCRIPTION
            "This trap indicates that the voltage is lower than the
            fatal low threshold."
        ::= { ibEntityExtTrapsPrefix 39 }

    ibEntityExtVoltageHigher NOTIFICATION-TYPE
        OBJECTS {
            ibEntityExtPhysicalIndex,
            ibEntityExtCurrentVoltage,
            ibEntityExtNominalVoltage,
            ibEntityExtVoltageMajorHighThreshold
            }
        STATUS current
        DESCRIPTION
            "This trap indicates that the voltage is higher than the
            high threshold."
        ::= { ibEntityExtTrapsPrefix 40 }

    ibEntityExtVoltageTooHigh NOTIFICATION-TYPE
        OBJECTS {
            ibEntityExtPhysicalIndex,
            ibEntityExtCurrentVoltage,
            ibEntityExtNominalVoltage,
            ibEntityExtVoltageFatalHighThreshold
            }
        STATUS current
        DESCRIPTION
            "This trap indicates that the voltage is higher than the
            fatal high threshold."
        ::= { ibEntityExtTrapsPrefix 41 }

    ibEntityExtSFPAlarmOnEx NOTIFICATION-TYPE
        OBJECTS {
            ibEntityExtPhysicalIndex,
            entPhysicalName,
            ibEntityExtAdminStatus,
            ibEntityExtAlarmLight,
            ibEntityExtErrorStatus
            }
        STATUS current
        DESCRIPTION
            "The trap is generated when the SFP module fails
            or runs abnormally for some particular reason.
            This trap is used to replace ibEntityExtSFPAlarmOn."
        ::= { ibEntityExtTrapsPrefix 42 }

    ibEntityExtSFPAlarmOffEx NOTIFICATION-TYPE
        OBJECTS {
            ibEntityExtPhysicalIndex,
            entPhysicalName,
            ibEntityExtAdminStatus,
            ibEntityExtAlarmLight,
            ibEntityExtErrorStatus
            }
        STATUS current
        DESCRIPTION
            "The trap is generated when the SFP module is restored to
            normal status.
            This trap is used to replace ibEntityExtSFPAlarmOff."
        ::= { ibEntityExtTrapsPrefix 43 }

    ibEntityExtBoardServiceMisMatch NOTIFICATION-TYPE
        OBJECTS {
            ibEntityExtPhysicalIndex,
            entPhysicalName,
            ibEntityExtRelativeLocation,
            ibEntityExtServiceName
            }
        STATUS current
        DESCRIPTION
            "This notification is generated when a service not supported
             by a card on the device is configured, or a card that does
             not support a service that has been configured on the device
             is installed."
        ::= { ibEntityExtTrapsPrefix 44 }

    ibEntityExtTrapDescription OBJECT-TYPE
        SYNTAX      SnmpAdminString (SIZE (0..255))
        MAX-ACCESS  accessible-for-notify
        STATUS      current
        DESCRIPTION
            "The information of trap."
        ::= { ibEntityExtTrapsInfor 1 }

    ibEntityExtECCParityAlarmStatus OBJECT-TYPE
        SYNTAX  INTEGER {
                         other(1),
                         l1cache(2),       -- cpu l1 data cache err
                         l2cache(3),       -- cpu l2 data cache err
                         sdram(4),         -- sdram err for cpu
                         mac(5),           -- mac err
                         tcam(6),          -- tcam err
                         ingressbuffer(7), -- IB err
                         egressbuffer(8),  -- EB err
                         lpm(9),           -- lpm err
                         controlmemory(10) -- controlmemory err
                        }
        MAX-ACCESS  accessible-for-notify
        STATUS      current
        DESCRIPTION
               "ECC parity error."
        ::= { ibEntityExtTrapsInfor 2 }

    ibEntityExtSFPInvalidInDays OBJECT-TYPE
        SYNTAX      Integer32
        MAX-ACCESS  accessible-for-notify
        STATUS      current
        DESCRIPTION
            "The days when the transceiver module is still valid,
            but after those days, it will be invalidated."
        ::= { ibEntityExtTrapsInfor 3 }

    ibEntityExtFirstTrapTime OBJECT-TYPE
        SYNTAX      TimeTicks
        MAX-ACCESS  accessible-for-notify
        STATUS      current
        DESCRIPTION
            "Represents the first trap time."
        ::= { ibEntityExtTrapsInfor 4 }

    ibEntityExtRelativeLocation OBJECT-TYPE
        SYNTAX      OCTET STRING(SIZE (0..255))
        MAX-ACCESS  accessible-for-notify
        STATUS      current
        DESCRIPTION
            "The relative location of physical entity."
        ::= { ibEntityExtTrapsInfor 5 }

    ibEntityExtServiceName OBJECT-TYPE
        SYNTAX      OCTET STRING(SIZE (1..255))
        MAX-ACCESS  accessible-for-notify
        STATUS      current
        DESCRIPTION
            "Name of the service."
        ::= { ibEntityExtTrapsInfor 6 }

--  Conformance and Compliance
    ibEntityExtConformance OBJECT IDENTIFIER ::= { ibEntityExtend 3 }

    ibEntityExtCompliances OBJECT IDENTIFIER ::= { ibEntityExtConformance 1 }

--  this module
    ibEntityExtCompliance MODULE-COMPLIANCE
        STATUS current
        DESCRIPTION
            "The compliance statement for systems supporting this MIB."
        MODULE -- this module
            MANDATORY-GROUPS { ibEntityExtGroup, ibEntityExtNotificationGroup,
                               ibEntityExtManuGroup, ibEntityExtPowerGroup }
            OBJECT ibEntityExtAdminStatus
                MIN-ACCESS read-only
                DESCRIPTION
                    "Write access is not required."
            OBJECT ibEntityExtCpuUsageThreshold
                MIN-ACCESS read-only
                DESCRIPTION
                    "Write access is not required."
            OBJECT ibEntityExtMemUsageThreshold
                MIN-ACCESS read-only
                DESCRIPTION
                    "Write access is not required."
            OBJECT ibEntityExtTemperatureThreshold
                MIN-ACCESS read-only
                DESCRIPTION
                    "Write access is not required."
            OBJECT ibEntityExtVoltageLowThreshold
                MIN-ACCESS read-only
                DESCRIPTION
                    "Write access is not required."
            OBJECT ibEntityExtVoltageHighThreshold
                MIN-ACCESS read-only
                DESCRIPTION
                    "Write access is not required."
        ::= { ibEntityExtCompliances 1 }

    ibEntityExtGroups OBJECT IDENTIFIER ::= { ibEntityExtConformance 2 }

    ibEntityExtGroup OBJECT-GROUP
        OBJECTS {
            ibEntityExtPhysicalIndex,
            ibEntityExtAdminStatus,
            ibEntityExtOperStatus,
            ibEntityExtStandbyStatus,
            ibEntityExtAlarmLight,
            ibEntityExtCpuUsage,
            ibEntityExtCpuUsageThreshold,
            ibEntityExtMemUsage,
            ibEntityExtMemUsageThreshold,
            ibEntityExtMemSize,
            ibEntityExtUpTime,
            ibEntityExtTemperature,
            ibEntityExtTemperatureThreshold,
            ibEntityExtVoltage,
            ibEntityExtVoltageLowThreshold,
            ibEntityExtVoltageHighThreshold,
            ibEntityExtCriticalTemperatureThreshold,
            ibEntityExtMacAddress,
            ibEntityExtErrorStatus,
            ibEntityExtCpuMaxUsage,
            ibEntityExtLowerTemperatureThreshold,
            ibEntityExtShutdownTemperatureThreshold,
            ibEntityExtPhyMemSize,
            ibEntityExtPhyCpuFrequency,
            ibEntityExtFirstUsedDate,
            ibEntityExtCpuAvgUsage,
            ibEntityExtMemAvgUsage,
            ibEntityExtMemType,
            ibEntityExtCriticalLowerTemperatureThreshold,
            ibEntityExtShutdownLowerTemperatureThreshold,
            ibEntityExtCpuUsageRecoverThreshold,
            ibEntityExtMemSizeRev,
            ibEntityExtCpuUsageIn1Minute,
            ibEntityExtCpuUsageIn5Minutes
            }
        STATUS current
        DESCRIPTION
            "Entity Extend group."
        ::= { ibEntityExtGroups 1 }

    ibEntityExtNotificationGroup NOTIFICATION-GROUP
        NOTIFICATIONS { ibEntityExtTemperatureThresholdNotification,
                ibEntityExtVoltageLowThresholdNotification,
                ibEntityExtVoltageHighThresholdNotification,
                ibEntityExtCpuUsageThresholdNotfication,
                ibEntityExtMemUsageThresholdNotification,
                ibEntityExtOperEnabled,
                ibEntityExtOperDisabled,
                ibEntityExtCriticalTemperatureThresholdNotification,
                ibEntityExtSFPAlarmOn,
                ibEntityExtSFPAlarmOff,
                ibEntityExtSFPPhony,
                ibEntityInsert,
                ibEntityRemove,
                ibEntityExtForcedPowerOff,
                ibEntityExtForcedPowerOn,
                ibEntityExtFaultAlarmOn,
                ibEntityExtFaultAlarmOff,
                ibEntityExtResourceLack,
                ibEntityExtResourceEnough,
                ibEntityExtTemperatureLower,
                ibEntityExtTemperatureTooUp,
                ibEntityExtTemperatureNormal,
                ibEntityExternalAlarmOccur,
                ibEntityExternalAlarmRecover,
                ibEntityExtCpuUsageThresholdRecover,
                ibEntityExtMemUsageThresholdRecover,
                ibEntityExtMemAllocatedFailed,
                ibEntityExtECCParityAlarm,
                ibEntityExtCritLowerTempThresholdNotification,
                ibEntityExtTemperatureTooLow,
                ibEntityExtFanDirectionNotPreferred,
                ibEntityExtFanDirectionNotAccord,
                ibEntityExtSFPInvalid,
                ibEntityExtSFPInvalidNow,
                ibEntityExtMemUsageThresholdOverTrap,
                ibEntityExtMemUsageThresholdRecoverTrap,
                ibEntityExtVoltageNormal,
                ibEntityExtVoltageTooLow,
                ibEntityExtVoltageLower,
                ibEntityExtVoltageHigher,
                ibEntityExtVoltageTooHigh,
                ibEntityExtSFPAlarmOnEx,
                ibEntityExtSFPAlarmOffEx
                }
        STATUS current
        DESCRIPTION
            "Entity Extend Notification group."
            ::= { ibEntityExtGroups 2 }

    ibEntityExtManuGroup OBJECT-GROUP
        OBJECTS {
            ibEntityExtManuPhysicalIndex,
            ibEntityExtManuSerialNum,
            ibEntityExtManuBuildInfo,
            ibEntityExtManuBOM,
            ibEntityExtMacAddressCount
            }
        STATUS current
        DESCRIPTION
            "Standard Device Manufacture Information group."
        ::= { ibEntityExtGroups 3 }

    ibEntityExtPowerGroup OBJECT-GROUP
        OBJECTS {
            ibEntityExtPowerPhysicalIndex,
            ibEntityExtNominalPower,
            ibEntityExtCurrentPower,
            ibEntityExtAveragePower,
            ibEntityExtPeakPower
            }
        STATUS current
        DESCRIPTION
            "Standard Entity Power Information group."
        ::= { ibEntityExtGroups 4 }

    ibEntityExtRasTraps OBJECT IDENTIFIER ::= { ibEntityExtend 4 }

    ibEntityExtRasTrapsPrefix OBJECT IDENTIFIER ::= { ibEntityExtRasTraps 0 }
    ibEntityExtRasTrapsInfor OBJECT IDENTIFIER ::= { ibEntityExtRasTraps 1 }

    ibEntityExtSystemFatalAlarmOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when a system fatal alarm occurred."
        ::= { ibEntityExtRasTrapsPrefix 1 }

    ibEntityExtSystemFatalAlarmClear NOTIFICATION-TYPE
        OBJECTS {
            ibEntityExtPhysicalIndex,
            entPhysicalName,
            ibEntityExtRelativeResource,
            ibEntityExtErrorCode,
            ibEntityExtReason
            }
        STATUS current
        DESCRIPTION
            "The trap is generated when a system fatal alarm cleared."
        ::= { ibEntityExtRasTrapsPrefix 2 }

    ibEntityExtSystemAlarmOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when a system alarm occurred."
        ::= { ibEntityExtRasTrapsPrefix 3 }

    ibEntityExtSystemAlarmClear NOTIFICATION-TYPE
        OBJECTS {
            ibEntityExtPhysicalIndex,
            entPhysicalName,
            ibEntityExtRelativeResource,
            ibEntityExtErrorCode,
            ibEntityExtReason
            }
        STATUS current
        DESCRIPTION
            "The trap is generated when a system alarm cleared."
        ::= { ibEntityExtRasTrapsPrefix 4 }

    ibEntityExtSystemWarningOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when a system warning occurred."
        ::= { ibEntityExtRasTrapsPrefix 5 }

    ibEntityExtSystemWarningClear NOTIFICATION-TYPE
        OBJECTS {
            ibEntityExtPhysicalIndex,
            entPhysicalName,
            ibEntityExtRelativeResource,
            ibEntityExtErrorCode,
            ibEntityExtReason
            }
        STATUS current
        DESCRIPTION
            "The trap is generated when a system warning cleared."
        ::= { ibEntityExtRasTrapsPrefix 6 }

    ibEntityExtBoardFatalAlarmOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when a board fatal alarm occurred."
        ::= { ibEntityExtRasTrapsPrefix 7 }

    ibEntityExtBoardFatalAlarmClear NOTIFICATION-TYPE
        OBJECTS {
            ibEntityExtPhysicalIndex,
            entPhysicalName,
            ibEntityExtRelativeResource,
            ibEntityExtErrorCode,
            ibEntityExtReason
            }
        STATUS current
        DESCRIPTION
            "The trap is generated when a board fatal alarm cleared."
        ::= { ibEntityExtRasTrapsPrefix 8 }

    ibEntityExtBoardAlarmOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when a board alarm occurred."
        ::= { ibEntityExtRasTrapsPrefix 9 }

    ibEntityExtBoardAlarmClear NOTIFICATION-TYPE
        OBJECTS {
            ibEntityExtPhysicalIndex,
            entPhysicalName,
            ibEntityExtRelativeResource,
            ibEntityExtErrorCode,
            ibEntityExtReason
            }
        STATUS current
        DESCRIPTION
            "The trap is generated when a board alarm cleared."
        ::= { ibEntityExtRasTrapsPrefix 10 }

    ibEntityExtBoardWarningOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when a board warning occurred."
        ::= { ibEntityExtRasTrapsPrefix 11 }

    ibEntityExtBoardWarningClear NOTIFICATION-TYPE
        OBJECTS {
            ibEntityExtPhysicalIndex,
            entPhysicalName,
            ibEntityExtRelativeResource,
            ibEntityExtErrorCode,
            ibEntityExtReason
            }
        STATUS current
        DESCRIPTION
            "The trap is generated when a board warning cleared."
        ::= { ibEntityExtRasTrapsPrefix 12 }

    ibEntityExtPowerFatalAlarmOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when a power fatal alarm occurred."
        ::= { ibEntityExtRasTrapsPrefix 13 }

    ibEntityExtPowerFatalAlarmClear NOTIFICATION-TYPE
        OBJECTS {
            ibEntityExtPhysicalIndex,
            entPhysicalName,
            ibEntityExtRelativeResource,
            ibEntityExtErrorCode,
            ibEntityExtReason
            }
        STATUS current
        DESCRIPTION
            "The trap is generated when a power fatal alarm cleared."
        ::= { ibEntityExtRasTrapsPrefix 14 }

    ibEntityExtPowerAlarmOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when a power alarm occurred."
        ::= { ibEntityExtRasTrapsPrefix 15 }

    ibEntityExtPowerAlarmClear NOTIFICATION-TYPE
        OBJECTS {
            ibEntityExtPhysicalIndex,
            entPhysicalName,
            ibEntityExtRelativeResource,
            ibEntityExtErrorCode,
            ibEntityExtReason
            }
        STATUS current
        DESCRIPTION
            "The trap is generated when a power alarm cleared."
        ::= { ibEntityExtRasTrapsPrefix 16 }

    ibEntityExtPowerWarningOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when a power warning occurred."
        ::= { ibEntityExtRasTrapsPrefix 17 }

    ibEntityExtPowerWarningClear NOTIFICATION-TYPE
        OBJECTS {
            ibEntityExtPhysicalIndex,
            entPhysicalName,
            ibEntityExtRelativeResource,
            ibEntityExtErrorCode,
            ibEntityExtReason
            }
        STATUS current
        DESCRIPTION
            "The trap is generated when a power warning cleared."
        ::= { ibEntityExtRasTrapsPrefix 18 }

    ibEntityExtFanFatalAlarmOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when a fan fatal alarm occurred."
        ::= { ibEntityExtRasTrapsPrefix 19 }

    ibEntityExtFanFatalAlarmClear NOTIFICATION-TYPE
        OBJECTS {
            ibEntityExtPhysicalIndex,
            entPhysicalName,
            ibEntityExtRelativeResource,
            ibEntityExtErrorCode,
            ibEntityExtReason
            }
        STATUS current
        DESCRIPTION
            "The trap is generated when a fan fatal alarm cleared."
        ::= { ibEntityExtRasTrapsPrefix 20 }

    ibEntityExtFanAlarmOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when a fan alarm occurred."
        ::= { ibEntityExtRasTrapsPrefix 21 }

    ibEntityExtFanAlarmClear NOTIFICATION-TYPE
        OBJECTS {
            ibEntityExtPhysicalIndex,
            entPhysicalName,
            ibEntityExtRelativeResource,
            ibEntityExtErrorCode,
            ibEntityExtReason
            }
        STATUS current
        DESCRIPTION
            "The trap is generated when a fan alarm cleared."
        ::= { ibEntityExtRasTrapsPrefix 22 }

    ibEntityExtFanWarningOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when a fan warning occurred."
        ::= { ibEntityExtRasTrapsPrefix 23 }

    ibEntityExtFanWarningClear NOTIFICATION-TYPE
        OBJECTS {
            ibEntityExtPhysicalIndex,
            entPhysicalName,
            ibEntityExtRelativeResource,
            ibEntityExtErrorCode,
            ibEntityExtReason
            }
        STATUS current
        DESCRIPTION
            "The trap is generated when a fan warning cleared."
        ::= { ibEntityExtRasTrapsPrefix 24 }

    ibEntityExtVoltageFatalAlarmOccur NOTIFICATION-TYPE
        OBJECTS {
            ibEntityExtPhysicalIndex,
            entPhysicalName,
            ibEntityExtRelativeResource,
            ibEntityExtErrorCode,
            ibEntityExtReason,
            ibEntityExtThresholdType,
            ibEntityExtThresholdVal,
            ibEntityExtCurrentVal
            }
        STATUS current
        DESCRIPTION
            "The trap is generated when a voltage fatal alarm occurred."
        ::= { ibEntityExtRasTrapsPrefix 25 }

    ibEntityExtVoltageFatalAlarmClear NOTIFICATION-TYPE
        OBJECTS {
            ibEntityExtPhysicalIndex,
            entPhysicalName,
            ibEntityExtRelativeResource,
            ibEntityExtErrorCode,
            ibEntityExtReason,
            ibEntityExtThresholdType,
            ibEntityExtThresholdVal,
            ibEntityExtCurrentVal
            }
        STATUS current
        DESCRIPTION
            "The trap is generated when a voltage fatal alarm cleared."
        ::= { ibEntityExtRasTrapsPrefix 26 }

    ibEntityExtVoltageAlarmOccur NOTIFICATION-TYPE
        OBJECTS {
            ibEntityExtPhysicalIndex,
            entPhysicalName,
            ibEntityExtRelativeResource,
            ibEntityExtErrorCode,
            ibEntityExtReason,
            ibEntityExtThresholdType,
            ibEntityExtThresholdVal,
            ibEntityExtCurrentVal
            }
        STATUS current
        DESCRIPTION
            "The trap is generated when a voltage alarm occurred."
        ::= { ibEntityExtRasTrapsPrefix 27 }

    ibEntityExtVoltageAlarmClear NOTIFICATION-TYPE
        OBJECTS {
            ibEntityExtPhysicalIndex,
            entPhysicalName,
            ibEntityExtRelativeResource,
            ibEntityExtErrorCode,
            ibEntityExtReason,
            ibEntityExtThresholdType,
            ibEntityExtThresholdVal,
            ibEntityExtCurrentVal
            }
        STATUS current
        DESCRIPTION
            "The trap is generated when a voltage alarm cleared."
        ::= { ibEntityExtRasTrapsPrefix 28 }

    ibEntityExtVoltageWarningOccur NOTIFICATION-TYPE
        OBJECTS {
            ibEntityExtPhysicalIndex,
            entPhysicalName,
            ibEntityExtRelativeResource,
            ibEntityExtErrorCode,
            ibEntityExtReason,
            ibEntityExtThresholdType,
            ibEntityExtThresholdVal,
            ibEntityExtCurrentVal
            }
        STATUS current
        DESCRIPTION
            "The trap is generated when a voltage warning occurred."
        ::= { ibEntityExtRasTrapsPrefix 29 }

    ibEntityExtVoltageWarningClear NOTIFICATION-TYPE
        OBJECTS {
            ibEntityExtPhysicalIndex,
            entPhysicalName,
            ibEntityExtRelativeResource,
            ibEntityExtErrorCode,
            ibEntityExtReason,
            ibEntityExtThresholdType,
            ibEntityExtThresholdVal,
            ibEntityExtCurrentVal
            }
        STATUS current
        DESCRIPTION
            "The trap is generated when a voltage warning cleared."
        ::= { ibEntityExtRasTrapsPrefix 30 }

    ibEntityExtTemperatureFatalAlarmOccur NOTIFICATION-TYPE
        OBJECTS {
            ibEntityExtPhysicalIndex,
            entPhysicalName,
            ibEntityExtRelativeResource,
            ibEntityExtErrorCode,
            ibEntityExtReason,
            ibEntityExtThresholdType,
            ibEntityExtThresholdVal,
            ibEntityExtCurrentVal
            }
        STATUS current
        DESCRIPTION
            "The trap is generated when a temperature fatal alarm occurred."
        ::= { ibEntityExtRasTrapsPrefix 31 }

    ibEntityExtTemperatureFatalAlarmClear NOTIFICATION-TYPE
        OBJECTS {
            ibEntityExtPhysicalIndex,
            entPhysicalName,
            ibEntityExtRelativeResource,
            ibEntityExtErrorCode,
            ibEntityExtReason,
            ibEntityExtThresholdType,
            ibEntityExtThresholdVal,
            ibEntityExtCurrentVal
            }
        STATUS current
        DESCRIPTION
            "The trap is generated when a temperature fatal alarm cleared."
        ::= { ibEntityExtRasTrapsPrefix 32 }

    ibEntityExtTemperatureAlarmOccur NOTIFICATION-TYPE
        OBJECTS {
            ibEntityExtPhysicalIndex,
            entPhysicalName,
            ibEntityExtRelativeResource,
            ibEntityExtErrorCode,
            ibEntityExtReason,
            ibEntityExtThresholdType,
            ibEntityExtThresholdVal,
            ibEntityExtCurrentVal
            }
        STATUS current
        DESCRIPTION
            "The trap is generated when a temperature alarm occurred."
        ::= { ibEntityExtRasTrapsPrefix 33 }

    ibEntityExtTemperatureAlarmClear NOTIFICATION-TYPE
        OBJECTS {
            ibEntityExtPhysicalIndex,
            entPhysicalName,
            ibEntityExtRelativeResource,
            ibEntityExtErrorCode,
            ibEntityExtReason,
            ibEntityExtThresholdType,
            ibEntityExtThresholdVal,
            ibEntityExtCurrentVal
            }
        STATUS current
        DESCRIPTION
            "The trap is generated when a temperature alarm cleared."
        ::= { ibEntityExtRasTrapsPrefix 34 }

    ibEntityExtTemperatureWarningOccur NOTIFICATION-TYPE
        OBJECTS {
            ibEntityExtPhysicalIndex,
            entPhysicalName,
            ibEntityExtRelativeResource,
            ibEntityExtErrorCode,
            ibEntityExtReason,
            ibEntityExtThresholdType,
            ibEntityExtThresholdVal,
            ibEntityExtCurrentVal
            }
        STATUS current
        DESCRIPTION
            "The trap is generated when a temperature warning occurred."
        ::= { ibEntityExtRasTrapsPrefix 35 }

    ibEntityExtTemperatureWarningClear NOTIFICATION-TYPE
        OBJECTS {
            ibEntityExtPhysicalIndex,
            entPhysicalName,
            ibEntityExtRelativeResource,
            ibEntityExtErrorCode,
            ibEntityExtReason,
            ibEntityExtThresholdType,
            ibEntityExtThresholdVal,
            ibEntityExtCurrentVal
            }
        STATUS current
        DESCRIPTION
            "The trap is generated when a temperature warning cleared."
        ::= { ibEntityExtRasTrapsPrefix 36 }

    ibEntityExtClockFatalAlarmOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when a clock fatal alarm occurred."
        ::= { ibEntityExtRasTrapsPrefix 37 }

    ibEntityExtClockFatalAlarmClear NOTIFICATION-TYPE
        OBJECTS {
            ibEntityExtPhysicalIndex,
            entPhysicalName,
            ibEntityExtRelativeResource,
            ibEntityExtErrorCode,
            ibEntityExtReason
            }
        STATUS current
        DESCRIPTION
            "The trap is generated when a clock fatal alarm cleared."
        ::= { ibEntityExtRasTrapsPrefix 38 }

    ibEntityExtClockAlarmOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when a clock alarm occurred."
        ::= { ibEntityExtRasTrapsPrefix 39 }

    ibEntityExtClockAlarmClear NOTIFICATION-TYPE
        OBJECTS {
            ibEntityExtPhysicalIndex,
            entPhysicalName,
            ibEntityExtRelativeResource,
            ibEntityExtErrorCode,
            ibEntityExtReason
            }
        STATUS current
        DESCRIPTION
            "The trap is generated when a clock alarm cleared."
        ::= { ibEntityExtRasTrapsPrefix 40 }

    ibEntityExtClockWarningOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when a clock warning occurred."
        ::= { ibEntityExtRasTrapsPrefix 41 }

    ibEntityExtClockWarningClear NOTIFICATION-TYPE
        OBJECTS {
            ibEntityExtPhysicalIndex,
            entPhysicalName,
            ibEntityExtRelativeResource,
            ibEntityExtErrorCode,
            ibEntityExtReason
            }
        STATUS current
        DESCRIPTION
            "The trap is generated when a clock warning cleared."
        ::= { ibEntityExtRasTrapsPrefix 42 }

    ibEntityExtDiskFatalAlarmOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when a disk fatal alarm occurred."
        ::= { ibEntityExtRasTrapsPrefix 43 }

    ibEntityExtDiskFatalAlarmClear NOTIFICATION-TYPE
        OBJECTS {
            ibEntityExtPhysicalIndex,
            entPhysicalName,
            ibEntityExtRelativeResource,
            ibEntityExtErrorCode,
            ibEntityExtReason
            }
        STATUS current
        DESCRIPTION
            "The trap is generated when a disk fatal alarm cleared."
        ::= { ibEntityExtRasTrapsPrefix 44 }

    ibEntityExtDiskAlarmOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when a disk alarm occurred."
        ::= { ibEntityExtRasTrapsPrefix 45 }

    ibEntityExtDiskAlarmClear NOTIFICATION-TYPE
        OBJECTS {
            ibEntityExtPhysicalIndex,
            entPhysicalName,
            ibEntityExtRelativeResource,
            ibEntityExtErrorCode,
            ibEntityExtReason
            }
        STATUS current
        DESCRIPTION
            "The trap is generated when a disk alarm cleared."
        ::= { ibEntityExtRasTrapsPrefix 46 }

    ibEntityExtDiskWarningOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when a disk warning occurred."
        ::= { ibEntityExtRasTrapsPrefix 47 }

    ibEntityExtDiskWarningClear NOTIFICATION-TYPE
        OBJECTS {
            ibEntityExtPhysicalIndex,
            entPhysicalName,
            ibEntityExtRelativeResource,
            ibEntityExtErrorCode,
            ibEntityExtReason
            }
        STATUS current
        DESCRIPTION
            "The trap is generated when a disk warning cleared."
        ::= { ibEntityExtRasTrapsPrefix 48 }

    ibEntityExtOpticalFatalAlarmOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when an optical fatal alarm occurred."
        ::= { ibEntityExtRasTrapsPrefix 49 }

    ibEntityExtOpticalFatalAlarmClear NOTIFICATION-TYPE
        OBJECTS {
            ibEntityExtPhysicalIndex,
            entPhysicalName,
            ibEntityExtRelativeResource,
            ibEntityExtErrorCode,
            ibEntityExtReason
            }
        STATUS current
        DESCRIPTION
            "The trap is generated when an optical fatal alarm cleared."
        ::= { ibEntityExtRasTrapsPrefix 50 }

    ibEntityExtOpticalAlarmOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when an optical alarm occurred."
        ::= { ibEntityExtRasTrapsPrefix 51 }

    ibEntityExtOpticalAlarmClear NOTIFICATION-TYPE
        OBJECTS {
            ibEntityExtPhysicalIndex,
            entPhysicalName,
            ibEntityExtRelativeResource,
            ibEntityExtErrorCode,
            ibEntityExtReason
            }
        STATUS current
        DESCRIPTION
            "The trap is generated when an optical alarm cleared."
        ::= { ibEntityExtRasTrapsPrefix 52 }

    ibEntityExtOpticalWarningOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when an optical warning occurred."
        ::= { ibEntityExtRasTrapsPrefix 53 }

    ibEntityExtOpticalWarningClear NOTIFICATION-TYPE
        OBJECTS {
            ibEntityExtPhysicalIndex,
            entPhysicalName,
            ibEntityExtRelativeResource,
            ibEntityExtErrorCode,
            ibEntityExtReason
            }
        STATUS current
        DESCRIPTION
            "The trap is generated when an optical warning cleared."
        ::= { ibEntityExtRasTrapsPrefix 54 }

    ibEntityExtInternalLinkFatalAlarmOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when an internal link fatal alarm occurred."
        ::= { ibEntityExtRasTrapsPrefix 55 }

    ibEntityExtInternalLinkFatalAlarmClear NOTIFICATION-TYPE
        OBJECTS {
            ibEntityExtPhysicalIndex,
            entPhysicalName,
            ibEntityExtRelativeResource,
            ibEntityExtErrorCode,
            ibEntityExtReason
            }
        STATUS current
        DESCRIPTION
            "The trap is generated when an internal link fatal alarm cleared."
        ::= { ibEntityExtRasTrapsPrefix 56 }

    ibEntityExtInternalLinkAlarmOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when an internal link alarm occurred."
        ::= { ibEntityExtRasTrapsPrefix 57 }

    ibEntityExtInternalLinkAlarmClear NOTIFICATION-TYPE
        OBJECTS {
            ibEntityExtPhysicalIndex,
            entPhysicalName,
            ibEntityExtRelativeResource,
            ibEntityExtErrorCode,
            ibEntityExtReason
            }
        STATUS current
        DESCRIPTION
            "The trap is generated when an internal link alarm cleared."
        ::= { ibEntityExtRasTrapsPrefix 58 }

    ibEntityExtInternalLinkWarningOccur NOTIFICATION-TYPE
        OBJECTS {
            ibEntityExtPhysicalIndex,
            entPhysicalName,
            ibEntityExtRelativeResource,
            ibEntityExtErrorCode,
            ibEntityExtReason
            }
        STATUS current
        DESCRIPTION
            "The trap is generated when an internal link warning occurred."
        ::= { ibEntityExtRasTrapsPrefix 59 }

    ibEntityExtInternalLinkWarningClear NOTIFICATION-TYPE
        OBJECTS {
            ibEntityExtPhysicalIndex,
            entPhysicalName,
            ibEntityExtRelativeResource,
            ibEntityExtErrorCode,
            ibEntityExtReason
            }
        STATUS current
        DESCRIPTION
            "The trap is generated when an internal link warning cleared."
        ::= { ibEntityExtRasTrapsPrefix 60 }

    ibEntityExtRelativeResource OBJECT-TYPE
        SYNTAX      OCTET STRING(SIZE (0..255))
        MAX-ACCESS  accessible-for-notify
        STATUS      current
        DESCRIPTION
            "The relative resource of RAS trap."
        ::= { ibEntityExtRasTrapsInfor 1 }

    ibEntityExtErrorCode OBJECT-TYPE
        SYNTAX      Integer32
        MAX-ACCESS  accessible-for-notify
        STATUS      current
        DESCRIPTION
            "The error code of RAS trap."
        ::= { ibEntityExtRasTrapsInfor 2 }

    ibEntityExtReason OBJECT-TYPE
        SYNTAX      OCTET STRING(SIZE (0..255))
        MAX-ACCESS  accessible-for-notify
        STATUS      current
        DESCRIPTION
            "The reason of RAS trap."
        ::= { ibEntityExtRasTrapsInfor 3 }

    ibEntityExtThresholdType OBJECT-TYPE
        SYNTAX      OCTET STRING(SIZE (0..63))
        MAX-ACCESS  accessible-for-notify
        STATUS      current
        DESCRIPTION
            "The threshold type of RAS trap."
        ::= { ibEntityExtRasTrapsInfor 4 }

    ibEntityExtThresholdVal OBJECT-TYPE
        SYNTAX      OCTET STRING(SIZE (0..63))
        MAX-ACCESS  accessible-for-notify
        STATUS      current
        DESCRIPTION
            "The threshold value with unit of RAS trap."
        ::= { ibEntityExtRasTrapsInfor 5 }

    ibEntityExtCurrentVal OBJECT-TYPE
        SYNTAX      OCTET STRING(SIZE (0..63))
        MAX-ACCESS  accessible-for-notify
        STATUS      current
        DESCRIPTION
            "The current value with unit of RAS trap."
        ::= { ibEntityExtRasTrapsInfor 6 }

    END
