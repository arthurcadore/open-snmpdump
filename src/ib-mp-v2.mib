-- =================================================================
-- Copyright (C) 2023 Intelbras S.A. All rights reserved.
--
-- Description: This MIB file is used for querying MP (Multilink PPP)
--              link status information.
-- Reference:
-- Version: V1.2
-- History:
--   V1.0 Initial version 2013-07-15
--   V1.1 2013-10-08 updated by jinlei 07761
--        Added enum active(1) and inactive(2) to ibMpMemberlinkMpStatusV2
--   V1.2 2022-06-16 add ibMpRxLossPktAlarmTrapOid
--                   add ibMpRxLossPktAlarmTrap by wangzhenjun
-- =================================================================
IB-MP-V2-MIB DEFINITIONS ::= BEGIN

IMPORTS
    ibCommon
        FROM IB-OID-MIB
    ifIndex
        FROM IF-MIB
    Integer32, Counter32, OBJECT-TYPE, MODULE-IDENTITY, NOTIFICATION-TYPE
        FROM SNMPv2-SMI
    DisplayString
        FROM SNMPv2-TC;

ibMultilinkPPPV2 MODULE-IDENTITY
    LAST-UPDATED "202206160000Z"            -- June 16, 2022 at 00:00 GMT
    ORGANIZATION
        "Intelbras S.A. Industria de Telecomunicacao Eletronica Brasileria."
    CONTACT-INFO
        ""
    DESCRIPTION
         "Supporting the trap for MP(Multilink PPP)"
    REVISION "202206160000Z"        -- June 16, 2022 at 00:00 GMT
    DESCRIPTION
         "The IB-MP-V2-MIB provides read access to MP(Multilink PPP) link
          status information. The information available through this MIB includes:
          the father channel, the bundled son channel, the slot on which son channels
          are bundled,
          the number of son channels, the bundle name,
          the statistics for lost fragments, reordered packets, unassigned packets,
          interleaved packets, and the received/sent sequence number, etc."
    REVISION "201307150000Z"        -- July 15, 2013 at 00:00 GMT
    DESCRIPTION
        "IB-MP-V2-MIB module for managing MP(Multilink PPP)."
    ::= { ibCommon 140 }


ibMpObjectsV2 OBJECT IDENTIFIER ::= { ibMultilinkPPPV2  1 }

ibMpMultilinkV2Table OBJECT-TYPE
    SYNTAX SEQUENCE OF IbMpMultilinkV2Entry
    MAX-ACCESS not-accessible
    STATUS current
    DESCRIPTION
        "This table describes the information of MP link.
         The index of this table is the interface index of MP group or
         VA (Virtual Access) interface."
    ::= { ibMpObjectsV2 1 }

ibMpMultilinkV2Entry OBJECT-TYPE
    SYNTAX IbMpMultilinkV2Entry
    MAX-ACCESS not-accessible
    STATUS current
    DESCRIPTION
        "Each entry in this table describes the information of MP link.
         The available information includes:
         the father channel, the slot on which son channels are bundled,
         the number of bundled son channels,
         the statistics for lost fragments, reordered packets,
         unassigned packets, interleaved packets,
         and received/sent sequence number."
    INDEX { ifIndex }
    ::= { ibMpMultilinkV2Table 1 }

IbMpMultilinkV2Entry ::=
    SEQUENCE {
        ibMpMultilinkDescrV2
            DisplayString,
        ibMpBundleNameV2
            DisplayString,
        ibMpBundledSlotV2
            Integer32,
        ibMpBundledMemberCntV2
            Integer32,
        ibMpLostFragmentsV2
            Counter32,
        ibMpReorderedPktsV2
            Counter32,
        ibMpUnassignedPktsV2
            Counter32,
        ibMpInterleavedPktsV2
            Counter32,
        ibMpRcvdSequenceV2
            Integer32,
        ibMpSentSequenceV2
            Integer32
        }

ibMpMultilinkDescrV2 OBJECT-TYPE
    SYNTAX DisplayString (SIZE (0..255))
    MAX-ACCESS read-only
    STATUS current
    DESCRIPTION
        "The interface name of the father interface on which son channels are bundled.
        It is the name of a Virtual Access or an MP group."
    ::= { ibMpMultilinkV2Entry 1 }

ibMpBundleNameV2 OBJECT-TYPE
    SYNTAX DisplayString (SIZE (0..255))
    MAX-ACCESS read-only
    STATUS current
    DESCRIPTION
        "The bundle name of the multilink.
        When authentication is configured, the bundle name is the authenticated
        user name; when authentication is not configured, the bundle name is
        multilink.
        "
    ::= { ibMpMultilinkV2Entry 2 }

ibMpBundledSlotV2 OBJECT-TYPE
    SYNTAX Integer32
    MAX-ACCESS read-only
    STATUS current
    DESCRIPTION
        "The slot on which son channels are bundled.
        "
    ::= { ibMpMultilinkV2Entry 3 }

ibMpBundledMemberCntV2 OBJECT-TYPE
    SYNTAX Integer32
    MAX-ACCESS read-only
    STATUS current
    DESCRIPTION
        "The number of the bundled son channel of the MP link. "
    ::= { ibMpMultilinkV2Entry 4 }

ibMpLostFragmentsV2 OBJECT-TYPE
    SYNTAX Counter32
    MAX-ACCESS read-only
    STATUS current
    DESCRIPTION
        "The number of fragments of the MP link discarded because
        bad fragments were received, or assembling the packet failed, etc."
    ::= { ibMpMultilinkV2Entry 5 }

ibMpReorderedPktsV2 OBJECT-TYPE
    SYNTAX Counter32
    MAX-ACCESS read-only
    STATUS current
    DESCRIPTION
        "The number of reordered incoming packets of the MP link.
        "
    ::= { ibMpMultilinkV2Entry 6 }

ibMpUnassignedPktsV2 OBJECT-TYPE
    SYNTAX Counter32
    MAX-ACCESS read-only
    STATUS current
    DESCRIPTION
        "The number of received packets of the MP link waiting for reordering.
        "
    ::= { ibMpMultilinkV2Entry 7 }

ibMpInterleavedPktsV2 OBJECT-TYPE
    SYNTAX Counter32
    MAX-ACCESS read-only
    STATUS current
    DESCRIPTION
        "The number of received packets of the MP link interleaved by the
        packets queued in RTPQ (Real-time Transport Protocol Queue) or
        LLQ (Low Latency Queue).
        "
    ::= { ibMpMultilinkV2Entry 8 }

ibMpRcvdSequenceV2 OBJECT-TYPE
    SYNTAX Integer32
    MAX-ACCESS read-only
    STATUS current
    DESCRIPTION
        "The current sequence number for the MP link to receive.
        "
    ::= { ibMpMultilinkV2Entry 9 }

ibMpSentSequenceV2 OBJECT-TYPE
    SYNTAX Integer32
    MAX-ACCESS read-only
    STATUS current
    DESCRIPTION
        "The current sequence number for the MP link to send.
        "
    ::= { ibMpMultilinkV2Entry 10 }


ibMpMemberlinkV2Table OBJECT-TYPE
    SYNTAX SEQUENCE OF IbMpMemberlinkV2Entry
    MAX-ACCESS not-accessible
    STATUS current
    DESCRIPTION
        "This table describes the information of son channels of the MP link.
        The index of this table is the interface index of MP group or
        VA (Virtual Access) interface.
        "
    ::= { ibMpObjectsV2 2 }

ibMpMemberlinkV2Entry OBJECT-TYPE
    SYNTAX IbMpMemberlinkV2Entry
    MAX-ACCESS not-accessible
    STATUS current
    DESCRIPTION
        "Each entry in this table describes the information of the bundled
        son channels of MP link. The available information includes:
        the interface index of the son channel,
        the interface name of the son channel.
        "
    INDEX { ifIndex, ibMpMemberlinkSeqNumberV2 }
    ::= { ibMpMemberlinkV2Table 1 }

IbMpMemberlinkV2Entry ::=
    SEQUENCE {
        ibMpMemberlinkSeqNumberV2
            Integer32,
        ibMpMemberlinkIfIndexV2
            Integer32,
        ibMpMemberlinkDescrV2
            DisplayString,
        ibMpMemberlinkMpStatusV2
            INTEGER
    }

ibMpMemberlinkSeqNumberV2 OBJECT-TYPE
    SYNTAX Integer32 (1..128)
    MAX-ACCESS read-only
    STATUS current
    DESCRIPTION
        "The bundled sequence number of the son channels of the MP link.
        This object is one of the index of the table.
        "
    ::= { ibMpMemberlinkV2Entry 1 }

ibMpMemberlinkIfIndexV2 OBJECT-TYPE
    SYNTAX Integer32
    MAX-ACCESS read-only
    STATUS current
    DESCRIPTION
        "The interface index of the son channels of the MP link.
        "
    ::= { ibMpMemberlinkV2Entry 2 }

ibMpMemberlinkDescrV2 OBJECT-TYPE
    SYNTAX DisplayString (SIZE (0..255))
    MAX-ACCESS read-only
    STATUS current
    DESCRIPTION
        "The interface name of the son channels of the MP link.
        "
    ::= { ibMpMemberlinkV2Entry 3 }

ibMpMemberlinkMpStatusV2 OBJECT-TYPE
    SYNTAX INTEGER
        {
            active(1),
            inactive(2)
        }
    MAX-ACCESS read-only
    STATUS current
    DESCRIPTION
        "The MP status of the son channels of the MP link.
        "
    ::= { ibMpMemberlinkV2Entry 4 }

ibMpRxLossPktAlarmTrapOid OBJECT IDENTIFIER ::= { ibMpObjectsV2 3 }

ibMpRxLossAlarmIfName OBJECT-TYPE
    SYNTAX      DisplayString (SIZE (1..47))
    MAX-ACCESS  accessible-for-notify
    STATUS      current
    DESCRIPTION
        "The involved MP group interface name of trap information."
    ::= { ibMpRxLossPktAlarmTrapOid 1 }

ibMpRxLossCurValueString OBJECT-TYPE
    SYNTAX      DisplayString (SIZE (1..31))
    MAX-ACCESS  accessible-for-notify
    STATUS      current
    DESCRIPTION
        "The involved current loss rate of received packet of
         trap information."
    ::= { ibMpRxLossPktAlarmTrapOid 2 }

ibMpRxLossAlarmValueString OBJECT-TYPE
    SYNTAX      DisplayString (SIZE (1..31))
    MAX-ACCESS  accessible-for-notify
    STATUS      current
    DESCRIPTION
        "The involved alarm threshold of received packet dropped
         of trap information."
    ::= { ibMpRxLossPktAlarmTrapOid 3 }

ibMpRxLossResumeValueString OBJECT-TYPE
    SYNTAX      DisplayString (SIZE (1..31))
    MAX-ACCESS  accessible-for-notify
    STATUS      current
    DESCRIPTION
        "The involved resume threshold of received packet dropped
         of trap information."
    ::= { ibMpRxLossPktAlarmTrapOid 4 }

ibMpRxLossPktAlarmTrap OBJECT IDENTIFIER  ::= { ibMpObjectsV2 4 }

ibMpRxLossPktAlarmTrapPrefix OBJECT IDENTIFIER  ::= { ibMpRxLossPktAlarmTrap 0 }

ibMpRxLossPktAlarm NOTIFICATION-TYPE
    OBJECTS
    {
        ibMpRxLossAlarmIfName,
        ibMpRxLossCurValueString,
        ibMpRxLossAlarmValueString,
        ibMpRxLossResumeValueString
    }
    STATUS      current
    DESCRIPTION
        "This trap is generated when the rate of received packets dropped
         exceds the alarm threshold."
    ::= { ibMpRxLossPktAlarmTrapPrefix 1 }

ibMpRxLossPktAlarmResume NOTIFICATION-TYPE
    OBJECTS
    {
        ibMpRxLossAlarmIfName,
        ibMpRxLossCurValueString,
        ibMpRxLossAlarmValueString,
        ibMpRxLossResumeValueString
    }
    STATUS      current
    DESCRIPTION
        "This trap is generated when the rate of received packets dropped
         drops below the resume threshold."
    ::= { ibMpRxLossPktAlarmTrapPrefix 2 }
END
