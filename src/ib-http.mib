-- =================================================================
-- Copyright (C) 2023 Intelbras S.A. All rights reserved.
--
-- Description: HTTP mib
-- Reference:
-- Version: V1.0
-- History:
--  V1.0 Created by xiexiang
--      Initial version 2022-09-13
-- =================================================================
IB-HTTP-MIB DEFINITIONS ::= BEGIN

IMPORTS
    MODULE-IDENTITY, OBJECT-TYPE, NOTIFICATION-TYPE
        FROM SNMPv2-SMI
    DisplayString
        FROM SNMPv2-TC
    InetAddressType
        FROM INET-ADDRESS-MIB
    ibCommon
        FROM IB-OID-MIB;

ibHttp MODULE-IDENTITY
    LAST-UPDATED "202209130000Z"
    ORGANIZATION
        "Intelbras S.A. Industria de Telecomunicacao Eletronica Brasileria."
    CONTACT-INFO
        ""
    DESCRIPTION
        "The MIB module is used for HTTP connection notification."
    REVISION    "202209130000Z"
    DESCRIPTION    "The initial version."
    ::= { ibCommon 255 }

-- ==================================================================
--
-- HTTP trap object
--
-- ==================================================================
ibHttpObjects OBJECT IDENTIFIER ::= { ibHttp 1 }

ibHttpConnObjects OBJECT IDENTIFIER ::= { ibHttpObjects 1 }

ibHttpUserName OBJECT-TYPE
    SYNTAX       DisplayString (SIZE(1..80))
    MAX-ACCESS   accessible-for-notify
    STATUS   current
    DESCRIPTION
    "The name of an HTTP user."
    ::= { ibHttpConnObjects 1 }

ibHttpUserIPAddressType OBJECT-TYPE
    SYNTAX       InetAddressType
    MAX-ACCESS   accessible-for-notify
    STATUS   current
    DESCRIPTION
    "The IP address type of the HTTP user."
    ::= { ibHttpConnObjects 2 }

ibHttpUserIPAddress OBJECT-TYPE
    SYNTAX       DisplayString (SIZE(1..80))
    MAX-ACCESS   accessible-for-notify
    STATUS   current
    DESCRIPTION
    "The IP address of the HTTP user."
    ::= { ibHttpConnObjects 3 }

ibHttpUserService OBJECT-TYPE
    SYNTAX       DisplayString (SIZE(1..80))
    MAX-ACCESS   accessible-for-notify
    STATUS   current
    DESCRIPTION
    "The service type of the HTTP user, such as web and soap."
    ::= { ibHttpConnObjects 4 }

ibHttpTrap OBJECT IDENTIFIER ::= { ibHttp 2 }

ibHttpConnTrapPrefix OBJECT IDENTIFIER ::= { ibHttpTrap 0 }

ibHttpUserLogin NOTIFICATION-TYPE
    OBJECTS {
            ibHttpUserName,
            ibHttpUserIPAddressType,
            ibHttpUserIPAddress,
            ibHttpUserService
        }
    STATUS  current
    DESCRIPTION
        "This notification is generated when a user logs in successfully through HTTP."
::= { ibHttpConnTrapPrefix 1 }

ibHttpUserLoginFail NOTIFICATION-TYPE
    OBJECTS {
            ibHttpUserName,
            ibHttpUserIPAddressType,
            ibHttpUserIPAddress,
            ibHttpUserService
        }
    STATUS  current
    DESCRIPTION
        "This notification is generated when a user fails to log in through HTTP."
::= { ibHttpConnTrapPrefix 2 }

ibHttpUserLogout NOTIFICATION-TYPE
    OBJECTS {
            ibHttpUserName,
            ibHttpUserIPAddressType,
            ibHttpUserIPAddress,
            ibHttpUserService
        }
    STATUS  current
    DESCRIPTION
        "This notification is generated when a user logs out successfully through HTTP."
::= { ibHttpConnTrapPrefix 3 }

END
