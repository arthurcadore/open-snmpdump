-- =============================================================================
-- Copyright (C) 2023 Intelbras S.A. All rights reserved.
--
-- Description:
--   The file defines a MIB to provide MESH configuration information.
-- Reference:
-- Version: V1.6
-- History:
--   V1.0 2008-07-08 Initial version, created by ChangHuifeng
--   V1.1 2008-11-07 modified by liyugang
--        Add ibDot11sMeshLinkStatisTable, ibDot11sMeshNbrStatusTable
--        to ibDot11sMeshStatusGroup
--   V1.2 2009-08-01 modified by Wang Shaojie
--        Add ibDot11sMeshLinkIFName to ibDot11sMeshLinkStatisTable.
--   V1.3 2013-09-14 modified by Zhang Siyu
--        Add ibDot11sMeshLinkType to ibDot11sMeshLinkStatusTable
--   V1.4 2015-02-02 modified by Xiao min
--        Add ibDot11sMeshLinkSNR to ibDot11sMeshLinkStatusTable
--        Add ibDot11sMeshLinkNoise to ibDot11sMeshLinkStatusTable
--        Add ibDot11sMeshLinkPeerSNR to ibDot11sMeshLinkStatusTable
--        Add ibDot11sMeshLinkPeerNoise to ibDot11sMeshLinkStatusTable
--   V1.5 2015-05-6 modified by guoxuzhen
--        Add ibDot11sMeshAKMMode, ibDot11sSimplerKey to IbDot11sMeshPflTable
--        Add ibDot11sBindInterface to ibDot11sRadioCfgTable
--        2015-08-14 modified by Xiao min
--        Add ibDot11sMeshLinkPeerIPAddress to ibDot11sMeshLinkStatusTable
--        Add ibDot11sMeshLinkPeerSystemName to ibDot11sMeshLinkStatusTable
--   V1.6 2018-05-15 modified by liuxiaolong
--        Add ibDot11sMlspExtCfgTable to ibDot11sConfigGroup
--        Add ibDot11sMeshLinkNotifyGroup to ibDot11sMesh
--        Add ibDot11sMlspMode to ibDot11sMpPlcyTable
--        Add ibDot11sWaveGuideHoldRSSI to ibDot11sMpPlcyTable
--        Add ibDot11sWaveGuideSwitch to ibDot11sMpPlcyTable
--        Add ibDot11sOptimizeEnable to ibDot11sMpPlcyTable
--        Add ibDot11sOptimizeThreshold to ibDot11sMpPlcyTable
--        Add ibDot11sMlspLogEnable to ibDot11sMpPlcyTable
--        Add ibDot11sMlspLogInterval to ibDot11sMpPlcyTable
--        Add ibDot11sActiveKeepaliveCount to ibDot11sMpPlcyTable
--        Add ibDot11sLinkEstaThreshold to ibDot11sMpPlcyTable
--        Add ibDot11sTransmissionMethod to ibDot11sMpPlcyTable
--        Add ibDot11sTransmitLevel to ibDot11sMpPlcyTable
--        Add ibDot11sTempLinkEnable to ibDot11sMpPlcyTable
-- =============================================================================
IB-DOT11S-MESH-MIB DEFINITIONS ::= BEGIN

IMPORTS
        TruthValue,
        MacAddress,
        RowStatus
    FROM SNMPv2-TC
        MODULE-IDENTITY,
        OBJECT-TYPE,
        Integer32,
        Unsigned32,
        Counter32,
        IpAddress,
        NOTIFICATION-TYPE
    FROM SNMPv2-SMI
        ibDot11, IbDot11RadioElementIndex, ibDot11APElementIndex, IbDot11AKMType
    FROM IB-DOT11-REF-MIB;

ibDot11sMesh MODULE-IDENTITY
    LAST-UPDATED "201805151000Z"        -- May 15, 2018 at 10:00 GMT
    ORGANIZATION
        "Intelbras S.A. Industria de Telecomunicacao Eletronica Brasileria."
    CONTACT-INFO
        ""
    DESCRIPTION
        "The file defines a MIB to provide MESH configuration information.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Fat AP
        Applied in the home, SOHO and so on, and it could
        work independently without help from AC.

        Fit AP
        Applied in the enterprise environment, it will work
        under the control and management from AC.

        BSS
        IEEE 802.11 Basic Service Set (Radio Cell).  The
        BSS of an AP comprises of the stations directly
        associating with the AP.

        Radio
        The chip set to receive and send wireless signal.

        Mesh
        A network consisting of two or more mesh points
        which communicate with each other via mesh services.

        Mesh Point (MP)
        An IEEE 802.11 entity that contains an IEEE 802.11-conformant
        medium access control (MAC) and physical layer (PHY) interface
        to the wireless medium (WM) that supports mesh services.

        Mesh Access Point (MAP)
        A mesh point that is collocated with one or more access points.

        Mesh Portal Point (MPP)
        A mesh point that is collocated with one or more portals.

        Mesh Link
        A link between two MPs.

        Simultaneous Authentication of Equals (SAE)
        A password-authenticated key exchange based on
        a zero-knowledge proof."
    REVISION "201805151000Z"        -- May 15, 2018 at 10:00 GMT
    DESCRIPTION
        "Add new nodes and new table"
    REVISION "201508141000Z"        -- Aug 01, 2009 at 10:00 GMT
    DESCRIPTION
        "Add ibDot11sMeshLinkPeerIPAddress to ibDot11sMeshLinkStatusTable,
         Add ibDot11sMeshLinkPeerSystemName to ibDot11sMeshLinkStatusTable"
    REVISION "201505061500Z"        -- May 6, 2015 at 15:00 GMT
    DESCRIPTION
        "Add new nodes."
    REVISION "200908011000Z"        -- Aug 01, 2009 at 10:00 GMT
    DESCRIPTION
        "Add new nodes."
    REVISION "200811071000Z"        -- Nov 07, 2008 at 10:00 GMT
    DESCRIPTION
        "Modified to add new nodes and a new table."
    REVISION "200807081800Z"        -- July 8, 2008 at 18:00 GMT
    DESCRIPTION
        "The initial revision of this MIB module."
    ::= { ibDot11 11 }

-- *****************************************************************************
-- *  Major sections
-- *****************************************************************************

ibDot11sConfigGroup OBJECT IDENTIFIER  ::= { ibDot11sMesh 1 }
--  Dot11s Configuration Group has the following children:
--  ibDot11sMeshGlobalPara             ::= { ibDot11sConfigGroup 1 }
--  ibDot11sMeshPflTable               ::= { ibDot11sConfigGroup 2 }
--  ibDot11sMpPlcyTable                ::= { ibDot11sConfigGroup 3 }
--  ibDot11sMlspCfgTable               ::= { ibDot11sConfigGroup 4 }
--  ibDot11sRadioCfgTable              ::= { ibDot11sConfigGroup 5 }
--  ibDot11sAPCfgTable                 ::= { ibDot11sConfigGroup 6 }
--  ibDot11sMlspExtCfgTable            ::= { ibDot11sConfigGroup 7 }

ibDot11sWDSConfigGroup OBJECT IDENTIFIER ::= { ibDot11sMesh 2 }
--  Dot11s WDS Configuration Group has the following children:
--  ibDot11sWDSPeerMacTable         ::= { ibDot11sWDSConfigGroup 1 }

ibDot11sMeshStatusGroup OBJECT IDENTIFIER ::= { ibDot11sMesh 3 }
--  Dot11s Mesh Status Group has the following children:
--  ibDot11sMeshLinkStatusTable    ::= { ibDot11sMeshStatusGroup 1 }
--  ibDot11sMeshLinkStatisTable    ::= { ibDot11sMeshStatusGroup 2 }
--  ibDot11sMeshNbrStatusTable     ::= { ibDot11sMeshStatusGroup 3 }

ibDot11sMeshLinkNotifyGroup OBJECT IDENTIFIER ::= { ibDot11sMesh 4 }
-- *****************************************************************************
-- *  ibDot11sMeshGlobalPara Definition
-- *****************************************************************************
ibDot11sMeshGlobalPara OBJECT IDENTIFIER  ::= { ibDot11sConfigGroup 1 }

ibDot11sMeshMkdID OBJECT-TYPE
    SYNTAX      MacAddress
    MAX-ACCESS  read-write
    STATUS      current
    DESCRIPTION
        "This object represents the mesh key distributor identifier (MKD-ID).
        If the MKD-ID is not configured, the value is '00:00:00:00:00:00'."
    ::= { ibDot11sMeshGlobalPara 1 }

-- *****************************************************************************
-- * End of ibDot11sMeshGlobalPara Definition
-- *****************************************************************************
-- *****************************************************************************
-- *  ibDot11sMeshPflTable Definition
-- *****************************************************************************
ibDot11sMeshPflTable OBJECT-TYPE
    SYNTAX      SEQUENCE OF IbDot11sMeshPflEntry
    MAX-ACCESS  not-accessible
    STATUS      current
    DESCRIPTION
        "This table is used to configure mesh profile.
        A mesh profile is created and mapped to a MP so that
        it can provide mesh services to other MPs which have the same
        mesh ID.
        When the mesh profile is enabled, all of the object in this table
        cannot be modified except ibDot11sMeshPflEnable.
        The mesh profile cannot be deleted when it is bound with the radio."
    ::= { ibDot11sConfigGroup 2 }

ibDot11sMeshPflEntry OBJECT-TYPE
    SYNTAX      IbDot11sMeshPflEntry
    MAX-ACCESS  not-accessible
    STATUS      current
    DESCRIPTION
        "Each entry contains information of a mesh profile."
    INDEX
        {
            ibDot11sMeshPflIndex
        }
    ::= { ibDot11sMeshPflTable 1 }

IbDot11sMeshPflEntry ::= SEQUENCE
    {
        ibDot11sMeshPflIndex         Integer32,
        ibDot11sMeshPflMeshID        OCTET STRING,
        ibDot11sMeshPflBindIntNum    Integer32,
        ibDot11sMeshPflKeepAlive     Integer32,
        ibDot11sMeshPflBackhaulRate  Integer32,
        ibDot11sMeshMkdServEnable    TruthValue,
        ibDot11sMeshPflEnable        TruthValue,
        ibDot11sMeshPflRowStatus     RowStatus,
        ibDot11sMeshAKMMode          IbDot11AKMType,
        ibDot11sMeshSimpleKey        OCTET STRING
    }

ibDot11sMeshPflIndex OBJECT-TYPE
    SYNTAX      Integer32
    MAX-ACCESS  not-accessible
    STATUS      current
    DESCRIPTION
        "This object represents the index of the mesh profile."
    ::= { ibDot11sMeshPflEntry 1 }

ibDot11sMeshPflMeshID OBJECT-TYPE
    SYNTAX      OCTET STRING (SIZE (0..32))
    MAX-ACCESS  read-create
    STATUS      current
    DESCRIPTION
        "This object represents the mesh ID of the mesh profile.
        The string length of this object is zero when the mesh ID is not
        configured.  If the mesh ID is not configured, ibDot11sMeshPflEnable
        cannot be set to 'true'."
    ::= { ibDot11sMeshPflEntry 2 }

ibDot11sMeshPflBindIntNum OBJECT-TYPE
    SYNTAX      Integer32
    MAX-ACCESS  read-create
    STATUS      current
    DESCRIPTION
        "This object represents the specified mesh interface number
        bound to the mesh profile.
        If the value is set to -1, the binding will be removed."
    DEFVAL      { -1 }
    ::= { ibDot11sMeshPflEntry 3 }

ibDot11sMeshPflKeepAlive OBJECT-TYPE
    SYNTAX      Integer32(1..1800)
    UNITS       "second"
    MAX-ACCESS  read-create
    STATUS      current
    DESCRIPTION
        "This object represents the mesh link keep-alive interval."
    ::= { ibDot11sMeshPflEntry 4 }

ibDot11sMeshPflBackhaulRate OBJECT-TYPE
    SYNTAX      Integer32
    UNITS       "Kbps"
    MAX-ACCESS  read-create
    STATUS      current
    DESCRIPTION
        "This object represents the link backhaul rate."
    ::= { ibDot11sMeshPflEntry 5 }

ibDot11sMeshMkdServEnable OBJECT-TYPE
    SYNTAX      TruthValue
    MAX-ACCESS  read-create
    STATUS      current
    DESCRIPTION
        "This object indicates whether the mesh key distributor (MKD)
        service for the mesh profile is enabled.
        'true': The MKD service for the mesh profile is enabled.
        'false': The MKD service for the mesh profile is disabled."
    DEFVAL      { false }
    ::= { ibDot11sMeshPflEntry 6 }

ibDot11sMeshPflEnable OBJECT-TYPE
    SYNTAX      TruthValue
    MAX-ACCESS  read-create
    STATUS      current
    DESCRIPTION
        "This object indicates whether the mesh profile is enabled.
        'true': The mesh profile is enabled.
        'false': The mesh profile is disabled."
    DEFVAL      { false }
    ::= { ibDot11sMeshPflEntry 7 }

ibDot11sMeshPflRowStatus OBJECT-TYPE
    SYNTAX      RowStatus
    MAX-ACCESS  read-create
    STATUS      current
    DESCRIPTION
        "The status of this table entry."
    ::= { ibDot11sMeshPflEntry 8 }

ibDot11sMeshAKMMode OBJECT-TYPE
    SYNTAX      IbDot11AKMType
    MAX-ACCESS  read-create
    STATUS      current
    DESCRIPTION
        "Represents the authentication and key management mode defined by 802.11s.
        The following values are supported:
        'none': No key management mode configured.
        'psk': pre-shared key authentication."
    DEFVAL      { none }
    ::= { ibDot11sMeshPflEntry 9 }

ibDot11sMeshSimpleKey OBJECT-TYPE
    SYNTAX      OCTET STRING
    MAX-ACCESS  read-create
    STATUS      current
    DESCRIPTION
        "Represents the simple key for SAE."
    ::= { ibDot11sMeshPflEntry 10 }

-- *****************************************************************************
-- * End of ibDot11sMeshPflTable Definition
-- *****************************************************************************
-- *****************************************************************************
-- *  ibDot11sMpPlcyTable Definition
-- *****************************************************************************
ibDot11sMpPlcyTable OBJECT-TYPE
    SYNTAX      SEQUENCE OF IbDot11sMpPlcyEntry
    MAX-ACCESS  not-accessible
    STATUS      current
    DESCRIPTION
        "This table is used to configure MP policy.
        There is a default policy on system and its index is 1.
        The default policy cannot be deleted or modified.
        The MP policy cannot be deleted when it is applied to a radio."
    ::= { ibDot11sConfigGroup 3 }

ibDot11sMpPlcyEntry OBJECT-TYPE
    SYNTAX      IbDot11sMpPlcyEntry
    MAX-ACCESS  not-accessible
    STATUS      current
    DESCRIPTION
        "Each entry contains information of a MP policy."
    INDEX
        {
            ibDot11sMpPlcyIndex
        }
    ::= { ibDot11sMpPlcyTable 1 }

IbDot11sMpPlcyEntry ::= SEQUENCE
    {
        ibDot11sMpPlcyIndex          Integer32,
        ibDot11sMpPlcyName           OCTET STRING,
        ibDot11sMpPlcyInitEnable     TruthValue,
        ibDot11sMlspEnable           TruthValue,
        ibDot11sProbReqInterval      Integer32,
        ibDot11sRoleAuthEnable       TruthValue,
        ibDot11sLinkHoldRSSI         Integer32,
        ibDot11sLinkHoldTime         Integer32,
        ibDot11sSwitchMargin         Integer32,
        ibDot11sLinkSaturationRSSI   Integer32,
        ibDot11sLinkRateMode         INTEGER,
        ibDot11sMaxLinkNum           Integer32,
        ibDot11sMpPlcyRowStatus      RowStatus,
        ibDot11sMlspMode             INTEGER,
        ibDot11sWaveGuideHoldRSSI    Integer32,
        ibDot11sWaveGuideSwitch      TruthValue,
        ibDot11sOptimizeEnable       TruthValue,
        ibDot11sOptimizeThreshold    Integer32,
        ibDot11sMlspLogEnable        TruthValue,
        ibDot11sMlspLogInterval      Integer32,
        ibDot11sActiveKeepaliveCount Integer32,
        ibDot11sLinkEstaThreshold    Integer32,
        ibDot11sTransmissionMethod   INTEGER,
        ibDot11sTransmitLevel        Integer32,
        ibDot11sTempLinkEnable       TruthValue
    }

ibDot11sMpPlcyIndex OBJECT-TYPE
    SYNTAX      Integer32
    MAX-ACCESS  not-accessible
    STATUS      current
    DESCRIPTION
        "This object represents the MP policy index."
    ::= { ibDot11sMpPlcyEntry 1 }

ibDot11sMpPlcyName OBJECT-TYPE
    SYNTAX      OCTET STRING (SIZE (1..31))
    MAX-ACCESS  read-create
    STATUS      current
    DESCRIPTION
        "This object represents the MP policy name.
        MP policy cannot be created with the name of the
        default policy.
        Modification is not supported."
    ::= { ibDot11sMpPlcyEntry 2 }

ibDot11sMpPlcyInitEnable OBJECT-TYPE
    SYNTAX      TruthValue
    MAX-ACCESS  read-create
    STATUS      current
    DESCRIPTION
        "This object indicates whether the link initiation for
        the MP policy is enabled.
        'true': The link initiation for the MP policy is enabled.
        'false': The link initiation for the MP policy is disabled."
    DEFVAL      { true }
    ::= { ibDot11sMpPlcyEntry 3 }

ibDot11sMlspEnable OBJECT-TYPE
    SYNTAX      TruthValue
    MAX-ACCESS  read-create
    STATUS      current
    DESCRIPTION
        "This object indicates whether the mesh link switch protocol (MLSP)
        is enabled.
        'true': MLSP is enabled.
        'false': MLSP is disabled."
    DEFVAL      { false }
    ::= { ibDot11sMpPlcyEntry 4 }

ibDot11sProbReqInterval OBJECT-TYPE
    SYNTAX      Integer32
    UNITS       "millisecond"
    MAX-ACCESS  read-create
    STATUS      current
    DESCRIPTION
        "This object represents the probe request interval."
    ::= { ibDot11sMpPlcyEntry 5 }

ibDot11sRoleAuthEnable OBJECT-TYPE
    SYNTAX      TruthValue
    MAX-ACCESS  read-create
    STATUS      current
    DESCRIPTION
        "This object indicates whether the device can play as the role
        of an authenticator."
    DEFVAL      { true }
    ::= { ibDot11sMpPlcyEntry 6 }

ibDot11sLinkHoldRSSI OBJECT-TYPE
    SYNTAX      Integer32(5..100)
    UNITS       "dBm"
    MAX-ACCESS  read-create
    STATUS      current
    DESCRIPTION
        "This object represents the link-hold
        receive signal strength indicator (RSSI)."
    ::= { ibDot11sMpPlcyEntry 7 }

ibDot11sLinkHoldTime OBJECT-TYPE
    SYNTAX      Integer32(1000..20000)
    UNITS       "millisecond"
    MAX-ACCESS  read-create
    STATUS      current
    DESCRIPTION
        "This object represents the link-hold time."
    ::= { ibDot11sMpPlcyEntry 8 }

ibDot11sSwitchMargin OBJECT-TYPE
    SYNTAX      Integer32(1..100)
    UNITS       "dBm"
    MAX-ACCESS  read-create
    STATUS      current
    DESCRIPTION
        "This object represents the link-switch margin."
    ::= { ibDot11sMpPlcyEntry 9 }

ibDot11sLinkSaturationRSSI OBJECT-TYPE
    SYNTAX      Integer32(30..150)
    UNITS       "dBm"
    MAX-ACCESS  read-create
    STATUS      current
    DESCRIPTION
        "This object represents the link saturation
        receive signal strength indicator (RSSI)."
    ::= { ibDot11sMpPlcyEntry 10 }

ibDot11sLinkRateMode OBJECT-TYPE
    SYNTAX      INTEGER
        {
            fixed(1),
            realtime(2)
        }
    MAX-ACCESS  read-create
    STATUS      current
    DESCRIPTION
        "This object represents the rate mode of the mesh link."
    DEFVAL      { fixed }
    ::= { ibDot11sMpPlcyEntry 11 }

ibDot11sMaxLinkNum OBJECT-TYPE
    SYNTAX      Integer32
    MAX-ACCESS  read-create
    STATUS      current
    DESCRIPTION
        "This object represents the maximum number of the mesh link."
    ::= { ibDot11sMpPlcyEntry 12 }

ibDot11sMpPlcyRowStatus OBJECT-TYPE
    SYNTAX      RowStatus
    MAX-ACCESS  read-create
    STATUS      current
    DESCRIPTION
        "The status of this table entry."
    ::= { ibDot11sMpPlcyEntry 13 }

ibDot11sMlspMode OBJECT-TYPE
    SYNTAX      INTEGER
        {
            normal(0),
            satble(1)
        }
    MAX-ACCESS  read-create
    STATUS      current
    DESCRIPTION
        "This object represents the MLSP mode."
    DEFVAL      { normal }
    ::= { ibDot11sMpPlcyEntry 14 }

ibDot11sWaveGuideHoldRSSI OBJECT-TYPE
    SYNTAX      Integer32(5..100)
    UNITS       "dBm"
    MAX-ACCESS  read-create
    STATUS      current
    DESCRIPTION
        "This object represents the link-hold
        receive signal strength indicator (RSSI) of wave guides."
    DEFVAL      { 15 }
    ::= { ibDot11sMpPlcyEntry 15 }

ibDot11sWaveGuideSwitch OBJECT-TYPE
    SYNTAX      TruthValue
    MAX-ACCESS  read-create
    STATUS      current
    DESCRIPTION
        "This object represents the wave-guide switch state."
    DEFVAL      { false }
    ::= { ibDot11sMpPlcyEntry 16 }

ibDot11sOptimizeEnable OBJECT-TYPE
    SYNTAX      TruthValue
    MAX-ACCESS  read-create
    STATUS      current
    DESCRIPTION
        "This object indicates whether the mesh link switch protocol (MLSP)
        optimization function is enabled."
    DEFVAL      { false }
    ::= { ibDot11sMpPlcyEntry 17 }

ibDot11sOptimizeThreshold OBJECT-TYPE
    SYNTAX      Integer32(15..80)
    UNITS       "dBm"
    MAX-ACCESS  read-create
    STATUS      current
    DESCRIPTION
        "This object represents the mesh link switch protocol (MLSP)
        optimization threshold."
    DEFVAL      { 30 }
    ::= { ibDot11sMpPlcyEntry 18 }

ibDot11sMlspLogEnable OBJECT-TYPE
    SYNTAX      TruthValue
    MAX-ACCESS  read-create
    STATUS      current
    DESCRIPTION
        "This object indicates whether the mesh link switch protocol (MLSP)
        link switch logging function is enabled."
    DEFVAL      { false }
    ::= { ibDot11sMpPlcyEntry 19 }

ibDot11sMlspLogInterval OBJECT-TYPE
    SYNTAX      Integer32(500..4000)
    UNITS       "millisecond"
    MAX-ACCESS  read-create
    STATUS      current
    DESCRIPTION
        "This object represents the mesh link switch protocol (MLSP)
        link switch logging interval."
    DEFVAL      { 1000 }
    ::= { ibDot11sMpPlcyEntry 20 }

ibDot11sActiveKeepaliveCount OBJECT-TYPE
    SYNTAX      Integer32(1..100)
    MAX-ACCESS  read-create
    STATUS      current
    DESCRIPTION
        "This object represents the mesh link switch protocol (MLSP)
        active link keepalive packet limit."
    DEFVAL      { 6 }
    ::= { ibDot11sMpPlcyEntry 21 }

ibDot11sLinkEstaThreshold OBJECT-TYPE
    SYNTAX      Integer32(1..100)
    UNITS       "dBm"
    MAX-ACCESS  read-create
    STATUS      current
    DESCRIPTION
        "This object represents the mesh link establishment threshold."
    DEFVAL      { 5 }
    ::= { ibDot11sMpPlcyEntry 22 }

ibDot11sTransmissionMethod OBJECT-TYPE
    SYNTAX      INTEGER
        {
            air(0),
            waveGuide(1)
        }
    MAX-ACCESS  read-create
    STATUS      current
    DESCRIPTION
        "This object represents the method for mesh link signal transmission."
    DEFVAL      { air }
    ::= { ibDot11sMpPlcyEntry 23 }

ibDot11sTransmitLevel OBJECT-TYPE
    SYNTAX      Integer32(0..4)
    MAX-ACCESS  read-create
    STATUS      current
    DESCRIPTION
        "This object represents the active mesh link keepalive packet transmission level."
    DEFVAL      { 0 }
    ::= { ibDot11sMpPlcyEntry 24 }

ibDot11sTempLinkEnable OBJECT-TYPE
    SYNTAX      TruthValue
    MAX-ACCESS  read-create
    STATUS      current
    DESCRIPTION
        "This object indicates whether to allow temporary mesh link establishment."
    DEFVAL      { true }
    ::= { ibDot11sMpPlcyEntry 25 }

-- *****************************************************************************
-- * End of ibDot11sMpPlcyTable Definition
-- *****************************************************************************
-- *****************************************************************************
-- *  ibDot11sMlspCfgTable Definition
-- *****************************************************************************
ibDot11sMlspCfgTable OBJECT-TYPE
    SYNTAX      SEQUENCE OF IbDot11sMlspCfgEntry
    MAX-ACCESS  not-accessible
    STATUS      current
    DESCRIPTION
        "This table is used to configure MLSP proxy MAC address.
        Only if the specified MP policy is modifiable and the MLSP
        is enabled, the row of this table can be created and deleted.
        The row of this table cannot be modified."
    ::= { ibDot11sConfigGroup 4 }

ibDot11sMlspCfgEntry OBJECT-TYPE
    SYNTAX      IbDot11sMlspCfgEntry
    MAX-ACCESS  not-accessible
    STATUS      current
    DESCRIPTION
        "Each entry contains information of MLSP proxy MAC address."
    INDEX
        {
            ibDot11sMpPlcyIndex,
            ibDot11sMlspProxyIndex
        }
    ::= { ibDot11sMlspCfgTable 1 }

IbDot11sMlspCfgEntry ::= SEQUENCE
    {
        ibDot11sMlspProxyIndex       Integer32,
        ibDot11sMlspProxyMac         MacAddress,
        ibDot11sMlspRowStatus        RowStatus
    }

ibDot11sMlspProxyIndex OBJECT-TYPE
    SYNTAX      Integer32
    MAX-ACCESS  not-accessible
    STATUS      current
    DESCRIPTION
        "This object represents the MLSP proxy MAC address index."
    ::= { ibDot11sMlspCfgEntry 1 }

ibDot11sMlspProxyMac OBJECT-TYPE
    SYNTAX      MacAddress
    MAX-ACCESS  read-create
    STATUS      current
    DESCRIPTION
        "This object represents the MLSP proxy MAC address."
    ::= { ibDot11sMlspCfgEntry 2 }

ibDot11sMlspRowStatus OBJECT-TYPE
    SYNTAX      RowStatus
    MAX-ACCESS  read-create
    STATUS      current
    DESCRIPTION
        "The status of this table entry."
    ::= { ibDot11sMlspCfgEntry 3 }

-- *****************************************************************************
-- * End of ibDot11sMlspCfgTable Definition
-- *****************************************************************************
-- *****************************************************************************
-- *  ibDot11sRadioCfgTable Definition
-- *****************************************************************************
ibDot11sRadioCfgTable OBJECT-TYPE
    SYNTAX      SEQUENCE OF IbDot11sRadioCfgEntry
    MAX-ACCESS  not-accessible
    STATUS      current
    DESCRIPTION
        "This table is used to configure mesh to the specified radio."
    ::= { ibDot11sConfigGroup 5 }

ibDot11sRadioCfgEntry OBJECT-TYPE
    SYNTAX      IbDot11sRadioCfgEntry
    MAX-ACCESS  not-accessible
    STATUS      current
    DESCRIPTION
        "Each entry contains mesh configure information
        of the specified radio."
    INDEX
        {
            ibDot11sCfgRadioIndex
        }
    ::= { ibDot11sRadioCfgTable 1 }

IbDot11sRadioCfgEntry ::= SEQUENCE
    {
        ibDot11sCfgRadioIndex        IbDot11RadioElementIndex,
        ibDot11sMeshPflMap           Integer32,
        ibDot11sMpPlcyMap            Integer32,
        ibDot11sBindInterface        Integer32
    }

ibDot11sCfgRadioIndex OBJECT-TYPE
    SYNTAX      IbDot11RadioElementIndex
    MAX-ACCESS  not-accessible
    STATUS      current
    DESCRIPTION
        "Represents index of the radio."
    ::= { ibDot11sRadioCfgEntry 1 }

ibDot11sMeshPflMap OBJECT-TYPE
    SYNTAX      Integer32
    MAX-ACCESS  read-write
    STATUS      current
    DESCRIPTION
        "This object represents the number of the mesh profile mapped to
        the specified radio.  The value is zero when the radio is not
        bound to a mesh profile."
    DEFVAL      { 0 }
    ::= { ibDot11sRadioCfgEntry 2 }

ibDot11sMpPlcyMap OBJECT-TYPE
    SYNTAX      Integer32
    MAX-ACCESS  read-write
    STATUS      current
    DESCRIPTION
        "This object represents the index of the MP policy mapped to the
        specified radio.  The MP policy is the default policy when the radio
        is not bound to the user-defined MP policy.
        The index of the default policy is 1.
        This object cannot be modified when the radio is enabled."
    DEFVAL      { 1 }
    ::= { ibDot11sRadioCfgEntry 3 }

ibDot11sBindInterface OBJECT-TYPE
    SYNTAX      Integer32
    MAX-ACCESS  read-write
    STATUS      current
    DESCRIPTION
        "This object represents the number of the WLAN-Mesh interface
        mapped to the specified radio.  The value is -1 when the
        radio is not bound to a WLAN-Mesh interface."
    DEFVAL      { -1 }
    ::= { ibDot11sRadioCfgEntry 4 }

-- *****************************************************************************
-- * End of ibDot11sRadioCfgTable Definition
-- *****************************************************************************
-- *****************************************************************************
-- *  ibDot11sAPCfgTable Definition
-- *****************************************************************************
ibDot11sAPCfgTable OBJECT-TYPE
    SYNTAX      SEQUENCE OF IbDot11sAPCfgEntry
    MAX-ACCESS  not-accessible
    STATUS      current
    DESCRIPTION
        "This table is used to configure mesh to the specified AP."
    ::= { ibDot11sConfigGroup 6 }

ibDot11sAPCfgEntry OBJECT-TYPE
    SYNTAX      IbDot11sAPCfgEntry
    MAX-ACCESS  not-accessible
    STATUS      current
    DESCRIPTION
        "Each entry contains mesh configure information
        of the specified AP."
    INDEX
        {
            ibDot11APElementIndex
        }
    ::= { ibDot11sAPCfgTable 1 }

IbDot11sAPCfgEntry ::= SEQUENCE
    {
        ibDot11sPortalEnable         TruthValue
    }

ibDot11sPortalEnable OBJECT-TYPE
    SYNTAX      TruthValue
    MAX-ACCESS  read-write
    STATUS      current
    DESCRIPTION
        "This object indicates whether the portal service is enabled.
        'true': The portal service is enabled.
        'false': The portal service is disabled."
    DEFVAL      { false }
    ::= { ibDot11sAPCfgEntry 1 }

-- *****************************************************************************
-- * End of ibDot11sAPCfgTable Definition
-- *****************************************************************************
-- *****************************************************************************
-- *  ibDot11sWDSPeerMacTable Definition
-- *****************************************************************************
ibDot11sWDSPeerMacTable OBJECT-TYPE
    SYNTAX      SEQUENCE OF IbDot11sWDSPeerMacEntry
    MAX-ACCESS  not-accessible
    STATUS      current
    DESCRIPTION
        "This table is used to configure wireless distribution system (WDS).
        The row of this table cannot be modified."
    ::= { ibDot11sWDSConfigGroup 1 }

ibDot11sWDSPeerMacEntry OBJECT-TYPE
    SYNTAX      IbDot11sWDSPeerMacEntry
    MAX-ACCESS  not-accessible
    STATUS      current
    DESCRIPTION
        "Each entry contains information of WDS."
    INDEX
        {
            ibDot11sCfgRadioIndex,
            ibDot11sWDSPeerMacIndex
        }
    ::= { ibDot11sWDSPeerMacTable 1 }

IbDot11sWDSPeerMacEntry ::= SEQUENCE
    {
        ibDot11sWDSPeerMacIndex      Integer32,
        ibDot11sWDSPeerMacAddrss     MacAddress,
        ibDot11sWDSPeerMacRowStatus  RowStatus
    }

ibDot11sWDSPeerMacIndex OBJECT-TYPE
    SYNTAX      Integer32
    MAX-ACCESS  not-accessible
    STATUS      current
    DESCRIPTION
        "This object represents the peer MAC address index."
    ::= { ibDot11sWDSPeerMacEntry 1 }

ibDot11sWDSPeerMacAddrss OBJECT-TYPE
    SYNTAX      MacAddress
    MAX-ACCESS  read-create
    STATUS      current
    DESCRIPTION
        "This object represents the peer MAC address."
    ::= { ibDot11sWDSPeerMacEntry 2 }

ibDot11sWDSPeerMacRowStatus OBJECT-TYPE
    SYNTAX      RowStatus
    MAX-ACCESS  read-create
    STATUS      current
    DESCRIPTION
        "The status of this table entry."
    ::= { ibDot11sWDSPeerMacEntry 3 }

-- *****************************************************************************
-- * End of ibDot11sWDSPeerMacTable Definition
-- *****************************************************************************
-- *****************************************************************************
-- *  ibDot11sMlspExtCfgTable Definition
-- *****************************************************************************
ibDot11sMlspExtCfgTable OBJECT-TYPE
    SYNTAX      SEQUENCE OF IbDot11sMlspExtCfgEntry
    MAX-ACCESS  not-accessible
    STATUS      current
    DESCRIPTION
        "This table is used to configure MLSP proxy MAC address.
        Only if the specified MP policy is modifiable and MLSP
        is enabled, the row of this table can be created and deleted.
        The row of this table cannot be modified."
    ::= { ibDot11sConfigGroup 7 }

ibDot11sMlspExtCfgEntry OBJECT-TYPE
    SYNTAX      IbDot11sMlspExtCfgEntry
    MAX-ACCESS  not-accessible
    STATUS      current
    DESCRIPTION
        "Each entry contains MLSP proxy MAC address infomation."
    INDEX
        {
            ibDot11sMlspExtPolicyName,
            ibDot11sMlspExtProxyMac,
            ibDot11sMlspExtProxyVlanID
        }
    ::= { ibDot11sMlspExtCfgTable 1 }

IbDot11sMlspExtCfgEntry ::= SEQUENCE
    {
            ibDot11sMlspExtPolicyName       OCTET STRING,
            ibDot11sMlspExtProxyMac         MacAddress,
            ibDot11sMlspExtProxyVlanID      Integer32,
            ibDot11sMlspExtProxyIP          IpAddress,
            ibDot11sMlspExtRowStatus        RowStatus
    }
ibDot11sMlspExtPolicyName OBJECT-TYPE
    SYNTAX      OCTET STRING (SIZE (1..31))
    MAX-ACCESS  read-only
    STATUS      current
    DESCRIPTION
        "This object represents the MP policy name.
        An MP policy cannot be created with the name of the
        default policy.
        Modification is not supported."
    ::= { ibDot11sMlspExtCfgEntry 1 }

ibDot11sMlspExtProxyMac OBJECT-TYPE
    SYNTAX      MacAddress
    MAX-ACCESS  read-only
    STATUS      current
    DESCRIPTION
        "This object represents the MLSP proxy MAC address."
    ::= { ibDot11sMlspExtCfgEntry 2 }


ibDot11sMlspExtProxyVlanID OBJECT-TYPE
    SYNTAX      Integer32(1..4096)
    MAX-ACCESS  read-only
    STATUS      current
    DESCRIPTION
        "This object represents the MLSP proxy VLAN ID."
    ::= { ibDot11sMlspExtCfgEntry 3 }

ibDot11sMlspExtProxyIP OBJECT-TYPE
    SYNTAX      IpAddress
    MAX-ACCESS  read-create
    STATUS      current
    DESCRIPTION
        "This object represents the MLSP proxy IP address."
    ::= { ibDot11sMlspExtCfgEntry 4 }

ibDot11sMlspExtRowStatus OBJECT-TYPE
    SYNTAX      RowStatus
    MAX-ACCESS  read-create
    STATUS      current
    DESCRIPTION
        "The status of this table entry."
    ::= { ibDot11sMlspExtCfgEntry 5 }

-- *****************************************************************************
-- * End of ibDot11sMlspExtCfgTable Definition
-- *****************************************************************************
-- *****************************************************************************
-- *  ibDot11sMeshLinkStatusTable Definition
-- *****************************************************************************
ibDot11sMeshLinkStatusTable OBJECT-TYPE
    SYNTAX      SEQUENCE OF IbDot11sMeshLinkStatusEntry
    MAX-ACCESS  not-accessible
    STATUS      current
    DESCRIPTION
        "This table is used to represent the status of mesh link."
    ::= { ibDot11sMeshStatusGroup 1 }

ibDot11sMeshLinkStatusEntry OBJECT-TYPE
    SYNTAX      IbDot11sMeshLinkStatusEntry
    MAX-ACCESS  not-accessible
    STATUS      current
    DESCRIPTION
        "Each entry contains status information of mesh link."
    INDEX
        {
            ibDot11sMeshLinkIfIndex
        }
    ::= { ibDot11sMeshLinkStatusTable 1 }

IbDot11sMeshLinkStatusEntry ::= SEQUENCE
    {
        ibDot11sMeshLinkIfIndex        Unsigned32,
        ibDot11sMeshLinkName           OCTET STRING,
        ibDot11sMeshLinkBSSID          MacAddress,
        ibDot11sMeshLinkPeerMac        MacAddress,
        ibDot11sMeshLinkExistDuration  Integer32,
        ibDot11sMeshLinkType           INTEGER,
        ibDot11sMeshLinkSNR            Integer32,
        ibDot11sMeshLinkNoise          Integer32,
        ibDot11sMeshLinkPeerSNR        Integer32,
        ibDot11sMeshLinkPeerNoise      Integer32,
        ibDot11sMeshLinkPeerIPAddress  IpAddress,
        ibDot11sMeshLinkPeerSystemName OCTET STRING
    }

ibDot11sMeshLinkIfIndex OBJECT-TYPE
    SYNTAX      Unsigned32
    MAX-ACCESS  not-accessible
    STATUS      current
    DESCRIPTION
        "This object represents the interface index of the mesh link."
    ::= { ibDot11sMeshLinkStatusEntry 1 }

ibDot11sMeshLinkName OBJECT-TYPE
    SYNTAX      OCTET STRING
    MAX-ACCESS  read-only
    STATUS      current
    DESCRIPTION
        "This object represents the name of the mesh link."
    ::= { ibDot11sMeshLinkStatusEntry 2 }

ibDot11sMeshLinkBSSID OBJECT-TYPE
    SYNTAX      MacAddress
    MAX-ACCESS  read-only
    STATUS      current
    DESCRIPTION
        "This object represents the BSS ID of the mesh link."
    ::= { ibDot11sMeshLinkStatusEntry 3 }

ibDot11sMeshLinkPeerMac OBJECT-TYPE
    SYNTAX      MacAddress
    MAX-ACCESS  read-only
    STATUS      current
    DESCRIPTION
        "This object represents the peer MAC address of the mesh link."
    ::= { ibDot11sMeshLinkStatusEntry 4 }

ibDot11sMeshLinkExistDuration OBJECT-TYPE
    SYNTAX      Integer32
    UNITS       "second"
    MAX-ACCESS  read-only
    STATUS      current
    DESCRIPTION
        "This object represents the time for which the link has been up."
    ::= { ibDot11sMeshLinkStatusEntry 5 }

ibDot11sMeshLinkType OBJECT-TYPE
    SYNTAX      INTEGER
        {
            active(1),
            dormant(2)
        }
    MAX-ACCESS  read-only
    STATUS      current
    DESCRIPTION
        "This object represents the type for the link."
    ::= { ibDot11sMeshLinkStatusEntry 6 }

ibDot11sMeshLinkSNR OBJECT-TYPE
    SYNTAX      Integer32
    UNITS       "percent"
    MAX-ACCESS  read-only
    STATUS      current
    DESCRIPTION
        "Represents the SNR for the link."
    ::= { ibDot11sMeshLinkStatusEntry 7 }

ibDot11sMeshLinkNoise OBJECT-TYPE
    SYNTAX      Integer32
    MAX-ACCESS  read-only
    STATUS      current
    DESCRIPTION
        "Represents the noise for the link."
    ::= { ibDot11sMeshLinkStatusEntry 8 }

ibDot11sMeshLinkPeerSNR OBJECT-TYPE
    SYNTAX      Integer32
    UNITS       "percent"
    MAX-ACCESS  read-only
    STATUS      current
    DESCRIPTION
        "Represents the SNR transferred from the neighbor of this mesh link."
    ::= { ibDot11sMeshLinkStatusEntry 9 }

ibDot11sMeshLinkPeerNoise OBJECT-TYPE
    SYNTAX      Integer32
    MAX-ACCESS  read-only
    STATUS      current
    DESCRIPTION
        "Represents the noise transferred from the neighbor of this mesh link."
    ::= { ibDot11sMeshLinkStatusEntry 10 }

ibDot11sMeshLinkPeerIPAddress OBJECT-TYPE
    SYNTAX      IpAddress
    MAX-ACCESS  read-only
    STATUS      current
    DESCRIPTION
        "Represents the IP address of the neighbor of this mesh link."
    ::= { ibDot11sMeshLinkStatusEntry 11 }

ibDot11sMeshLinkPeerSystemName OBJECT-TYPE
    SYNTAX      OCTET STRING
    MAX-ACCESS  read-only
    STATUS      current
    DESCRIPTION
        "Represents the system name of the neighbor of this mesh link."
    ::= { ibDot11sMeshLinkStatusEntry 12 }

-- *****************************************************************************
-- * End of ibDot11sMeshLinkStatusTable Definition
-- *****************************************************************************

-- *****************************************************************************
-- *  ibDot11sMeshLinkStatisTable Definition
-- *****************************************************************************
ibDot11sMeshLinkStatisTable OBJECT-TYPE
    SYNTAX      SEQUENCE OF IbDot11sMeshLinkStatisEntry
    MAX-ACCESS  not-accessible
    STATUS      current
    DESCRIPTION
        "This table is used to represent the statistical information of
         mesh link."
    ::= { ibDot11sMeshStatusGroup 2 }

ibDot11sMeshLinkStatisEntry OBJECT-TYPE
    SYNTAX      IbDot11sMeshLinkStatisEntry
    MAX-ACCESS  not-accessible
    STATUS      current
    DESCRIPTION
        "Each entry contains statistical information of mesh link."
    INDEX
        {
            ibDot11APElementIndex,
            ibDot11sMeshLinkStatIfIndex
        }
    ::= { ibDot11sMeshLinkStatisTable 1 }

IbDot11sMeshLinkStatisEntry ::= SEQUENCE
    {
        ibDot11sMeshLinkStatIfIndex    Unsigned32,
        ibDot11sMeshLinkNbrIndex       Unsigned32,
        ibDot11sMeshLinkRxTotByte      Counter32,
        ibDot11sMeshLinkRxTotPkt       Counter32,
        ibDot11sMeshLinkRxUniPkt       Counter32,
        ibDot11sMeshLinkRxBrocPkt      Counter32,
        ibDot11sMeshLinkRxMuticPkt     Counter32,
        ibDot11sMeshLinkRxDiscPkt      Counter32,
        ibDot11sMeshLinkTxTotByte      Counter32,
        ibDot11sMeshLinkTxTotPkt       Counter32,
        ibDot11sMeshLinkTxUniPkt       Counter32,
        ibDot11sMeshLinkTxBrocPkt      Counter32,
        ibDot11sMeshLinkTxMuticPkt     Counter32,
        ibDot11sMeshLinkTxDiscPkt      Counter32,
        ibDot11sMeshLinkIFName         OCTET STRING
    }

ibDot11sMeshLinkStatIfIndex OBJECT-TYPE
    SYNTAX      Unsigned32
    MAX-ACCESS  not-accessible
    STATUS      current
    DESCRIPTION
        "This object represents the interface index of the mesh link."
    ::= { ibDot11sMeshLinkStatisEntry 1 }

ibDot11sMeshLinkNbrIndex OBJECT-TYPE
    SYNTAX      Unsigned32
    MAX-ACCESS  read-only
    STATUS      current
    DESCRIPTION
        "Represents the neighbor index of the mesh link."
    ::= { ibDot11sMeshLinkStatisEntry 2 }

ibDot11sMeshLinkRxTotByte OBJECT-TYPE
    SYNTAX      Counter32
    MAX-ACCESS  read-only
    STATUS      current
    DESCRIPTION
        "Represents the amount of bytes that the mesh link received."
    ::= { ibDot11sMeshLinkStatisEntry 3 }

ibDot11sMeshLinkRxTotPkt OBJECT-TYPE
    SYNTAX      Counter32
    MAX-ACCESS  read-only
    STATUS      current
    DESCRIPTION
        "Represents the amount of packets that the mesh link received."
    ::= { ibDot11sMeshLinkStatisEntry 4 }

ibDot11sMeshLinkRxUniPkt OBJECT-TYPE
    SYNTAX      Counter32
    MAX-ACCESS  read-only
    STATUS      current
    DESCRIPTION
        "Represents the amount of unicast packets that the mesh link received."
    ::= { ibDot11sMeshLinkStatisEntry 5 }

ibDot11sMeshLinkRxBrocPkt OBJECT-TYPE
    SYNTAX      Counter32
    MAX-ACCESS  read-only
    STATUS      current
    DESCRIPTION
        "Represents the amount of broadcast packets that the mesh link
         received."
    ::= { ibDot11sMeshLinkStatisEntry 6 }

ibDot11sMeshLinkRxMuticPkt OBJECT-TYPE
    SYNTAX      Counter32
    MAX-ACCESS  read-only
    STATUS      current
    DESCRIPTION
        "Represents the amount of multicast packets that the mesh link
         received."
    ::= { ibDot11sMeshLinkStatisEntry 7 }

ibDot11sMeshLinkRxDiscPkt OBJECT-TYPE
    SYNTAX      Counter32
    MAX-ACCESS  read-only
    STATUS      current
    DESCRIPTION
        "Represents the amount of packets that the mesh link discarded."
    ::= { ibDot11sMeshLinkStatisEntry 8 }

ibDot11sMeshLinkTxTotByte OBJECT-TYPE
    SYNTAX      Counter32
    MAX-ACCESS  read-only
    STATUS      current
    DESCRIPTION
        "Represents the total amount of bytes that the mesh link transmitted."
    ::= { ibDot11sMeshLinkStatisEntry 9 }

ibDot11sMeshLinkTxTotPkt OBJECT-TYPE
    SYNTAX      Counter32
    MAX-ACCESS  read-only
    STATUS      current
    DESCRIPTION
        "Represents the total amount of packets that the mesh link transmitted."
    ::= { ibDot11sMeshLinkStatisEntry 10 }

ibDot11sMeshLinkTxUniPkt OBJECT-TYPE
    SYNTAX      Counter32
    MAX-ACCESS  read-only
    STATUS      current
    DESCRIPTION
        "Represents the amount of unicast packets that the mesh link
         transmitted."
    ::= { ibDot11sMeshLinkStatisEntry 11 }

ibDot11sMeshLinkTxBrocPkt OBJECT-TYPE
    SYNTAX      Counter32
    MAX-ACCESS  read-only
    STATUS      current
    DESCRIPTION
        "Represents the amount of broadcast packets that the mesh link
         transmitted."
    ::= { ibDot11sMeshLinkStatisEntry 12 }

ibDot11sMeshLinkTxMuticPkt OBJECT-TYPE
    SYNTAX      Counter32
    MAX-ACCESS  read-only
    STATUS      current
    DESCRIPTION
        "Represents the amount of multicast packets that the mesh link
         transmitted."
    ::= { ibDot11sMeshLinkStatisEntry 13 }

ibDot11sMeshLinkTxDiscPkt OBJECT-TYPE
    SYNTAX      Counter32
    MAX-ACCESS  read-only
    STATUS      current
    DESCRIPTION
        "Represents the amount of discarded packets that the mesh link
         transmitted."
    ::= { ibDot11sMeshLinkStatisEntry 14 }

ibDot11sMeshLinkIFName    OBJECT-TYPE
    SYNTAX      OCTET STRING
    MAX-ACCESS  read-only
    STATUS      current
    DESCRIPTION
        "Represents the name of mesh link interface."
    ::= { ibDot11sMeshLinkStatisEntry 15 }

-- *****************************************************************************
-- * End of ibDot11sMeshLinkStatisTable Definition
-- *****************************************************************************

-- *****************************************************************************
-- *  ibDot11sMeshNbrStatusTable Definition
-- *****************************************************************************
ibDot11sMeshNbrStatusTable OBJECT-TYPE
    SYNTAX      SEQUENCE OF IbDot11sMeshNbrStatusEntry
    MAX-ACCESS  not-accessible
    STATUS      current
    DESCRIPTION
        "This table represents the status information for the neighbors of MP."
    ::= { ibDot11sMeshStatusGroup 3 }

ibDot11sMeshNbrStatusEntry OBJECT-TYPE
    SYNTAX      IbDot11sMeshNbrStatusEntry
    MAX-ACCESS  not-accessible
    STATUS      current
    DESCRIPTION
        "Each entry of the table will provide status information for the
         neighbors of MP."
    INDEX
        {
            ibDot11APElementIndex,
            ibDot11sMeshNbrIndex
        }
    ::= { ibDot11sMeshNbrStatusTable 1 }

IbDot11sMeshNbrStatusEntry ::= SEQUENCE
    {
        ibDot11sMeshNbrIndex          Unsigned32,
        ibDot11sMeshNbrRadioID        Unsigned32,
        ibDot11sMeshLocalMeshID       OCTET STRING,
        ibDot11sMeshNbrMeshID         OCTET STRING,
        ibDot11sMeshNbrBSSID          MacAddress,
        ibDot11sMeshNbrPeerMac        MacAddress,
        ibDot11sMeshLinkInMp          Unsigned32,
        ibDot11sMeshMPLinkStatus      INTEGER,
        ibDot11sMeshNbrChannel        Unsigned32,
        ibDot11sMeshNbrLinkDuration   Integer32,
        ibDot11sMeshNbrRSSI           Integer32,
        ibDot11sMeshNbrSNR            Integer32
    }

ibDot11sMeshNbrIndex OBJECT-TYPE
    SYNTAX      Unsigned32
    MAX-ACCESS  not-accessible
    STATUS      current
    DESCRIPTION
        "Represents the index for the neighbor."
    ::= { ibDot11sMeshNbrStatusEntry 1 }

ibDot11sMeshNbrRadioID OBJECT-TYPE
    SYNTAX      Unsigned32
    MAX-ACCESS  read-only
    STATUS      current
    DESCRIPTION
        "Represents the radio ID of the neighbor."
    ::= { ibDot11sMeshNbrStatusEntry 2 }

ibDot11sMeshLocalMeshID OBJECT-TYPE
    SYNTAX      OCTET STRING(SIZE(0..32))
    MAX-ACCESS  read-only
    STATUS      current
    DESCRIPTION
        "Represents the local mesh ID."
    ::= { ibDot11sMeshNbrStatusEntry 3 }

ibDot11sMeshNbrMeshID OBJECT-TYPE
    SYNTAX      OCTET STRING(SIZE(0..32))
    MAX-ACCESS  read-only
    STATUS      current
    DESCRIPTION
        "Represents the mesh ID of the neighbor."
    ::= { ibDot11sMeshNbrStatusEntry 4 }

ibDot11sMeshNbrBSSID OBJECT-TYPE
    SYNTAX      MacAddress
    MAX-ACCESS  read-only
    STATUS      current
    DESCRIPTION
        "Represents the BSS ID of the neighbor."
    ::= { ibDot11sMeshNbrStatusEntry 5 }

ibDot11sMeshNbrPeerMac OBJECT-TYPE
    SYNTAX      MacAddress
    MAX-ACCESS  read-only
    STATUS      current
    DESCRIPTION
        "Represents the MAC address of the peer neighbor."
    ::= { ibDot11sMeshNbrStatusEntry 6 }

ibDot11sMeshLinkInMp OBJECT-TYPE
    SYNTAX      Unsigned32
    MAX-ACCESS  read-only
    STATUS      current
    DESCRIPTION
        "Represents the interface index of mesh link that used to connect with
         this neighbor."
    ::= { ibDot11sMeshNbrStatusEntry 7 }

ibDot11sMeshMPLinkStatus OBJECT-TYPE
    SYNTAX      INTEGER
        {
            processing(1),
            up(2),
            down(3)
        }
    MAX-ACCESS  read-only
    STATUS      current
    DESCRIPTION
        "Represents the status of mesh link that used to connect with this
         neighbor."
    ::= { ibDot11sMeshNbrStatusEntry 8 }

ibDot11sMeshNbrChannel OBJECT-TYPE
    SYNTAX      Unsigned32
    MAX-ACCESS  read-only
    STATUS      current
    DESCRIPTION
        "Represents the channel number used by this neighbor."
    ::= { ibDot11sMeshNbrStatusEntry 9 }

ibDot11sMeshNbrLinkDuration OBJECT-TYPE
    SYNTAX      Integer32
    UNITS       "second"
    MAX-ACCESS  read-only
    STATUS      current
    DESCRIPTION
        "Represents the duration of mesh link that used to connect with this
         neighbor."
    ::= { ibDot11sMeshNbrStatusEntry 10 }

ibDot11sMeshNbrRSSI OBJECT-TYPE
    SYNTAX      Integer32
    MAX-ACCESS  read-only
    STATUS      current
    DESCRIPTION
        "Represents the RSSI of mesh link that used to connect with this
         neighbor."
    ::= { ibDot11sMeshNbrStatusEntry 11 }

ibDot11sMeshNbrSNR OBJECT-TYPE
    SYNTAX      Integer32
    UNITS       "percent"
    MAX-ACCESS  read-only
    STATUS      current
    DESCRIPTION
        "Represents the SNR of mesh link that used to connect with this
         neighbor."
    ::= { ibDot11sMeshNbrStatusEntry 12 }

-- *****************************************************************************
-- *  End of ibDot11sMeshNbrStatusTable Definition
-- *****************************************************************************
-- *****************************************************************************
-- *  ibDot11sMeshLinkTraps Definition
-- *****************************************************************************

ibDot11sMeshLinkTraps OBJECT IDENTIFIER ::= { ibDot11sMeshLinkNotifyGroup 0 }

ibDot11sMeshLinkSwitchTrap NOTIFICATION-TYPE
    OBJECTS
        {
            ibDot11sMeshLinkBSSIDMAC,
            ibDot11sMeshLinkPeerMAC
        }
    STATUS        current
    DESCRIPTION
        "This notification is to indicate the occurrence of a mesh link switchover."
    ::= { ibDot11sMeshLinkTraps 1 }

ibDot11sMeshLinkTrapObjects OBJECT IDENTIFIER ::= { ibDot11sMeshLinkNotifyGroup 1 }

ibDot11sMeshLinkBSSIDMAC OBJECT-TYPE
    SYNTAX      MacAddress
    MAX-ACCESS  accessible-for-notify
    STATUS      current
    DESCRIPTION
        "Represents the BSSID of the MP."
    ::= { ibDot11sMeshLinkTrapObjects 1 }

ibDot11sMeshLinkPeerMAC OBJECT-TYPE
    SYNTAX      MacAddress
    MAX-ACCESS  accessible-for-notify
    STATUS      current
    DESCRIPTION
        "Represents the MAC address of the peer MP after mesh link switchover."
    ::= { ibDot11sMeshLinkTrapObjects 2 }
END
