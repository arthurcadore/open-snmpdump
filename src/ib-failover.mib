-- ============================================================================
-- Copyright (C) 2023 Intelbras S.A. All rights reserved.
--
-- Description: FAILOVER GROUP MIB
-- Reference:
-- Version: V1.0
-- History:
-- revision 1.0 2015-10-27 created by j03525
--
-- ============================================================================
IB-FAILOVER-MIB DEFINITIONS ::= BEGIN

IMPORTS
    ibCommon
        FROM IB-OID-MIB
    Integer32, Unsigned32, OBJECT-TYPE, MODULE-IDENTITY, NOTIFICATION-TYPE
        FROM SNMPv2-SMI
    DisplayString, RowStatus
        FROM SNMPv2-TC;

ibFailover MODULE-IDENTITY
    LAST-UPDATED "201510271040Z"
    ORGANIZATION
        "Intelbras S.A. Industria de Telecomunicacao Eletronica Brasileria."
    CONTACT-INFO
        ""
    DESCRIPTION
        "This MIB file is to provide the definition of failover group.

        Such as:
        1. Configure Failover Groups for a device and display Failover Groups
           and their status.
        2. Assign CPU to the Failover Group, and display their status.

        Failover Group: A failover group contains a primary node and a secondary node.
        When a failover group is referenced by a service module, the primary node
        processes services and backs up service data to the secondary node.
        The secondary node does not process services, but it takes over the services
        when the primary node fails.
        When the primary node is recovered, traffic is switched to the primary node again."
    REVISION "201510271040Z"
    DESCRIPTION
        "The initial revision of this MIB module."
    ::= { ibCommon 164 }


-- Node definitions

ibFailoverScalarObjects OBJECT IDENTIFIER ::= { ibFailover 1 }

ibFailoverMaxNum OBJECT-TYPE
    SYNTAX Unsigned32
    MAX-ACCESS read-only
    STATUS current
    DESCRIPTION
        "The maximum number of Failover groups which the system supported to create, does not include the AutoBackup."
    ::= { ibFailoverScalarObjects 1 }


ibFailoverCurrentNum OBJECT-TYPE
    SYNTAX Unsigned32
    MAX-ACCESS read-only
    STATUS current
    DESCRIPTION
        "The current number of Failover groups which the system has created, does not include the AutoBackup."
    ::= { ibFailoverScalarObjects 2 }


ibFailoverTables OBJECT IDENTIFIER ::= { ibFailover 2 }

ibFailoverCfgTable OBJECT-TYPE
    SYNTAX SEQUENCE OF IbFailoverCfgEntry
    MAX-ACCESS not-accessible
    STATUS current
    DESCRIPTION
        "This table is for configuration of backup group."
    ::= { ibFailoverTables 1 }


ibFailoverCfgEntry OBJECT-TYPE
    SYNTAX IbFailoverCfgEntry
    MAX-ACCESS not-accessible
    STATUS current
    DESCRIPTION
        "An entry of the ibFailoverGroupCfgTable."
    INDEX { ibFailoverIndex }
    ::= { ibFailoverCfgTable 1 }


IbFailoverCfgEntry ::=
    SEQUENCE
    {
        ibFailoverIndex
            Unsigned32,
        ibFailoverName
            DisplayString,
        ibFailoverPrimaryChassisID
            Integer32,
        ibFailoverPrimarySlotID
            Integer32,
        ibFailoverPrimaryCpuID
            Integer32,
        ibFailoverSecondaryChassisID
            Integer32,
        ibFailoverSecondarySlotID
            Integer32,
        ibFailoverSecondaryCpuID
            Integer32,
        ibFailoverState
            INTEGER,
        ibFailoverRowStatus
            RowStatus
    }

ibFailoverIndex OBJECT-TYPE
    SYNTAX Unsigned32 (0..4294967295)
    MAX-ACCESS accessible-for-notify
    STATUS current
    DESCRIPTION
        "Failover group ID is used as group index, the value range of failover group ID
        depends on the device model.
        The failover GroupIndex cannot be modified after creation."
    ::= { ibFailoverCfgEntry 1 }


ibFailoverName OBJECT-TYPE
    SYNTAX DisplayString (SIZE (1..63))
    MAX-ACCESS read-create
    STATUS current
    DESCRIPTION
        "Specifies the backup group name, a case-sensitive string of 1 to 63 characters.
        The failover group name cannot be modified after creation.
        The name can not include '?', and can not begin or end with ' '."
    ::= { ibFailoverCfgEntry 2 }


ibFailoverPrimaryChassisID OBJECT-TYPE
    SYNTAX Integer32 (-1..255)
    MAX-ACCESS read-create
    STATUS current
    DESCRIPTION
        "Specifies a card on an IRF member device.  The chassis-number argument represents
        the member ID of the IRF member device.  (Distributed devices In IRF mode.)
        On a centralized or distributed device, the value for this node is always zero.
        Note:The -1 for delete the node."
    ::= { ibFailoverCfgEntry 3 }


ibFailoverPrimarySlotID OBJECT-TYPE
    SYNTAX Integer32 (-1..255)
    MAX-ACCESS read-create
    STATUS current
    DESCRIPTION
        "Specifies a card by its slot number.  (Distributed devices In standalone mode.)
        Note:The -1 for delete the node."
    ::= { ibFailoverCfgEntry 4 }


ibFailoverPrimaryCpuID OBJECT-TYPE
    SYNTAX Integer32 (-1..7)
    MAX-ACCESS read-create
    STATUS current
    DESCRIPTION
        "Specifies a CPU by its number.  This option is available only if multiple CPUs
        are available on the specified slot.
        Note:The -1 for delete the node."
    ::= { ibFailoverCfgEntry 5 }


ibFailoverSecondaryChassisID OBJECT-TYPE
    SYNTAX Integer32 (-1..255)
    MAX-ACCESS read-create
    STATUS current
    DESCRIPTION
        "Specifies a card on an IRF member device.  The chassis-number argument represents
        the member ID of the IRF member device.  (Distributed devices In IRF mode.)
        On a centralized or distributed device, the value for this node is always zero.
        Note:The -1 for delete the node."
    ::= { ibFailoverCfgEntry 6 }


ibFailoverSecondarySlotID OBJECT-TYPE
    SYNTAX Integer32 (-1..255)
    MAX-ACCESS read-create
    STATUS current
    DESCRIPTION
        "Specifies a card by its slot number.  (Distributed devices In standalone mode.)
        Note:The -1 for delete the node."
    ::= { ibFailoverCfgEntry 7 }


ibFailoverSecondaryCpuID OBJECT-TYPE
    SYNTAX Integer32 (-1..7)
    MAX-ACCESS read-create
    STATUS current
    DESCRIPTION
        "Specifies a CPU by its number.  This option is available only if multiple CPUs
        are available on the specified slot.
        Note:The -1 for delete the node."
    ::= { ibFailoverCfgEntry 8 }


ibFailoverState OBJECT-TYPE
    SYNTAX INTEGER
        {
            initial(1),
            normal(2),
            fault(3)
        }
    MAX-ACCESS read-only
    STATUS current
    DESCRIPTION
        "Backup group state:
        Initial: No node in the failover group is processing services.
        Normal: The primary node is processing services.
        Fault: The secondary node is processing services."
    ::= { ibFailoverCfgEntry 9 }


ibFailoverRowStatus OBJECT-TYPE
    SYNTAX RowStatus
    MAX-ACCESS read-create
    STATUS current
    DESCRIPTION
        "The status of this table entry.
        Only support active(1), createAndGo(4) and destroy(6)."
    ::= { ibFailoverCfgEntry 10 }

--
-- Notification definitions
--
-- =================================================================
-- Traps are defined below.
ibFailoverNotification OBJECT IDENTIFIER ::= { ibFailover 3 }

-- All objects used for TRAP only are defined here.
ibFailoverTrap OBJECT IDENTIFIER ::= { ibFailoverNotification 0 }

ibFailoverCreate  NOTIFICATION-TYPE
    OBJECTS
        {
            ibFailoverIndex,
            ibFailoverName
        }

    STATUS current
    DESCRIPTION
        "The ibFailoverCreate trap indicates that the failover group has created."
    ::= { ibFailoverTrap 1 }

ibFailoverDelete  NOTIFICATION-TYPE
    OBJECTS
        {
            ibFailoverIndex,
            ibFailoverName
        }
    STATUS current
    DESCRIPTION
        "The ibFailoverDelete trap indicates that the failover group has deleted."
    ::= { ibFailoverTrap 2 }

ibFailoverPrimaryNodeAdd  NOTIFICATION-TYPE
    OBJECTS
        {
            ibFailoverIndex,
            ibFailoverName,
            ibFailoverPrimaryChassisID,
            ibFailoverPrimarySlotID,
            ibFailoverPrimaryCpuID
        }
    STATUS current
    DESCRIPTION
        "The ibFailoverPrimaryNodeAdd trap indicates that the failover group has
        added the primary node."
    ::= { ibFailoverTrap 3 }

ibFailoverPrimaryNodeRemove  NOTIFICATION-TYPE
    OBJECTS
        {
            ibFailoverIndex,
            ibFailoverName,
            ibFailoverPrimaryChassisID,
            ibFailoverPrimarySlotID,
            ibFailoverPrimaryCpuID
        }
    STATUS current
    DESCRIPTION
        "The ibFailoverPrimaryNodeRemove trap indicates that the failover group has
        removed the primary node."
    ::= { ibFailoverTrap 4 }

ibFailoverSecondaryNodeAdd  NOTIFICATION-TYPE
    OBJECTS
        {
            ibFailoverIndex,
            ibFailoverName,
            ibFailoverSecondaryChassisID,
            ibFailoverSecondarySlotID,
            ibFailoverSecondaryCpuID
        }
    STATUS current
    DESCRIPTION
        "The ibFailoverSecondaryNodeAdd trap indicates that the failover group has
        added the secondary node."
    ::= { ibFailoverTrap 5 }

ibFailoverSecondaryNodeRemove  NOTIFICATION-TYPE
    OBJECTS
        {
            ibFailoverIndex,
            ibFailoverName,
            ibFailoverSecondaryChassisID,
            ibFailoverSecondarySlotID,
            ibFailoverSecondaryCpuID
        }
    STATUS current
    DESCRIPTION
        "The ibFailoverSecondaryNodeRemove trap indicates that the failover group has
        removed the secondary node."
    ::= { ibFailoverTrap 6 }

END
