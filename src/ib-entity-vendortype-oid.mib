-- =================================================================
-- Copyright (C) 2023 Intelbras S.A. All rights reserved.
--
-- Description: The definition of Entity Vendortype OID
-- Reference:
-- Version: V5.16
-- History:
-- V1.0 2004.05.13  Created by lvzhenfeng, modified by gaolong.
-- V1.1 2004.05.22  Adjusted by gaolong and lvzhenfeng.
--   1. Adjust module name to ibEntityVendorTypeOID and its location is set to { ib 3 }.
--   2. Rename module name prefix from ibevtModule to ibevtModuleRt_
--   and ibevtModuleSw_ for routers and switches seperately.
--   3. Add ibevtSubModuleRouter and ibevtSubModuleSwitch under ibevtModule.
--   4. Split port type into two groups, one for routers, another for switches.
-- V1.11 2004-06-17 add ibevtHotSwapFan node by limeng for garibaldi
-- V1.12 2004-07-19 add ibevtModuleSwitchType {117-138}
-- V1.13 2004-07-29 add ibevtPortSwitchType {50-58}
-- V1.14 2004-08-12 add ibevtModuleSw_LSA1FP8U(ibevtModuleSwitchType 139)
-- V1.15 2004-08-25 change enumeration name
--                     from ibevtModuleSw_LS81SFCA(120) to ibevtModuleSw_LS81SRPG0(120),
--                     from ibevtModuleSw_LS81SFCB(121) to ibevtModuleSw_LS81SRPG1(121),
--                     from ibevtModuleSw_LS81SFCC(122) to ibevtModuleSw_LS81SRPG2(122),
--                     from ibevtModuleSw_LS81SFCD(123) to ibevtModuleSw_LS81SRPG3(123).
--                  modify comments for these enumerations as well.
-- V1.2  2004-08-26 add sub identifier of ibevtPortSwitchType from 59 to 71.
-- V1.21 2004-09-08 add sub identifier of ibevtModuleSwitchType from 140 to 148.
-- V1.3  2004-09-14 add subidentifier under ibevtModuleSwitchType from 149 to 157 by wangyahui
--                  add subidentifier under ibevtModuleSwitchType from 158 to 159 by kangyinan
--                  add subidentifier under ibevtModuleSwitchType from 72 to 93 by wangyahui
--                  add subidentifier under ibevtModuleSwitchType from 94 to 96 by kangyinan
--                  add type description for ibevtModuleSw_SP4, ibevtModuleSw_UP1, ibevtModuleSw_XP4 by kangyinan
-- V2.0  2004-10-12 updated by gaolong
--                  Change all underscore('_') characters to hyphen characters('-') because underscore character is not allowed in MIB module.
--                  Remove some adjacent hyphens
-- V2.1  2004-10-19 add subidentifier under ibevtModuleSwitchType from 160 to 162 by kangyinan
--                  add subidentifier under ibevtPortSwitchType 97 by kangyinan
-- V2.2  2004-09-18 add sub identifier for ibevtModuleRouterType from 111 to 117 by taotao
-- V2.3  2004-11-18 add sub identifier 2 under ibevtFan by liyutao
-- V2.4  2004-11-23 add subidentifier under ibevtModuleSwitchType from 163 to 166 by zhangchengmei
-- V2.5  2004-12-04 add subidentifier 118 under ibevtModuleRouterType by lizhiyong
-- V2.6  2004-12-23 add sub identifier 4 to 7 under ibevtPowerSupply by Zhangjianfeng
--                  add sub identifier 167 to 169 under ibevtModuleSwitchType by Zhangjianfeng
-- V2.7  2004-12-26 add subidentifier 170 under ibevtModuleSwitchType by wangyahui
-- v2.8  2004-12-23 add subidentifier under ibevtModuleSwitchType from 171 to 172 and
--                  add sub identifier 98 to 99 under ibevtPortSwitchType by liyue
-- V2.9  2004-12-26 add sub identifier 173 under ibevtModuleSwitchType by Zhangjianfeng
--                  add sub identifier 100 for 24G cascade port under ibevtPort by Zhangjianfeng
-- V3.0  2004-01-07 add subidentifier 174 and 175 under ibevtModuleSwitchType by wangyahui
-- V3.1  2005-01-31 add subidentifier 176 under ibevtModuleSwitchType by wangyahui
-- V3.2  2005-02-26 add subidentifier 177 under ibevtModuleSwitchType by zhangchengmei
--                  add subidentifier 101 to 137 under ibevtPortSwitchType by zhangchengmei
--                  add subidentifier 178 under ibevtModuleSwitchType by zhouqiang
--                  add subidentifier 138 under ibevtPortSwitchType by zhouqiang
--                  add subidentifier 179 to 180 under ibevtModuleSwitchType by wangyahui
--                  remove trailing spaces
-- V3.3  2005-03-22 add subidentifier 181 to 187 under ibevtModuleSwitchType by zhangchengmei
-- V3.4  2004-12-29 add subidentifier 119 to 120 under ibevtModuleRouterType by lizhiyong
-- V3.5  2005-04-12 add subidentifier 141 to 144 under ibevtModuleRouterType by yinxiaoyu
--                  add subidentifier 30 to 33 under ibevtPortRouterType by yinxiaoyu
-- V3.6  2005-04-07 add subidentifier 121 to 140 under ibevtModuleRouterType by taotao
--                  change the name of subidentifier 118 under ibevtModuleRouterType by taotao
--                  adjust file format
-- V3.7  2005-05-10 add subidentifier 188 to 216 under ibevtModuleSwitchType by zhangchengmei
-- V3.8  2005-06-12 add subidentifier 145 to 149 under ibevtModuleRouterType,
--                  add subidentifier 34 under ibevtPortRouterType by wanghanlin
-- V3.9  2005-06-22 add subidentifier 150 under ibevtModuleRouterType by yinxiaoyu
-- V4.0  2005-07-18 add subidentifier 217 to 219 under ibevtModuleSwitchType by yangliming
--                  add subidentifier 139 to 142 under ibevtPortSwitchType by wangyahui
-- V4.01 2005-07-29 add subidentifier 220 to 225 under ibevtModuleSwitchType by wangyahui
-- V4.02 2005-07-21 change the name of subidentifier 183 under ibevtModuleSwitchType,
--                  add subidentifier 226 to 227 under ibevtModuleSwitchType by zhangchengmei
--       2005-08-29 add subidentifier 143 under ibevtPortSwitchType by qianxiaoyu
--                  add subidentifier 151 to 161 under ibevtModuleRouterType by taotao
--                  add subidentifier 35 to 41 under ibevtPortRouterType by taotao
-- V4.03 2005-09-07 add ibevtCPU and ibevtGeneralCPU by taotao
--                  add subidentifier 162 to 163 under ibevtModuleRouterType by taotao
--                  adjust file format by gaolong
-- V4.04 2005-09-13 add subidentifier 228 to 253 under ibevtModuleSwitchType by zhangchengmei
--       2005-09-13 add subidentifier 257 to 268 under ibevtModuleSwitchType by zhangchengmei
-- V4.05 2005-11-04 add subidentifier 144 to 149 under ibevtPortSwitchType by zhangchengmei
--                  add subidentifier 150 under ibevtPortSwitchType by huangyuetao
--                  add subidentifier 269 to 271 under ibevtModuleSwitchType by yangxiaopeng
--                  add subidentifier 272 under ibevtModuleSwitchType by qianxiaoyu
--                  add subidentifier 164 to 165 under ibevtModuleRouterType by xuejiayong
-- V4.06 2005-11-24 add subidentifier 500 to 501 under ibevtModuleSwitchType by wangyahui
-- V4.07 2005-11-28 add subidentifier 300 to 316 under ibevtModuleSwitchType by zhangchengmei
-- V4.08 2005-12-09 add subidentifier 220 to 223 under ibevtModuleRouterType by taotao
-- V4.09 2005-12-30 add subidentifier 151 to 170 under ibevtPortSwitchType by zhangchengmei
-- V4.10 2006-01-04 add subidentifier 701 under ibevtModuleSwitchType by qianxiaoyu
-- V4.11 2006-02-12 add subidentifier 200 to 219 under ibevtModuleRouterType by liutinghai
--                  add subidentifier 702 under ibevtModuleSwitchType by chenxiaohui
--                  add subidentifier 600 under ibevtModuleRouterType by qujin
--                  add subidentifier 317 under ibevtModuleSwitchType by zhangchengmei
-- V4.12 2006-02-24 add subidentifier 703 under ibevtModuleSwitchType by chijuntao
--                  add subidentifier 224 to 228 under ibevtModuleRouterType by taotao
-- V4.13 2006-02-27 add subidentifier 171 to 174 under ibevtPortSwitchType by wangshunli
--                  add subidentifier 318 to 336 under ibevtModuleSwitchType by zhaiyingying
-- V4.14 2006-03-14 add subidentifier 175 under ibevtPortSwitchType by wangyahui
--                  add subidentifier 502 to 504 under ibevtModuleSwitchType by wangyahui
-- V4.15 2006-04-03 add subidentifier 176 under ibevtPortSwitchType by wangyahui
-- V4.16 2006-04-26 add subidentifier 229 to 233 under ibevtModuleRouterType by taotao
-- V4.17 2006-04-21 add subidentifier 337 to 340 under ibevtModuleSwitchType by zhaiyingying
-- V4.18 2006-06-05 add subidentifier 704 to 705 under ibevtModuleSwitchType by zhangxianguo
--                  add subidentifier 505 to 506 under ibevtModuleSwitchType by zhangjianfeng
--                  add subidentifier 341 to 349 under ibevtModuleSwitchType by zhaiyingying
--                  add subidentifier 177 to 178 under ibevtPortSwitchType by zhangjianfeng
--                  add subidentifier 179 to 180 under ibevtPortSwitchType by zhangxianguo
-- V4.19 2006-08-23 add subidentifier 507 to 509 under ibevtModuleSwitchType by wangyahui
--                  modify object name of subidentifier 502 and 503 under ibevtModuleSwitchType by wangyahui
--                  add subidentifier 234 to 235 under ibevtModuleRouterType by liutinghai
--                  add subidentifier 350 to 357 under ibevtModuleSwitchType by zhaiyingying
-- V4.20 2006-09-26 add subidentifier 510 to 514 under ibevtModuleSwitchType by wangyahui
--                  add subidentifier 601 to 603 under ibevtModuleRouterType by zhoujianming
--                  add subidentifier 236 to 239 under ibevtModuleRouterType by qikai
--                  add subidentifier 240 to 241 under ibevtModuleRouterType by liutinghai
--                  add subidentifier 800 to 801 under ibevtModuleSwitchType by luoguixing
-- V4.21 2006-10-26 add subidentifier 358 to 370 under ibevtModuleSwitchType by zhaiyingying
--                  add subidentifier 183 under ibevtPortSwitchType by zhaiyingying
--                  add subidentifier 515 to 526 under ibevtModuleSwitchType by wangyahui
--                  add subidentifier 181 to 182 under ibevtPortSwitchType by wangyahui
-- V4.22 2006-11-02 add subidentifier 527 to 536 under ibevtModuleSwitchType by wangyahui
--                  modify description of 511 to 513 under ibevtModuleSwitchType by wangyahui
--       2006-11-10 add subidentifier 371 to 378 under ibevtModuleSwitchType by shuxiongtao
--       2006-11-08 add subidentifier 184 to 185 under ibevtPortSwitchType by zhaiyingying
-- V4.23 2006-12-04 add subidentifier 242 to 243 under ibevtModuleRouterType by liutinghai
-- V4.24 2006-01-24 add subidentifier 244 to 245 under ibevtModuleRouterType by liutinghai
-- V4.25 2007-03-19 add subidentifier 537 under ibevtModuleSwitchType by wangyahui
-- V4.26 2007-04-12 add subidentifier 538 to 542 under ibevtModuleSwitchType by wangyahui
-- V4.27 2007-04-25 add subidentifier 706 under ibevtModuleSwitchType by zhangzongyi
--                  add subidentifier 379 to 380 under ibevtModuleSwitchType by zhaiyingying
--                  add subidentifier 246 to 250 under ibevtModuleRouterType by liutinghai
--                  add subidentifier 42 under ibevtPortRouterType by liutinghai
-- V4.28 2007-05-28 add subidentifier 707 under ibevtModuleSwitchType by ligaoxu
--                  add subidentifier 381 to 392 under ibevtModuleSwitchType by shuxiongtao
--                  modify name of subidentifier 371 and 374 under ibevtModuleSwitchType by shuxiongtao
--                  add subidentifier 251 to 253 under ibevtModuleRouterType by qikai
--                  add subidentifier 254 to 255 under ibevtModuleRouterType by liutinghai
--                  add subidentifier 186 under ibevtPortSwitchType by jinzhaoqiong
-- V4.29 2007-07-09 add subidentifier 543 to 551 under ibevtModuleSwitchType by zhangjianfeng
--                  add subidentifier 552 to 554 under ibevtModuleSwitchType by wangyahui
-- V4.30 2007-07-26 add subidentifier 400 under ibevtModuleRouterType by xuejiayong
--                  add subidentifier 708 under ibevtModuleSwitchType by xiuyihong
--                  add subidentifier 256 to 258 under ibevtModuleRouterType by qikai
--                  add subidentifier 259 to 263 under ibevtModuleRouterType by liutinghai
--                  add subidentifier 3 to 5 under ibevtOther by gaolong
-- V4.31 2007-08-27 add subidentifier 187 to 188 under ibevtPortSwitchType by ruanhan
--                  add subidentifier 802 to 804 under ibevtModuleSwitchType by luoguixing
--                  add subidentifier 393 to 397 under ibevtModuleSwitchType by shuxiongtao
-- V4.32 2007-09-25 add subidentifier 555 to 559 under ibevtModuleSwitchType by wangyahui
--                  add subidentifier 805 under ibevtModuleSwitchType by luoguixing
--                  add subidentifier 401 to 403 under ibevtModuleRouterType by tanwen
--                  add subidentifier 43 under ibevtPortRouterType by qikai
--                  add subidentifier 266 to 267 under ibevtModuleRouterType by qikai
--                  add subidentifier 398 to 399 under ibevtModuleSwitchType by hexuefei
-- V4.33 2007-10-22 add subidentifier 189 under ibevtPortSwitchType by liaoxin
--                  add subidentifier 268 under ibevtModuleRouterType by liutinghai
-- V4.34 2007-11-26 add subidentifier 269 to 273 under ibevtModuleRouterType by liutinghai
--                  add subidentifier 274 to 276 under ibevtModuleRouterType by qikai
--                  add subidentifier 404 to 406 under ibevtModuleRouterType by chaiyaqin
--                  add subidentifier 400 to 407 under ibevtModuleSwitchType by shuxiongtao
-- V4.35 2007-12-27 add subidentifier 277 to 278 under ibevtModuleRouterType by liutinghai
--                  add subidentifier 560 to 568 under ibevtModuleSwitchType by wangyahui
-- V4.36 2008-01-30 add subidentifier 408 under ibevtModuleSwitchType by hexuefei
--                  add subidentifier 569 to 572 under ibevtModuleSwitchType by wangyahui
--                  add subidentifier 279 to 280 under ibevtModuleRouterType by qikai
--                  add subidentifier 190 under ibevtPortSwitchType by liujingya
-- V4.37 2008-02-20 add subidentifier 720 to 724 under ibevtModuleSwitchType by chaiyaqin
--                  add subidentifier 573 to 574 under ibevtModuleSwitchType by zhangjianfeng
--                  modify name of subidentifier 546 and 550 under ibevtModuleSwitchType by zhangjianfeng
--                  add subidentifier 575 to 576 under ibevtModuleSwitchType by wangyahui
--                  add subidentifier 281 under ibevtModuleRouterType by liutinghai
-- V4.38 2008-03-31 add subidentifier 806 to 808 under ibevtModuleSwitchType by luoguixing
--                  add subidentifier 709 to 715 under ibevtModuleSwitchType by wangcong
--                  add subidentifier 191 to 196 under ibevtPortSwitchType by wangcong
--                  add subidentifier 44 under ibevtPortRouterType by liutinghai
--                  add subidentifier 409 to 431 under ibevtModuleSwitchType by zhaiyingying
--                  add subidentifier 432 under ibevtModuleSwitchType by shuxiongtao
-- V4.39 2008-04-29 add subidentifier 577 to 589 under ibevtModuleSwitchType by wangyahui
--                  add subidentifier 407 to 409 under ibevtModuleRouterType by tanwen
-- V4.40 2008-05-31 add subidentifier 410 to 413 under ibevtModuleRouterType by tanwen
--                  add subidentifier 282 to 284 under ibevtModuleRouterType by qikai
--                  add subidentifier 285 to 286 under ibevtModuleRouterType by liutinghai
-- V4.41 2008-07-28 add subidentifier 590 to 592 under ibevtModuleSwitchType by wangyahui
--                  add subidentifier 287 to 289 under ibevtModuleRouterType by qikai
--                  add subidentifier 290 to 291 under ibevtModuleRouterType by liutinghai
--                  add subidentifier 45 to 46 under ibevtPortRouterType by liutinghai
--                  add subidentifier 809 to 810 under ibevtModuleSwitchType by luoguixing
-- V4.42 2008-08-26 modify name of 379 and 399 under ibevtModuleSwitchType by wangwei
--                  modify description of 408 under ibevtModuleSwitchType by wangwei
--                  modify name and description of 804 under ibevtModuleSwitchType by wangwei
--                  add subidentifier 433 to 434 under ibevtModuleSwitchType by wangwei
--                  add subidentifier 593 to 595 under ibevtModuleSwitchType by wangyahui
--                  modify name and description of 256 and 288 under ibevtPortRouterType by qikai
--                  add subidentifier 292 to 293 under ibevtPortRouterType by qikai
-- V4.43 2008-10-13 add subidentifier 725 under ibevtModuleSwitchType by ruanhan
--                  add subidentifier 197 under ibevtPortSwitchType by ruanhan
--                  add subidentifier 811 under ibevtModuleSwitchType by luoguixing
--                  add subidentifier 596 to 601 under ibevtModuleSwitchType by wangyahui
-- V4.44 2008-11-04 add subidentifier 294 under ibevtPortRouterType by qikai
--                  add subidentifier 414 under ibevtModuleRouterType by tanwen
-- V4.45 2008-12-01 add subidentifier 602 to 619 under ibevtModuleSwitchType by wangyahui
--                  add subidentifier 435 to 442 under ibevtModuleSwitchType by zhaiyingying
--                  modify name of 546 under ibevtModuleSwitchType by zhangjianfeng
--                  add subidentifier 295 under ibevtPortRouterType by qikai
--                  add subidentifier 443 under ibevtModuleSwitchType by shuxiongtao
-- V4.46 2008-12-25 add subidentifier 620 to 622 under ibevtModuleSwitchType by wangyahui
--                  add subidentifier 716 to 718 under ibevtModuleSwitchType by zhangshilin
--                  add subidentifier 444 to 445 under ibevtModuleSwitchType by wangchang
-- V4.47 2009-03-02 add subidentifier 446 to 452 under ibevtModuleSwitchType by wangchang
--                  add subidentifier 719 under ibevtModuleSwitchType by zhangshilin
--                  add subidentifier 623 to 633 under ibevtModuleSwitchType by wangyahui
-- V4.48 2009-03-31 add subidentifier 415 under ibevtModuleRouterType by tanwen
--                  add subidentifier 296 under ibevtPortRouterType by qikai
--                  add subidentifier 297 to 298 under ibevtPortRouterType by qianjialin
--                  add subidentifier 453 to 464 under ibevtModuleSwitchType by huyinxing
-- V4.49 2009-07-02 add subidentifier 299 to 302 under ibevtModuleRouterType by qikai
--                  add subidentifier 303 under ibevtModuleRouterType by chenfeihu
--                  add subidentifier 304 to 307 under ibevtModuleRouterType by qianjialin
--                  add subidentifier 634 to 637 under ibevtModuleSwitchType by wangyahui
--                  add subidentifier 604 to 606 under ibevtModuleRouterType by chenjianhui
--                  add subidentifier 465 to 468 under ibevtModuleSwitchType by zhaiyingying
--                  add subidentifier 469 to 472 under ibevtModuleSwitchType by huyinxing
--                  add subidentifier 198 under ibevtPortSwitchType by huyinxing
--                  add subidentifier 199 under ibevtPortSwitchType by zhangjianfeng
-- V4.50 2009-08-28 add subidentifier 638 to 640 under ibevtModuleSwitchType by wangyahui
--                  add subidentifier 308 to 310 under ibevtModuleRouterType by qianjialin
-- V4.51 2009-11-09 add subidentifier 726 under ibevtModuleSwitchType by ruanhan
--                  add subidentifier 641 under ibevtModuleSwitchType by wangyahui
--                  add subidentifier 473 to 477 under ibevtModuleSwitchType by yudongyang
--                  add subidentifier 478 to 485 under ibevtModuleSwitchType by heweibin
-- V4.52 2009-12-31 add subidentifier 200 to 201 under ibevtPortSwitchType by zhanghaiyang
--                  add subidentifier 642 to 651 under ibevtModuleSwitchType by wangyahui
--                  add subidentifier 416 under ibevtModuleRouterType by lixiaomin
--                  add subidentifier 486 under ibevtModuleSwitchType by yudongyang
--                  add subidentifier 727 to 728 under ibevtModuleSwitchType by xiaobing
--                  add subidentifier 652 to 659 under ibevtModuleSwitchType by wangyahui
--                  add subidentifier 487 to 488 under ibevtModuleSwitchType by huyinxing
--                  add subidentifier 660 to 662 under ibevtModuleSwitchType by wangyahui
--                  add subidentifier 202 to 203 under ibevtPortSwitchType by yangdonghong
-- V4.53 2010-03-03 add subidentifier 812 under ibevtModuleSwitchType by mashuhang
--                  add subidentifier 489 to 497 under ibevtModuleSwitchType by liubuxiang
--                  add subidentifier 498 to 499 under ibevtModuleSwitchType by shikejun
--                  add subidentifier 900 under ibevtModuleSwitchType by yangqiulin
--                  add subidentifier 901 to 902 under ibevtModuleSwitchType by huyinxing
-- V4.54 2010-04-21 add subidentifier 903 to 904 under ibevtModuleSwitchType by huyinxing
--                  add subidentifier 905 to 907 under ibevtModuleSwitchType by shikejun
--                  add subidentifier 663 to 685 under ibevtModuleSwitchType by wangyahui
--                  add subidentifier 813 under ibevtModuleSwitchType by mashuhang
--                  add subidentifier 729 under ibevtModuleSwitchType by zhangshilin
--                  add subidentifier 908 to 913 under ibevtModuleSwitchType by yangbin
--                  add subidentifier 914 to 918 under ibevtModuleSwitchType by huyinxing
--                  add subidentifier 5000 to 5011 under ibevtModuleRouterType by qianjialin
--                  add subidentifier 919 to 927 under ibevtModuleSwitchType by langgaoyi
-- V4.55 2011-01-31 add subidentifier 417 under ibevtModuleRouterType by tanwen
--                  add subidentifier 311 to 314 under ibevtModuleRouterType by qianjialin
--                  add subidentifier 686 to 691 under ibevtModuleSwitchType by wangyahui
--                  add subidentifier 928 to 929 under ibevtModuleSwitchType by langgaoyi
-- V4.56 2011-04-22 add subidentifier 930 under ibevtModuleSwitchType by liuhui
--                  add subidentifier 814 to 815 under ibevtModuleSwitchType by mashuhang
--                  add subidentifier 692 to 694 under ibevtModuleSwitchType by wangyahui
--                  add subidentifier 204 under ibevtPortSwitchType by yangliming
-- V4.57 2011-06-30 add subidentifier 695, 1201 to 1211 under ibevtModuleSwitchType by wangyahui
--                  add subidentifier 205 to 207 under ibevtPortSwitchType by gaoruichang
-- V4.58 2011-08-31 add subidentifier 696 to 697 under ibevtModuleSwitchType by langgaoyi
--                  add subidentifier 208 under ibevtPortSwitchType by wangshunli
--                  add subidentifier 931 to 933 under ibevtModuleSwitchType by langgaoyi
--                  add subidentifier 934 under ibevtModuleSwitchType by zhaohonghai
-- V4.59 2012-04-20 add subidentifier 935 to 938, 942 under ibevtModuleSwitchType by wangjiangnan
--                  add subidentifier 1212 to 1218 under ibevtModuleSwitchType by wangyahui
--                  add subidentifier 939 to 941 under ibevtModuleSwitchType by herui
--                  modify name of 205 to 207 under ibevtPortSwitchType by xvman
--                  add subidentifier 350 to 360 under ibevtModuleRouterType by chenfeihu
--                  add subidentifier 943 to 945 under ibevtModuleSwitchType by langgaoyi
--                  add subidentifier 209, 211 under ibevtPortSwitchType by wangyahui
--                  add subidentifier 730 to 731 under ibevtModuleSwitchType by panxiyuan
--                  add subidentifier 210 under ibevtPortSwitchType by panxiyuan
--                  add subidentifier 315 to 349 under ibevtModuleRouterType by qianjialin
--                  add subidentifier 946 to 948 under ibevtModuleSwitchType by zhangheng
--                  add subidentifier 949 to 956 under ibevtModuleSwitchType by zhengjiang
--                  add subidentifier 957 under ibevtModuleSwitchType by zhaohonghai
--                  add subidentifier 361 to 372 under ibevtModuleRouterType by qianjialin
--                  add subidentifier 212 under ibevtPortSwitchType by wangyahui
--                  add subidentifier 732 under ibevtModuleSwitchType by houchengshuai
--                  add subidentifier 1219 to 1230 under ibevtModuleSwitchType by wangyahui
-- V4.60 2013-01-07 add subidentifier 733 under ibevtModuleSwitchType by shixuemei
--                  add subidentifier 958 to 959 under hibevtModuleSwitchType by zhaohonghai
--                  add subidentifier 960 to 965, 996 under ibevtModuleSwitchType by zhangheng
--                  add subidentifier 966 to 988 under ibevtModuleSwitchType by yebiaoxiang
--                  add subidentifier 989 to 995 under ibevtModuleSwitchType by zhaohonghai
--                  add subidentifier 1231 to 1255 under ibevtModuleSwitchType by wangyahui
--                  add subidentifier 373 to 388 under ibevtModuleRouterType by qianjialin
--                  add subidentifier 1400 to 1410 under ibevtModuleSwitchType by qizhenglin
--                  add subidentifier 213 to 219 under ibevtPortSwitchType by yebiaoxiang
--                  add subidentifier 47 under ibevtPortRouterType by qianjialin
--                  add subidentifier 418 under ibevtModuleRouterType by tanwen
--                  modify name of 673, 1214, 1215 under ibevtModuleSwitchType by wangyahui
-- V4.61 2013-04-26 add subidentifier 1256 to 1269 under ibevtModuleSwitchType by wangyahui
--                  add subidentifier 607 to 610 under ibevtModuleRouterType by jiangwendong
--                  add subidentifier 220 to 222 under ibevtPortSwitchType by jiangyongjiang
--                  add subidentifier 389 to 392 under ibevtModuleRouterType by chenfeihu
--                  add subidentifier 393 to 398 under ibevtModuleRouterType by qianjialin
--                  modify name of 975 to 982 under ibevtModuleSwitchType by lihaijun
--                  add subidentifier 997 to 1015 under ibevtModuleSwitchType by chenke
--                  add subidentifier 1016 to 1018 under ibevtModuleSwitchType by jiangyongjiang
--                  add subidentifier 1270 to 1273 under ibevtModuleSwitchType by sunzhenxing
--                  add subidentifier 1 to 8 under ibevtModuleCommonCards by zhouxiaodong
-- V4.62 2013-10-10 add subidentifier 419 to 431 under ibevtModuleRouterType by tanwen
--                  add subidentifier 611 under ibevtModuleRouterType by jiangwendong
--                  add subidentifier 399, 800 to 804, 807 under ibevtModuleRouterType by qianjialin
--                  add subidentifier 805 to 806 under ibevtModuleRouterType by chenfeihu
--                  add subidentifier 1274 to 1279, 1293 to 1296 under ibevtModuleSwitchType by lihaijun
--                  add subidentifier 1019 to 1024 under ibevtModuleSwitchType by zhaohonghai
--                  add subidentifier 1280 to 1287, 1298 to 1306 under ibevtModuleSwitchType by sunzhenxing
--                  add subidentifier 1025, 1028, 1029, 1050 under ibevtModuleSwitchType by jiangyongjiang
--                  add subidentifier 1026 to 1027, 1030 to 1049 under ibevtModuleSwitchType by chenke
--                  add subidentifier 816 under ibevtModuleSwitchType by luoguixing
--                  add subidentifier 1288 to 1292, 1297 under ibevtModuleSwitchType by wujili
--                  modify name of 1234 to 1236 under ibevtModuleSwitchType by lihaijun
--                  add subidentifier 48 to 49 under ibevtPortRouterType by jiangwendong
--                  add subidentifier 223 to 224 under ibevtPortSwitchType by jiangyongjiang
-- V4.63 2014-01-26 add subidentifier 432 under ibevtModuleRouterType by zhaowenbin
--                  add subidentifier 808 to 809, 814 under ibevtModuleRouterType by qianjialin
--                  add subidentifier 810 to 813, 815 to 817 under ibevtModuleRouterType by chenfeihu
--                  add subidentifier 734 to 739 under ibevtModuleSwitchType by panxiyuan
--                  modify name of 1032 to 1041 under ibevtModuleSwitchType by chenke
--                  add subidentifier 1051 to 1055 under ibevtModuleSwitchType by zhaohonghai
--                  add subidentifier 1056 to 1058 under ibevtModuleSwitchType by chenke
--                  add subidentifier 1307 to 1313 under ibevtModuleSwitchType by wujili
--                  add subidentifier 1314 to 1316 under ibevtModuleSwitchType by lihaijun
--                  add subidentifier 1317 to 1319 under ibevtModuleSwitchType by sunzhenxing
--                  add subidentifier 1320 to 1326 under ibevtModuleSwitchType by jiangyongjiang
-- V4.64 2014-04-25 add subidentifier 1059 to 1069 under ibevtPortSwitchType by youhua
--                  add subidentifier 1070 to 1102 under ibevtModuleSwitchType by chenke
--                  add subidentifier 1103 to 1107 under ibevtModuleSwitchType by lihaijun
--                  add subidentifier 1108 under ibevtModuleSwitchType by zhaohonghai
--                  add subidentifier 1327 to 1328 under ibevtModuleSwitchType by sunzhenxing
--                  add subidentifier 1329 to 1331 under ibevtModuleSwitchType by lihaijun
--                  add subidentifier 1332 to 1371 under ibevtModuleSwitchType by jiangyongjiang
--                  add subidentifier 1372 to 1373 under ibevtModuleSwitchType by sunzhenxing
--                  modify name of 733 under ibevtModuleSwitchType by maoyun
--                  add subidentifier 740 to 743 ibevtModuleSwitchType by tanxiaopeng
--                  add subidentifier 433 under ibevtModuleRouterType by zhaowenbin
--                  add subidentifier 818 to 822, 824 to 825 under ibevtModuleRouterType by chenfeihu
--                  add subidentifier 823 under ibevtModuleRouterType by qianjialin
--                  add subidentifier 50 to 51 under ibevtPortRouterType by chenfeihu
--                  add subidentifier 225 to 232 under ibevtPortSwitchType by pantao
--                  modify name of 1400, remove 1401 to 1410 under ibevtModuleSwitchType by qizhenglin
-- V4.65 2014-09-18 add subidentifier 434 under ibevtModuleRouterType by zhaowenbin
--                  add subidentifier 612 to 615 under ibevtModuleRouterType by jiangwendong
--                  add subidentifier 826 to 833, 840 under ibevtModuleRouterType by qianjialin
--                  add subidentifier 834 to 839 under ibevtModuleRouterType by chenfeihu
--                  add subidentifier 52 under ibevtPortRouterType by jiangwendong
--                  add subidentifier 744 ibevtModuleSwitchType by tanxiaopeng
--                  add subidentifier 1109 to 1117 under ibevtModuleSwitchType by chenke
--                  add subidentifier 1118 to 1119, 1375 to 1376 under ibevtModuleSwitchType by lihaijun
--                  add subidentifier 1374, 1382 to 1385 under ibevtModuleSwitchType by jiangyongjiang
--                  add subidentifier 1377 to 1381, 1386 to 1389 under ibevtModuleSwitchType by sunzhenxing
--                  modify description of 1010 under ibevtModuleSwitchType by chenke
--                  modify name of 1320 to 1325, 1332 to 1371 under ibevtModuleSwitchType by jiangyongjiang
--                  add subidentifier 8 to 35 under ibevtPowerSupply, 3 to 23 under ibevtFan by jiangyongjiang
-- V4.66 2015-04-18 add subidentifier 435 under ibevtModuleRouterType by zhaowenbin
--                  add subidentifier 841 to 854 under ibevtModuleRouterType by qianjialin
--                  add subidentifier 855 to 858 under ibevtModuleRouterType by zhaohonghai
--                  add subidentifier 745 to 747 ibevtModuleSwitchType by tanxiaopeng
--                  add subidentifier 748 ibevtModuleSwitchType by wangshunli
--                  add subidentifier 1120 to 1125, 1127 to 1128, 1390 to 1397,
--                                    1647 to 1649, 1667 to 1673 under ibevtModuleSwitchType by lihaijun
--                  add subidentifier 1126 under ibevtModuleSwitchType by chenke
--                  add subidentifier 1129 to 1144 under ibevtPortSwitchType by youhua
--                  add subidentifier 1398, 1399, 1600 to 1605, 1623 to 1646,
--                                    1650 to 1652, 1660 to 1666, 1674 to 1685
--                                    under ibevtModuleSwitchType by jiangyongjiang
--                  add subidentifier 1606 to 1622 under ibevtModuleSwitchType by sunzhenxing
--                  add subidentifier 1653 to 1659 under ibevtModuleSwitchType by zhaiwanqing
--                  add subidentifier 233 to 237, 239 to 253 under ibevtPortSwitchType by pantao
--                  add subidentifier 238 under ibevtPortSwitchType by chenke
--                  modify name of 1315 and 1316 under ibevtModuleSwitchType by lihaijun
-- V4.67 2016-04-02 add subidentifier 436 to 437, 448 to 449 under ibevtModuleRouterType by zhaowenbin
--                  add subidentifier 438 to 439 and 616 to 618 under ibevtModuleRouterType by sunqingyan
--                  add subidentifier 440 under ibevtModuleRouterType by chengaishuang
--                  add subidentifier 441 to 446 under ibevtModuleRouterType by yaoshuo
--                  add subidentifier 447 under ibevtModuleRouterType by dongchanghai
--                  modify name of 856 to 858 under ibevtModuleSwitchType by zhaohonghai
--                  add subidentifier 859 to 862 under ibevtModuleRouterType by zhaohonghai
--                  add subidentifier 863 under ibevtModuleRouterType by qianjialin
--                  add subidentifier 864 to 878 under ibevtModuleRouterType by chenfeihu
--                  add subidentifier 879 to 884 under ibevtModuleRouterType by fujuan
--                  add subidentifier 749 under ibevtModuleSwitchType by wangshunli
--                  add subidentifier 750 under ibevtModuleSwitchType by yangjianlin
--                  add subidentifier 751 to 752 ibevtModuleSwitchType by mengfanhua
--                  add subidentifier 753 to 756 under ibevtModuleSwitchType by songkeke
--                  add subidentifier 1145, 1149 under ibevtPortSwitchType by youhua
--                  add subidentifier 1146 to 1148, 1150 to 1154 under ibevtPortSwitchType by chenke
--                  add subidentifier 1686 to 1694, 1710 to 1722, 1742 to 1760, 1767 to 1784, 1789 to 1793
--                                    under ibevtModuleSwitchType by jiangyongjiang
--                  add subidentifier 1695 to 1696 under ibevtModuleSwitchType by zhaiwanqing
--                  add subidentifier 1697 to 1709, 1723 to 1741, 1761 to 1766, 1785 to 1788, 1794 to 1805
--                                    under ibevtModuleSwitchType by lihaijun
--                  add subidentifier 53 to 54 under ibevtPortRouterType by chenfeihu
--                  add subidentifier 55 under ibevtPortRouterType by fujuan
--                  add subidentifier 56 under ibevtPortRouterType by qianjialin
--                  modify name of 1128 under ibevtModuleSwitchType by lihaijun
--                  modify description of 1673 under ibevtModuleSwitchType by lihaijun
--                  add subidentifier 254 to 262, 264 to 265 under ibevtPortSwitchType by guolei
--                  add subidentifier 263 under ibevtPortSwitchType by zhanghuimin
-- V4.68 2018-04-13 add subidentifier 1806 to 1829 under ibevtModuleSwitchType by jiangyongjiang
--                  add subidentifier 266 under ibevtPortSwitchType by guolei
--                  add subidentifier 1830 to 1841 under ibevtModuleSwitchType by lihaijun
--                  add subidentifier 757 to 758 under ibevtModuleSwitchType by wangshunli
--                  add subidentifier 1842 under ibevtModuleSwitchType by zhaoshihong
--                  add subidentifier 1843 to 1846 under ibevtModuleSwitchType by jiangyongjiang
--                  add subidentifier 759 under ibevtModuleSwitchType by mengfanhua
--                  add subidentifier 1847 under ibevtModuleSwitchType by jiangyongjiang
--                  add subidentifier 619 to 620 under ibevtModuleRouterType by songyanqing
--                  add subidentifier 1848 to 1849 under ibevtModuleSwitchType by lihaijun
--                  add subidentifier 885 to 886 under ibevtModuleRouterType by zhaohonghai
--                  add subidentifier 1850 to 1852 under ibevtModuleSwitchType by jiangyongjiang
--                  add subidentifier 1853 to 1857 under ibevtModuleSwitchType by lihaijun
--                  add subidentifier 1858 to 1862 under ibevtModuleSwitchType by lihaijun
--                  add subidentifier 1863 to 1893 under ibevtModuleSwitchType by jiangyongjiang
--                  add subidentifier 1155 to 1170 under ibevtModuleSwitchType by chenke
--                  add subidentifier 1894 to 1895 under ibevtModuleSwitchType by lihaijun
--                  add subidentifier 1896 under ibevtModuleSwitchType by jiangyongjiang
--                  add subidentifier 267 under ibevtPortSwitchType by guolei
--                  add subidentifier 887 to 889 under ibevtModuleRouterType by mazheng
--                  add subidentifier 1171 to 1176 under ibevtModuleSwitchType by chenke
--                  add subidentifier 1897 to 1904 under ibevtModuleSwitchType by jiangyongjiang
--                  add subidentifier 1905 ibevtModuleSwitchType by liuyanpeng
--                  add subidentifier 450 to 454 ibevtModuleRouterType by dongchanghai
--                  add subidentifier 1906 to 1907 ibevtModuleSwitchType by jiangyongjiang
--                  add subidentifier 1908 ibevtModuleSwitchType by liuyanpeng
--                  add subidentifier 1177 to 1181 under ibevtModuleSwitchType by chenke
--                  add subidentifier 760 to 762 ibevtModuleSwitchType by mengfanhua
--                  add subidentifier 890 to 894 under ibevtModuleRouterType by fujuan
--                  modify name of subidentifier 872 and 873 under ibevtModuleRouterType by fujuan
--                  add subidentifier 1909 to 1910 under ibevtModuleSwitchType by lihaijun
--                  add subidentifier 455 to 456 ibevtModuleRouterType by yaoshuo
--                  add subidentifier 1911 to 1935 under ibevtModuleSwitchType by jiangyongjiang
--                  add subidentifier 457 under ibevtModuleRouterType by lizhifeng
--                  add subidentifier 895 to 899 under ibevtModuleRouterType by zhaohonghai
--                  add subidentifier 1936 to 1938 under ibevtModuleSwitchType by zhangkun
--                  add subidentifier 1939 to 1941 under ibevtModuleSwitchType by jiangyongjiang
--                  add subidentifier 6 to 8 under ibevtOther by chenke
--                  add subidentifier 458 to 462 under ibevtModuleRouterType by wangchunlei
--                  add subidentifier 900 to 906 under ibevtModuleRouterType by fujuan
--                  add subidentifier 1182 under ibevtModuleSwitchType by youhua
--                  add subidentifier 1942 under ibevtModuleSwitchType by lihaijun
--                  add subidentifier 1943 to 1953 under ibevtModuleSwitchType by jiangyongjiang
--                  add subidentifier 463 to 468 under ibevtModuleRouterType by dongchanghai
--                  add subidentifier 1183 to 1196 under ibevtModuleSwitchType by chenke
--                  add subidentifier 907 to 921 under ibevtModuleRouterType by zhongchao
--                  add subidentifier 763 to 764 under ibevtModuleSwitchType by sunfang
--                  add subidentifier 1954 to 1957 under ibevtModuleSwitchType by lihaijun
--                  add subidentifier 1958 to 1972 under ibevtModuleSwitchType by jiangyongjiang
--                  add subidentifier 1973 to 1979 ibevtModuleSwitchType by lihaijun
--                  add subidentifier 1980 to 1981 ibevtModuleSwitchType by jiangyongjiang
--                  add subidentifier 274 to 279 under ibevtModuleSwitchType by guolei
--                  add subidentifier 469 under ibevtModuleRouterType by maxiaojie
--                  add subidentifier 470 to 473 under ibevtModuleSwitchType by fuzhanfeng
--                  add subidentifier 765 under ibevtModuleSwitchType by mengfanhua
--                  add subidentifier 1982 to 1985 ibevtModuleSwitchType by  lihaijun
--                  add subidentifier 1986 to 2003 ibevtModuleSwitchType by  jiangyongjiang
--                  add subidentifier 922 under ibevtModuleRouterType by mazheng
--                  add subidentifier 58 under ibevtPortRouterType by liuhua
--                  add subidentifier 474 to 477 under ibevtModuleSwitchType by tanyan
--                  add subidentifier 2004 to 2005 ibevtModuleSwitchType by  lihaijun
--                  add subidentifier 2006 to 2008 ibevtModuleSwitchType by  jiangyongjiang
--                  add subidentifier 2009 to 2015 ibevtModuleSwitchType by  lihaijun
--                  add subidentifier 1401 to 1450 under ibevtModuleSwitchType by chenke
--                  add subidentifier 923 under ibevtModuleRouterType by zhongchao
--                  add subidentifier 924 to 933 under ibevtModuleRouterType by fujuan
--                  add subidentifier 766 to 768 under ibevtModuleSwitchType by wangshunli
--                  add subidentifier 482 to 483 under ibevtModuleSwitchType by cuipeilei
--                  add subidentifier 35 to 37 under ibevtPowerSupply by wangchunlei
--                  add subidentifier 24 to 25 under  ibevtFan by wangchunlei
--                  add subidentifier 484 to 489 under ibevtModuleSwitchType by wangchunlei
--                  add subidentifier 938 under ibevtModuleRouterType by fujuan
--                  add subidentifier 491 to 492 under ibevtModuleSwitchType by fuzhanfeng
--                  add subidentifier 939 under ibevtModuleRouterType by zhongchao
--                  add subidentifier 769 under ibevtModuleSwitchType by yangjianlin
--                  add subidentifier 940 to 945 under ibevtModuleRouterType by fujuan
--                  add subidentifier 946 to 953 under ibevtModuleRouterType by zhaochao
--                  add subidentifier 493 under ibevtModuleSwitchType by liyujun
--                  add subidentifier 2016 to 2017 ibevtModuleSwitchType by  jiangyongjiang
--                  add subidentifier 769 to 770 under ibevtModuleSwitchType by yangjianlin
--                  add subidentifier 494 to 497 under ibevtModuleSwitchType by yangyuan
--                  add subidentifier 2018 to 2021 ibevtModuleSwitchType by  lihaijun
--                  add subidentifier 280 under ibevtPortSwitchType by yuanzhi
--                  add subidentifier 2022 to 2047 ibevtModuleSwitchType by  jiangyongjiang
--                  add subidentifier 281 to 283 under ibevtPortSw by wangshunli
--                  add subidentifier 954 to 958 under ibevtModuleRouterType by fujuan
--                  add subidentifier 959 to 960 under ibevtModuleRouterType by zhongchao
--                  add subidentifier 284 to 285 under ibevtPortSwitchType by guolei
--                  add subidentifier 771 to 775 under ibevtModuleSwitchType by wangshunli
--                  add subidentifier 961 to 962 under ibevtModuleRouterType by fujuan
--                  add subidentifier 963 to 968 under ibevtModuleRouterType by zhongchao
--                  modify name of 1822 and 1825 under ibevtModuleSwitchType by jiangyongjiang
--                  add subidentifier 499 to 508 under ibevtModuleSwitchType by tanyan
--                  add subidentifier 969 under ibevtModuleRouterType by fujuan
--                  add subidentifier 970 to 973 under ibevtModuleRouterType by zhongchao
--                  add subidentifier 2048 to 2049 ibevtModuleSwitchType by  lihaijun
--                  add subidentifier 2050 to 2055 ibevtModuleSwitchType by  jiangyongjiang
--                  add subidentifier 974 to 980 under ibevtModuleRouterType by zhaomeng
--                  add subidentifier 286 under ibevtPortSwitchType by zhaomeng
--                  add subidentifier 502 to 517 under ibevtModuleSwitchType by fuzhanfeng
--                  add subidentifier 287 under ibevtPortSwitchType by guolei
-- V4.69 2019-01-15 add subidentifier 518 to 519 under ibevtModuleSwitchType by tanyan
--                  add subidentifier 520 under ibevtModuleSwitchType by fuzhanfeng
--                  add subidentifier 287 under ibevtPortSwitchType by qinjuan
--                  add subidentifier 1451 to 1456 under ibevtModuleSwitchType by chenke
--                  add subidentifier 2056 to 2060 ibevtModuleSwitchType by  jiangyongjiang
-- V4.70 2019-01-21 add subidentifier 2061 to 2063 under ibevtModuleSwitchType by jiangyongjiang
--                  add subidentifier 1457 to 1459 under ibevtModuleSwitchType by  zhanglili
--       2019-02-12 add subidentifier 2064 to 2072 under ibevtModuleSwitchType by lihaijun
--                  add subidentifier 521 to 530 under ibevtModuleSwitchType by fuzhanfeng
--                  add subidentifier 621 to 625 under ibevtModuleRouterType by wangxinmeng
--                  add subidentifier 776 to 777 under ibevtModuleSwitchType by wangshunli
--                  modify name of 966 to 968, 970 to 971,980 under ibevtModuleSwitchType by zhaomeng
--                  add subidentifier 289 to 290 under ibevtModuleSwitchType by wangzilong
--                  add subidentifier 981 to 984 under ibevtModuleRouterType  by fujuan
--                  add subidentifier 985 to 986 under ibevtModuleRouterType wangxinmeng
--                  add subidentifier 987 to 989 under ibevtModuleRouterType  by fuzhanfeng
--                  add subidentifier 990  under ibevtModuleRouterType wangxinmeng
--                  add subidentifier 991 to 1004 under ibevtModuleRouterType  by fuzhanfeng
--                  add subidentifier 1005 under ibevtModuleRouterType  by zhaomeng
--                  add subidentifier 2076 under ibevtModuleSwitchType by maoyun
--                  add subidentifier 2077 under ibevtModuleSwitchType by jiangyongjiang
--                  add subidentifier 2078 to 2081 under ibevtModuleSwitchType by chenke
--                  add subidentifier 2082 to 2108 under ibevtModuleSwitchType by jiangyongjiang
--                  add subidentifier 2109 to 2111 under ibevtModuleSwitchType by maoyun
--                  add subidentifier 2112 under ibevtModuleSwitchType by chenke
--                  add subidentifier 291 to 292  under ibevtPortSwitchType wangzilong
--                  add subidentifier 2113 to 2116 under ibevtModuleSwitchType by lihaijun
--                  add subidentifier 2117 to 2118 under ibevtModuleSwitchType by chenke
--                  add subidentifier 2119 to 2129 under ibevtModuleSwitchType by jiangyongjian
--                  add subidentifier 2130 under ibevtModuleSwitchType by maoyun
--                  add subidentifier 1006 under ibevtModuleRouterType by fuzhanfeng
--                  add subidentifier 2131 to 2141 under ibevtModuleSwitchType by chenke
--                  add subidentifier 2142 to 2146 under ibevtModuleSwitchType by jiangyongjiang
--                  add subidentifier 2147 to 2148 under ibevtModuleSwitchType by maoyun
--                  add subidentifier 1007 to 1009 under ibevtModuleRouterType by zhaomeng
--                  add subidentifier 59 under ibevtPortRouterType  by fujuan
--                  add subidentifier 2149 to 2155 under ibevtModuleSwitchType by chenke
--                  add subidentifier 2156 to 2169 under ibevtModuleSwitchType by lihaijun
--                  add subidentifier 2170 to 2173 under ibevtModuleSwitchType by jiangyongjiang
--                  add subidentifier 2174 to 2175 under ibevtModuleSwitchType by lihaijun
-- V4.71 2019-08-21 add subidentifier 2176 to 2184 under ibevtModuleSwitchType by jiangyongjiang
--                  add subidentifier 1010 under ibevtModuleRouterType by zhaomeng
--                  add subidentifier 1011 to 1012 under ibevtModuleRouterType by fujuan
--                  add subidentifier 2185 to 2188 under ibevtModuleSwitchType by qichenlu
--                  add subidentifier 2189 to 2191 under ibevtModuleSwitchType by jiangyongjiang
--                  add subidentifier 60 to 64 under ibevtPortRouterType by zhaomeng
--                  add subidentifier 2192 to 2208 under ibevtModuleSwitchType by jiangyongjiang
--                  add subidentifier 293 to 294  under ibevtPortSwitchType wangzilong
--                  modify name of 901 under ibevtModuleRouterType by ludezhen 19699
--                  add subidentifier 1013 under ibevtModuleRouterType by zhaomeng
--                  add subidentifier 1014 to 1020 under ibevtModuleRouterType by fuzhanfeng
--                  add subidentifier 1021 to 1023 under ibevtModuleRouterType by zhaomeng
--                  add subidentifier 2209 under ibevtModuleSwitchType by liuhaijun
--                  add subidentifier 295  under ibevtPortSwitchType wangzilong
--                  add subidentifier 1024 under ibevtModuleRouterType by wangxinmeng
--                  add subidentifier 1025 to 1034 under ibevtModuleRouterType by ludezhen
--                  add subidentifier 2210 to 2212 under ibevtModuleSwitchType by jiangyongjiang
-- V4.72 2019-12-02 add subidentifier 2213 to 2217 under ibevtModuleSwitchType by lihaijun
--                  add subidentifier 2218 to 2222 under ibevtModuleSwitchType by jiangyongjiang
--                  modify name of 900 under ibevtModuleRouterType by ludezhen
--                  add subidentifier 2223 to 2224 under ibevtModuleSwitchType by maoyun
--                  add subidentifier 2225 to 2226 under ibevtModuleSwitchType by jiangyongjiang
--                  modify name of 864 to 880，890 to 894，901 to 906，924 to 934，938，940 to 943，945，
--                  954 to 958，961 to 962，969，981 to 984，1011，1025 to 1034 under ibevtModuleRouterType by ludezhen
--                  add subidentifier 1035 under  ibevtModuleRouterType by ludezhen
--                  add subidentifier 1036 under  ibevtModuleRouterType by zhaomeng
--                  add subidentifier 1037 to 1040 under  ibevtModuleRouterType by wangxinmeng
--                  add subidentifier 2227 under  ibevtModuleSwitchType by chenke
-- V4.73 2020-01-07 add subidentifier 2228 to 2229 under ibevtModuleSwitchType by chenke
--                  add subidentifier 531 to 538 under ibevtModuleRouterType by fuzhanfeng
--                  modify name of 943,1012,1035 under ibevtModuleRouterType by ludezhen
--                  add subidentifier 2230 under ibevtModuleSwitchType by jiangyongjiang
--                  add subidentifier 1042 to 1044 under ibevtModuleRouterType by zhaomeng
--                  add subidentifier 817 to 819 under ibevtModuleSwitchType by luoguixing
--                  add subidentifier 1042 to 1044 under ibevtModuleRouterType by ludezhen
-- V4.74 2020-02-11 modify name of 1035 under ibevtModuleRouterType by ludezhen
--                  add subidentifier 296  under ibevtPortSwitchType wangzilong
--                  add subidentifier 2231 to 2232  ibevtModuleSwitchType by chenke
--                  add subidentifier 2233 to 2236  ibevtModuleSwitchType by lihaijun
--                  add subidentifier 7  ibevtOther by ludezhen
--                  add subidentifier 2237 ibevtModuleSwitchType by zhanglili
-- V4.75 2020-03-10 add subidentifier 2238 to 2239 ibevtModuleSwitchType by zhanglili
--                  add subidentifier 539 to 546 under ibevtModuleRouterType by fuzhanfeng
--                  add subidentifier 297 under ibevtPortSwitchType wangzilong
--                  add subidentifier 2240 to 2256 ibevtModuleSwitchType by jiangyongjiang
--                  add subidentifier 2257 ibevtModuleSwitchType by zhanglili
-- V4.76 2020-04-13 add subidentifier 1048 to 1049 ibevtModuleRouterType by wangxinmeng
--                  add subidentifier 2258 ibevtModuleSwitchType by jiangyongjiang
--                  add subidentifier 1050 ibevtModuleRouterType by ludezhen
--                  add subidentifier 547 to 549 under ibevtModuleRouterType by fuzhanfeng
--                  add subidentifier 2259 ibevtModuleSwitchType by zhanglili
--                  add subidentifier 2260 ibevtModuleSwitchType by lihaijun
--                  modify name of 2233 to 2236 ibevtModuleSwitchType by lihaijun
-- V4.77 2020-05-13 add subidentifier 550 to ibevtModuleRouterType by wangxinmeng
--                  add subidentifier 1051 ibevtModuleRouterType by zhaomeng
--                  add subidentifier 1052 ibevtModuleRouterType by wangxinmeng
--                  add subidentifier 1053 to 1054 ibevtModuleRouterType by ludezhen
--                  modify name 2231 ibevtModuleRouterType by zhanglili
--                  add subidentifier 2261 ibevtModuleRouterType by zhanglili
--                  add subidentifier 2262 to 2274 ibevtModuleRouterType by jiangyongjiang
--                  add subidentifier 2275 ibevtModuleRouterType by zhanglili
-- V4.78 2020-06-12 add subidentifier 551 to 555 ibevtModuleRouterType by chenwei
--                  add subidentifier 1055 ibevtModuleRouterType by zhaomeng
--                  add subidentifier 2276 ibevtModuleRouterType by zhanglili
--                  add subidentifier 820 ibLswTypeOfSlot by luoguixing
-- V4.79 2020-07-13 add subidentifier 1056 to 1057 ibevtModuleRouterType by zhaomeng
--                  add subidentifier 65 under ibevtPortRouterType by zhaomeng
--                  add subidentifier 5012 to 5016 ibevtModuleRouterType  by songqinghong
--       2020-07-28 add subidentifier 1058 ibevtModuleRouterType by ludezhen
--                  add subidentifier 2277 to 2291 ibevtModuleRouterType by jiangyongjiang
--                  add subidentifier 66 under ibevtPortRouterType by zhaomeng
--                  add subidentifier 2292 ibevtModuleRouterType by qichenglu
--                  modify name 2186 ibevtModuleRouterType by qichenglu
--                  add subidentifier 2293 to 2295 ibevtModuleRouterType by jiangyongjiang
--                  add subidentifier 556 ibevtModuleRouterType by wangyuqiang
-- V4.80 2020-08-17 add subidentifier 778 to 780 ibevtModuleSwitchType by zhouqin
--                  add subidentifier 1059 to 1061  ibevtModuleRouterType by wangxinmeng
--                  add subidentifier 2296 to 2301 ibevtModuleRouterType by jiangyongjiang
--                  add subidentifier 2302 to 2307 ibevtModuleRouterType by zhanglili
--                  add subidentifier 1062 ibevtModuleRouterType by ludezhen
--                  add subidentifier 1063 to 1064  ibevtModuleRouterType by zhaomeng
-- V4.81 2020-09-10 modify name 2303 ibevtModuleRouterType by zhanglili
--                  add subidentifier 298 to 299 under ibevtPortSwitchType wangzilong
--                  add subidentifier 2308 to 2326 ibevtModuleRouterType by zhanglili
--                  add subidentifier 1065 to 1066 ibevtModuleRouterType by ludezhen
--                  add subidentifier 1067 ibevtModuleRouterType by zhaomeng
-- V4.82 2020-10-20 add subidentifier 2327 to 2355 ibevtModuleRouterType by jiangyongjiang
--                  add subidentifier 1068 ibevtModuleRouterType by zhaomeng
--                  add subidentifier 557 ibevtModuleRouterType by chenwei
--                  add subidentifier 67 ibevtPortRouterType by zhaomeng
-- V4.83 2020-11-12 add subidentifier 2356 to 2359 ibevtModuleRouterType by liuhaijun
--                  add subidentifier 2360 to 2361 ibevtModuleRouterType by jiangyongjiang
--                  add subidentifier 821 ibLswTypeOfSlot by luoguixing
-- V4.84 2020-12-10 add subidentifier 2362 ibevtModuleRouterType by jiangyongjiang
--                  add subidentifier 300 to 304 ibevtPortSwitchType by wangzilong
--                  add subidentifier 2363 ibLswTypeOfSlot by lihaijun
--                  add subidentifier 558 to 565 ibevtModuleRouterType by mazuhan
--                  add subidentifier 781 ibevtModuleSwitchType by zhouqin
-- V4.85 2021-01-12 add subidentifier 68 ibevtPortRouterType by zhaomeng
--                  modify name 65 ibevtPortRouterType by zhaomeng
--                  add subidentifier 566 ibevtModuleRouterType by mazuhan
--                  modify name 565 to 566 ibevtPortRouterType by wuzuhan
--                  modify name 2223 to 2224 ibevtModuleSwitchType by yangzhiyuan
--                  add subidentifier 1069 ibevtModuleRouterType by zhaomeng
--                  add subidentifier 166 to 167 under ibevtModuleRouterType by dengzhiyin
-- V4.86 2021-02-20 del 166 to 167 under ibevtModuleRouterType by dengzhiyin
--                  add subidentifier 1072 to 1073 ibevtModuleRouterType by dengzhiyin
--                  modify name 67 ibevtPortRouterType by zhaomeng
--                  add subidentifier 2364 to 2377  ibevtModuleRouterType by jiangyongjiang
-- V4.87 2021-03-16 modify name 1072 to 1073 ibevtModuleRouterType by dengzhiyin
--                  add subidentifier 305 ibevtPortSwitchType by wangzilong
--                  add subidentifier 2388 to 2390  ibevtModuleRouterType by jiangyongjiang
--                  modify name 1072 to 1073 ibevtModuleRouterType by liuzhongyuan
-- V4.88 2021-04-20 add subidentifier 1074 ibevtModuleRouterType by zhaomeng
--                  add subidentifier 2381 to 2393 ibevtModuleSwitchType by jiangyongjiang
--                  modify name 905 to 906 ibevtModuleRouterType by ludezhen
--                  add subidentifier 2394 to 2397 ibevtModuleSwitchType by zhanglili
-- V4.89 2021-05-15 add subidentifier 306 to 311 ibevtPortSwitchType by wangzilong
--                  add subidentifier 2398 to 2406 ibevtModuleSwitchType by lihaijun
--                  add subidentifier 2407 to 2408 ibevtModuleSwitchType by jiangyongjiang
--                  modify introduction  975,976 and 1057 ibevtModuleRouterType by zhaomeng
--                  modify name 2356 to 2358 subidentifier and del subidentifier 2403 to 2406 ibevtModuleSwitchType by lihaijun
--                  modify name 2213 to 2217 subidentifier ibevtModuleSwitchType by lihaijun
--                  add subidentifier 2409 ibevtModuleSwitchType by qichenglu
--                  add subidentifier 2410 to 2428 ibevtModuleSwitchType by jiangyongjiang
-- V4.90 2021-06-24 add subidentifier 1075 to 1078 ibevtModuleRouterType by zhaomeng
--                  add subidentifier 2429 to 2436 ibevtModuleSwitchType by zhanglili
--                  add subidentifier 1079 to 1080 ibevtModuleRouterType by zhaomeng
--                  add subidentifier 2437 to 2472 ibevtModuleSwitchType by jiangyongjiang
--                  add subidentifier 822 to 823 ibLswTypeOfSlot by luoguixing
-- V4.91 2021-08-03 add subidentifier 312 to 314 ibevtPortSwitchType by wangzilong
-- V4.92 2021-08-12 add subidentifier 1081 to 1083 ibevtModuleRouterType by wangxingmeng
--                  add subidentifier 1084 ibevtModuleRouterType by zhaomeng
--                  add subidentifier 567 to 574 ibevtPortRouterType by wuzuhan
--                  add subidentifier 1085 to 1086 ibevtModuleRouterType by ludezheng
--                  add subidentifier 2473 ibevtModuleSwitchType by zhanglili
--                  add subidentifier 2474 to 2476 ibevtModuleSwitchType by jiangyongjiang
-- V4.93 2021-10-11 add subidentifier 2477 to 2479 ibevtModuleRouterType by zhanglili
-- V4.94 2021-10-19 add subidentifier 2480 ibevtModuleRouterType by sunyuyan
--                  modify name 1057 ibevtModuleRouterType by zhaomeng
--                  add subidentifier 1087 to 1090 ibevtModuleRouterType by wangxinmeng
--                  add subidentifier 575 to 576 ibevtPortRouterType by wuzuhan
--                  add subidentifier 2481 to 2484 ibevtModuleRouterType by liuhaijun
--                  add subidentifier 315 to 317 ibevtPortSwitchType by wangzilong
--                  add subidentifier 2485 to 2490 ibevtModuleRouterType by zhanglili
-- V4.95 2021-11-15 add subidentifier 626 to 632 under ibevtModuleRouterType by wangxinmeng
--                  add subidentifier 2491 to 2496,2500 to 2503 ibevtModuleRouterType by jiangyongjiang
--                  add subidentifier 2504 to 2508 ibevtModuleRouterType by zhuyuchao
--                  add subidentifier 1091 ibevtModuleRouterType by ludezhen
--       2021-12-08 add subidentifier 2509 to 2522 ibevtModuleRouterType by zhanglili
-- V4.96 2021-12-28 add subidentifier 2523 to 2530 ibevtModuleRouterType by jiangyongjiang
--                  modify name 2458 to 2460 ibevtModuleSwitchType by jiangyongjiang
--                  add subidentifier 1092 to 1093 ibevtModuleRouterType by ludezhen
--                  add subidentifier 1094 ibevtModuleRouterType by zhaomeng
--                  add subidentifier 2531 to 2533 ibevtModuleRouterType by zhanglili
--                  add subidentifier 2534 to 2541 ibevtModuleRouterType by jiangyongjiang
--                  add subidentifier 2542 to 2544 ibevtModuleRouterType by licong
-- V4.97 2022-01-21 add subidentifier 2545 ibevtModuleRouterType by jiangyongjiang
--                  add subidentifier 318 to 319 ibevtPortSwitchType by wangzilong
--                  add subidentifier 2546 to 2561 ibevtModuleRouterType by jiangyongjiang
-- V4.98 2022-02-17 add subidentifier 320 to 321 ibevtPortSwitchType by wangzilong
--                  add subidentifier 69 under ibevtPortRouterType  by ludezhen
--                  add subidentifier 1095 to 1096 ibevtModuleRouterType by zhaomeng
--                  add subidentifier 2562 to 2568 ibevtModuleRouterType by niujiahao
--                  add subidentifier 1097 to 1099 ibevtModuleRouterType by wangxinmeng
--                  add subidentifier 577 to 578 ibevtPortRouterType by yanghongbing
-- V4.99 2022-03-17 add subidentifier 9 to 10 ibevtModuleCommonCards by jiangyongjiang
--                  add subidentifier 782 ibevtModuleSwitchType by zhouqin
--                  add subidentifier 2569 ibevtModuleSwitchType by niujiahao
--                  add subidentifier 1100 to 1102 ibevtModuleRouterType by liliming
--                  add subidentifier 2570 to 2576 ibevtModuleSwitchType by jiangyongjiang
--                  modify name 2504 to 2508 ibevtModuleSwitchType by zhuyuchao
--                  add subidentifier 2570 to 2576 ibevtModuleSwitchType by jiangyongjiang
--                  add subidentifier 2577 to 2580 ibevtModuleSwitchType by zhuyuchao
-- V5.00 2022-04-26 add subidentifier 2581 ibevtModuleSwitchType by zhuyuchao
--                  add subidentifier 1103 ibevtModuleRouterType by zhaomeng
--                  add subidentifier 2582 to 2615 ibevtModuleRouterType by jiangyongjiang
--                  add subidentifier 2616 to 2617 ibevtModuleRouterType by niujiahao
--                  add subidentifier 2618 to 2635 ibevtModuleRouterType by jiangyongjiang
--                  add subidentifier 824 ibevtModuleSwitchType by luoguixing
--                  modify name 2616 ibevtModuleSwitchType by niujiahao
-- V5.01 2022-05-28 add subidentifier 1104 to 1106  ibevtModuleRouterType by zhaomeng
--                  add subidentifier 637 to 649 under ibevtModuleRouterType by wangxinmeng
--                  add subidentifier 2641 ibevtModuleRouterType by niujiahao
--                  modify name 2586,2590,2606 ibevtModuleRouterType by jiangyongjiang
--       2022-06-15 add subidentifier 2642 to 2644 ibevtModuleSwitchType by songzhen
--                  add subidentifier 322 ibevtPortSwitchType by wangzilong
-- V5.02 2022-07-03 add subidentifier 2645 ibevtModuleSwitchType by zhuyuchao
--                  add subidentifier 323 ibevtPortSwitchType by wangzilong
--                  add subidentifier 2646 to 2651 ibevtModuleSwitchType by niujiahao
--                  add subidentifier 579 to 593 ibevtModuleRouterType by yangjiarui
--                  add subidentifier 594 to 597 ibevtModuleRouterType by wangyuqiang
-- V5.03 2022-08-09 add subidentifier 598 ibevtModuleRouterType by yangjiarui
--                  add subidentifier 2652 to 2660 ibevtModuleRouterType by jiangyongjiang
-- V5.04 2022-08-23 add subidentifier 2661 to 2663 ibevtModuleRouterType by niujiahao
--                  add subidentifier 2664 to 2683 ibevtModuleRouterType by jiangyongjiang
--                  add subidentifier 1107 to 1113 ibevtModuleRouterType by liliming
--                  add subidentifier 650 to 656 ibevtModuleRouterType by yangjiarui
--                  add subidentifier 1114 to 1115 ibevtModuleRouterType by zhaomeng
--                  add subidentifier 2684 to 2687 ibevtModuleRouterType by niujiahao
--                  modify name 1058 ibevtModuleRouterType by liliming
-- V5.05 2022-09-21 add subidentifier 657 ibevtModuleRouterType by wangxingmeng
--       2022-09-30 add subidentifier 599 ibevtModuleRouterType by yangjiarui
--       2022-09-30 add subidentifier 658 ibevtModuleRouterType by wangyuqiang
--                  add subidentifier 2688 to 2690 ibevtModuleRouterType by niujiahao
--                  add subidentifier 2691 to 2692 ibevtModuleRouterType by jiangyongjiang
--                  add subidentifier 324 to 333 ibevtPortSwitchType by wangzilong
--                  add subidentifier 324 to 333 ibevtPortSwitchType by wangzilong
--       2022-10-21 add subidentifier 659 ibevtModuleRouterType by wangxinmeng
-- V5.06 2022-10-28 add subidentifier 2693 to 2699 ibevtModuleRouterType by jiangyongjiang
--                  add subidentifier 334 ibevtPortSwitchType by wangzilong
--                  add subidentifier 1116 to 1119 ibevtModuleRouterType by liliming
--                  add subidentifier 660 ibevtModuleRouterType by wangxinmeng
--                  add subidentifier 2700 to 2701 ibevtModuleRouterType by niujiahao
--                  add subidentifier 661 to 678 ibevtModuleRouterType by yangjiarui
--                  add subidentifier 2702 to 2711 ibevtModuleRouterType by jiangyongjiang
-- V5.07 2022-12-05 add subidentifier 2712 ibevtModuleRouterType by yangmingjue
--                  add subidentifier 2713 to 2730 ibevtModuleRouterType by jiangyongjiang
--                  add subidentifier 1120 ibevtModuleRouterType by liliming
--                  add subidentifier 679 ibevtModuleRouterType by yangjiarui
-- V5.08 2023-01-06 add subidentifier 1130 ibevtModuleRouterType by zhenghuiling
--                  modify name 567 ibevtModuleRouterType by yangjiarui
--                  modify name 2715,2716,2720 to 2722 ibevtModuleSwitchType by jiangyongjiang
--                  add subidentifier 2732 to 2733 ibevtModuleRouterType by liuhaijun
--                  add subidentifier 2734 to 2735 ibevtModuleRouterType by jiangyongjiang
--                  add subidentifier 2736 ibevtModuleRouterType by niujiahao
--                  add subidentifier 1131 to 1138 ibevtModuleRouterType by zhaomeng
--                  add subidentifier 680 to 683 ibevtModuleRouterType by cuichenchen
--                  add subidentifier 2737 ibevtModuleRouterType by qichenglu
-- V5.09 2023-02-13 add subidentifier 2738 to 2750 ibevtModuleRouterType by niujiahao
--                  add subidentifier 684 ibevtModuleRouterType by zhenghuiling
--                  add subidentifier 1139 to 1140 ibevtModuleRouterType by zhaomeng
--                  add subidentifier 2751 ibevtModuleRouterType by zhaoyunpeng
-- V5.10 2023-03-24 add subidentifier 2752 to 2755 ibevtModuleRouterType by niujiahao
--                  add subidentifier 38 to 40 ibevtPowerSupply by heyujie
--                  add subidentifier 1141 to 1142 ibevtModuleRouterType by zhaomeng
--                  add subidentifier 335 ibevtPortSwitchType by wangzilong
--                  add subidentifier 1143 ibevtModuleRouterType by zhenghuiling
--                  add subidentifier 685 to 688 ibevtModuleRouterType by cuichenchen
--                  modify name 1139  ibevtModuleRouterType by zhaomeng
--                  del subidentifier 682 to 683 ibevtModuleRouterType by cuichenchen
--                  add subidentifier 1144 to 1146 ibevtModuleRouterType by liliming
-- V5.11 2023-05-10 add subidentifier 41 to 47 ibevtPowerSupply by by zhaomeng
--                  add subidentifier 1147 to 1152 ibevtModuleRouterType by zhenghuiling
--                  add subidentifier 2758 to 2771 ibevtModuleRouterType by jiangyongjiang
--                  modify name 464 ibevtModuleRouterType by cuichenchen
--                  add subidentifier 336 to 348 ibevtPortSwitchType by wangzilong
--                  add subidentifier 1153 ibevtModuleRouterType by zhaomeng
--                  add subidentifier 689 ibevtModuleRouterType by cuichenchen
-- V5.12 2023-05-26 add subidentifier 2772 to 2773 ibevtPowerSupply by by jiangyongjiang
--                  add subidentifier 1154 to 1155 ibevtModuleRouterType by zhaomeng
--                  add subidentifier 1156 to 1161 ibevtModuleRouterType by liliming
--                  add subidentifier 690 to 694 ibevtModuleRouterType by cuichenchen
--                  add subidentifier 1165 to 1166 ibevtModuleRouterType by zhaomeng
--                  add subidentifier 1167 to 1171 ibevtModuleRouterType by zhenghuiling
--                  add subidentifier 2774 ibevtPowerSupply by by jiangyongjiang
-- V5.13 2023-07-01 add subidentifier 695 to 721 ibevtPowerSupply by by cuichenchen
--                  add subidentifier 1172 to 1175 ibevtModuleRouterType by zhenghuiling
--                  add subidentifier 2775 to 2779 ibevtPowerSupply by by jiangyongjiang
-- V5.14 2023-07-28 modify name 692 ibevtModuleRouterType by cuichenchen
--                  add subidentifier 722 to 723 ibevtPowerSupply by by cuichenchen
--                  add subidentifier 1176 to 1178 ibevtModuleRouterType by zhenghuiling
--                  add subidentifier 2780 to 2781 ibevtPowerSupply by by jiangyongjiang
--                  add subidentifier 2782 to 2786 ibevtModuleSwitchType by by niujiahao
--                  add subidentifier 352 ibevtPortSwitchType by wangzilong
--                  add subidentifier 825 under ibevtModuleSwitchType by luoguixing
--                  add subidentifier 2787 to 2790 ibevtModuleSwitchType by by zhaoyunpeng
--                  add subidentifier 1179 to 1186 ibevtModuleRouterType by liliming
-- V5.15 2023-08-25 add subidentifier 1187 to 1196 ibevtModuleRouterType by zhenghuiling
--                  add subidentifier 357 to 358 ibevtPortSwitchType by wangzilong
--                  add subidentifier 2791 to 2799 ibevtModuleSwitchType by by jiangyongjiang
-- V5.16 2023-10-11 add subidentifier 2800 to 2812 ibevtModuleSwitchType by niujiahao
--                  add subidentifier 682 ibevtModuleRouterType by wangyuqiang
--                  add subidentifier 70 ibevtPortRouterType by zhaomeng
--                  add subidentifier 1197 ibevtModuleRouterType by zhenghuiling
--                  add subidentifier 2783 ibevtModuleSwitchType by niujiahao

-- =================================================================
IB-ENTITY-VENDORTYPE-OID-MIB DEFINITIONS ::= BEGIN

IMPORTS
    MODULE-IDENTITY
        FROM SNMPv2-SMI
    intelbras
        FROM IB-OID-MIB;


ibEntityVendorTypeOID MODULE-IDENTITY

        LAST-UPDATED "200903310000Z"
        ORGANIZATION
            "Intelbras S.A. Industria de Telecomunicacao Eletronica Brasileria."
        CONTACT-INFO
            ""
        DESCRIPTION
            "The private MIB includes the definition of the object
            identifiers on products, which are used by the
            entPhysicalTable of the ENTITY-MIB to uniquely identify the
            type of each physical entry."
        ::= { intelbras 3 }

ibEntityVendortypeObjects   OBJECT IDENTIFIER ::= { ibEntityVendorTypeOID 1 }

-- This MIB assigns OIDs for use as the values of entPhysicalVendorType.
-- The subtrees in which the OID values are assigned, are structured
-- into a hierarchy based on the values of RFC 2037's PhysicalClass
-- textual convention.  For reference, the definition of PhysicalClass
-- is as follows:
--
--      PhysicalClass ::= TEXTUAL-CONVENTION
--      STATUS          current
--      DESCRIPTION
--             "An enumerated value which provides an indication of the
--              general hardware type of a particular physical entity."
--      SYNTAX      INTEGER  {
--              other(1),
--              unknown(2),
--              chassis(3),
--              backplane(4),
--              container(5),    e.g. slot or daughter-card holder
--              powerSupply(6),
--              fan(7),
--              sensor(8),
--              module(9),       e.g. plug-in card or daughter-card
--              port(10),
--              stack(11)        e.g., stack of multiple chassis entities
--          }
--

ibevtOther     OBJECT IDENTIFIER ::= { ibEntityVendortypeObjects 1 }

-- May be defined detailed in future.

ibevtOtherUnknownCard  OBJECT IDENTIFIER ::= { ibevtOther 1 }
ibevtCPU               OBJECT IDENTIFIER ::= { ibevtOther 2 }
ibevtDOM               OBJECT IDENTIFIER ::= { ibevtOther 3 }  -- Disk on Module
ibevtCFCard            OBJECT IDENTIFIER ::= { ibevtOther 4 }  -- Compact Flash Card
ibevtHardDisk          OBJECT IDENTIFIER ::= { ibevtOther 5 }  -- Hard Disk
ibevtSDCard            OBJECT IDENTIFIER ::= { ibevtOther 6 }  -- Secure Digital Memory Card
ibevtMEM             OBJECT IDENTIFIER ::= { ibevtOther 7 }  -- Internal Memory

-- ibevtGeneralCPU is a general vendor type of CPU.  It is used only for
-- general purpose.  It is strongly recommended that this object should not
-- be used to present the specific CPU vendor type in most cases.  More
-- accurate and clear vendor types should be defined to present specific CPU.
ibevtGeneralCPU        OBJECT IDENTIFIER ::= { ibevtCPU 1 }


ibevtUnknown   OBJECT IDENTIFIER ::= { ibEntityVendortypeObjects 2 }

ibevtChassis   OBJECT IDENTIFIER ::= { ibEntityVendortypeObjects 3 }

-- chassis OID assignments
-- May be substituted by sysObjectID.  So none is assigned at present.

--
-- backplane
--   The enumeration 'backplane' is applicable if the physical
--   entity class is some sort of device for aggregating and
--   forwarding networking traffic, such as a shared backplane in
--   a modular ethernet switch.  Note that an agent may model a
--   backplane as a single physical entity, which is actually
--   implemented as multiple discrete physical components (within
--   a chassis or stack).
--

ibevtBackplane     OBJECT IDENTIFIER ::= { ibEntityVendortypeObjects 4 }

--
-- ibevtContainer section:
--
ibevtContainer     OBJECT IDENTIFIER ::= { ibEntityVendortypeObjects 5 }

--
-- ibevtPowerSupply section:
--
ibevtPowerSupply   OBJECT IDENTIFIER ::= { ibEntityVendortypeObjects 6 }
ibevtPowerSupplyAC            OBJECT IDENTIFIER ::= { ibevtPowerSupply 2 }
ibevtPowerSupplyDC            OBJECT IDENTIFIER ::= { ibevtPowerSupply 3 }
ibevtPowerSupplySTD130W       OBJECT IDENTIFIER ::= { ibevtPowerSupply 4 }     -- Standard 130W PSU
ibevtPowerSupplySTD180W       OBJECT IDENTIFIER ::= { ibevtPowerSupply 5 }     -- Standard 180W PSU
ibevtPowerSupplyPOE24Port     OBJECT IDENTIFIER ::= { ibevtPowerSupply 6 }     -- 24 Port POE PSU 480W
ibevtPowerSupplyPOE48Port     OBJECT IDENTIFIER ::= { ibevtPowerSupply 7 }     -- 48 Port POE PSU 480W
ibevtPowerSupplyLSUM1AC2500   OBJECT IDENTIFIER ::= { ibevtPowerSupply 8 }
ibevtPowerSupplyLSUM2AC2500   OBJECT IDENTIFIER ::= { ibevtPowerSupply 9 }
ibevtPowerSupplyLSUM1DC2400   OBJECT IDENTIFIER ::= { ibevtPowerSupply 10 }
ibevtPowerSupplyLSUM1AC1200   OBJECT IDENTIFIER ::= { ibevtPowerSupply 11 }
ibevtPowerSupplyLSQM1DC2400   OBJECT IDENTIFIER ::= { ibevtPowerSupply 12 }
ibevtPowerSupplyLSUM5AC2500   OBJECT IDENTIFIER ::= { ibevtPowerSupply 13 }
ibevtPowerSupplyLSUM5DC2400   OBJECT IDENTIFIER ::= { ibevtPowerSupply 14 }
ibevtPowerSupplyLSUM6DC2400   OBJECT IDENTIFIER ::= { ibevtPowerSupply 15 }
ibevtPowerSupplyLSUM6AC2500   OBJECT IDENTIFIER ::= { ibevtPowerSupply 16 }
ibevtPowerSupplyLSQM1AC1400   OBJECT IDENTIFIER ::= { ibevtPowerSupply 17 }
ibevtPowerSupplyLSQM1DC1400   OBJECT IDENTIFIER ::= { ibevtPowerSupply 18 }
ibevtPowerSupplyLSQM1AC2800   OBJECT IDENTIFIER ::= { ibevtPowerSupply 19 }
ibevtPowerSupplyLSQM2AC1400   OBJECT IDENTIFIER ::= { ibevtPowerSupply 20 }
ibevtPowerSupplyLSQM1AC6000   OBJECT IDENTIFIER ::= { ibevtPowerSupply 21 }
ibevtPowerSupplyLSQM2AC6000   OBJECT IDENTIFIER ::= { ibevtPowerSupply 22 }
ibevtPowerSupplyLSQM1AC300    OBJECT IDENTIFIER ::= { ibevtPowerSupply 23 }
ibevtPowerSupplyLSQM1AC650    OBJECT IDENTIFIER ::= { ibevtPowerSupply 24 }
ibevtPowerSupplyLSQM1DC650    OBJECT IDENTIFIER ::= { ibevtPowerSupply 25 }
ibevtPowerSupplyLSQM1PWRSPA   OBJECT IDENTIFIER ::= { ibevtPowerSupply 26 }
ibevtPowerSupplyLSWM1RPS800   OBJECT IDENTIFIER ::= { ibevtPowerSupply 27 }
ibevtPowerSupplyLSQM7AC1400   OBJECT IDENTIFIER ::= { ibevtPowerSupply 28 }
ibevtPowerSupplyLSQM7DC1400   OBJECT IDENTIFIER ::= { ibevtPowerSupply 29 }
ibevtPowerSupplyLSQM7AC2800   OBJECT IDENTIFIER ::= { ibevtPowerSupply 30 }
ibevtPowerSupplyLSQM7AC6000   OBJECT IDENTIFIER ::= { ibevtPowerSupply 31 }
ibevtPowerSupplyLSQM7AC300    OBJECT IDENTIFIER ::= { ibevtPowerSupply 32 }
ibevtPowerSupplyLSQM7AC650    OBJECT IDENTIFIER ::= { ibevtPowerSupply 33 }
ibevtPowerSupplyLSQM7DC650    OBJECT IDENTIFIER ::= { ibevtPowerSupply 34 }
ibevtPowerSupplyLSWM2RPS800   OBJECT IDENTIFIER ::= { ibevtPowerSupply 35 }
ibevtPowerSupplySecPathAC     OBJECT IDENTIFIER ::= { ibevtPowerSupply 36 }    -- F5000-NSUM1AC650-650W
ibevtPowerSupplySecPathDC     OBJECT IDENTIFIER ::= { ibevtPowerSupply 37}     -- F5000-NSUM1DC650-650W
ibevtPowerSupplyPSR240012AHAHB     OBJECT IDENTIFIER ::= { ibevtPowerSupply 38}
ibevtPowerSupplyPSR2400-54AA-B     OBJECT IDENTIFIER ::= { ibevtPowerSupply 39}
ibevtPowerSupplyPSRADC             OBJECT IDENTIFIER ::= { ibevtPowerSupply 40}
ibevtPowerSupplyPSR450-12A1   OBJECT IDENTIFIER ::= { ibevtPowerSupply 41 }    -- 450W AC Power Supply Module
ibevtPowerSupplyPSR250-12A1   OBJECT IDENTIFIER ::= { ibevtPowerSupply 42 }    -- 250W AC Power Supply Module
ibevtPowerSupplyPSR450-12AHD  OBJECT IDENTIFIER ::= { ibevtPowerSupply 43 }    -- 450W HVDC Power Supply Module
ibevtPowerSupplyPSR450-12D-F  OBJECT IDENTIFIER ::= { ibevtPowerSupply 44 }    -- 450W DC Power Supply Module
ibevtPowerSupplyPSR450-12A    OBJECT IDENTIFIER ::= { ibevtPowerSupply 45 }    -- 450W AC Power Supply Module
ibevtPowerSupplyPSR250-12A    OBJECT IDENTIFIER ::= { ibevtPowerSupply 46 }    -- 250W AC Power Supply Module
ibevtPowerSupplyPSR450-12D    OBJECT IDENTIFIER ::= { ibevtPowerSupply 47 }    -- 450W DC Power Supply Module
-- ibevtFan section:
--
ibevtFan       OBJECT IDENTIFIER ::= { ibEntityVendortypeObjects 7 }
ibevtHotSwapFan       OBJECT IDENTIFIER ::=  { ibevtFan 1 }
ibevtNonHotSwapFan    OBJECT IDENTIFIER ::=  { ibevtFan 2 }
ibevtFanLSUM110504    OBJECT IDENTIFIER ::=  { ibevtFan 3 }
ibevtFanLSUM110508    OBJECT IDENTIFIER ::=  { ibevtFan 4 }
ibevtFanLSUM110508V   OBJECT IDENTIFIER ::=  { ibevtFan 5 }
ibevtFanLSUM110512    OBJECT IDENTIFIER ::=  { ibevtFan 6 }
ibevtFanLSUM210512    OBJECT IDENTIFIER ::=  { ibevtFan 7 }
ibevtFanLSUM510504    OBJECT IDENTIFIER ::=  { ibevtFan 8 }
ibevtFanLSUM510508    OBJECT IDENTIFIER ::=  { ibevtFan 9 }
ibevtFanLSUM510508V   OBJECT IDENTIFIER ::=  { ibevtFan 10 }
ibevtFanLSUM510512U   OBJECT IDENTIFIER ::=  { ibevtFan 11 }
ibevtFanLSUM510512D   OBJECT IDENTIFIER ::=  { ibevtFan 12 }
ibevtFanLSUM511908V   OBJECT IDENTIFIER ::=  { ibevtFan 13 }
ibevtFanLSQM17502E    OBJECT IDENTIFIER ::=  { ibevtFan 14 }
ibevtFanLSQM17503E    OBJECT IDENTIFIER ::=  { ibevtFan 15 }
ibevtFanLSQM17503ES   OBJECT IDENTIFIER ::=  { ibevtFan 16 }
ibevtFanLSQM17506E    OBJECT IDENTIFIER ::=  { ibevtFan 17 }
ibevtFanLSQM17506EV   OBJECT IDENTIFIER ::=  { ibevtFan 18 }
ibevtFanLSQM17510E    OBJECT IDENTIFIER ::=  { ibevtFan 19 }
ibevtFanLSQM57503     OBJECT IDENTIFIER ::=  { ibevtFan 20 }
ibevtFanLSQM57502     OBJECT IDENTIFIER ::=  { ibevtFan 21 }
ibevtFanLSQM57506     OBJECT IDENTIFIER ::=  { ibevtFan 22 }
ibevtFanLSQM57510     OBJECT IDENTIFIER ::=  { ibevtFan 23 }
ibevtHotSwapFan-NSUM1BFANSC         OBJECT IDENTIFIER ::=  { ibevtFan 24 }   -- F5000-NSUM1BFANSC
ibevtHotSwapFan-NSUM1BFANSCB        OBJECT IDENTIFIER ::=  { ibevtFan 25 }   -- F5000-NSUM1BFANSCB
--
-- ibevtSensor section:
--
ibevtSensor        OBJECT IDENTIFIER ::= { ibEntityVendortypeObjects 8 }
ibevtSensorTemperature     OBJECT IDENTIFIER ::= { ibevtSensor 1 }
ibevtSensorVoltage         OBJECT IDENTIFIER ::= { ibevtSensor 2 }
ibevtSensorFanSpeed        OBJECT IDENTIFIER ::= { ibevtSensor 3 }


--
-- ibevtModule section:
--
ibevtModule        OBJECT IDENTIFIER ::= { ibEntityVendortypeObjects 9 }

-- ibevtModule is subdivided into sections like Router and Switch. These represent
-- cards used only on the router and switch.
-- ibevtModuleCommonCards contains cards that can be used interchangeably
-- across more than one platform


-- Acronyms used in the ibevtModule section:
--

ibevtModuleUnknownCard     OBJECT IDENTIFIER ::= { ibevtModule 1 }

-- ibevtModuleCommonCards - cards and subcards common to more
-- than one platform
ibevtModuleCommonCards     OBJECT IDENTIFIER ::= { ibevtModule 2 }

ibevtModuleBoxCEN                         OBJECT IDENTIFIER ::= { ibevtModuleCommonCards 1 }
ibevtModuleBoxIRF48GE                     OBJECT IDENTIFIER ::= { ibevtModuleCommonCards 2 }
ibevtModuleBoxIRF24GE24TGE                OBJECT IDENTIFIER ::= { ibevtModuleCommonCards 3 }
ibevtModuleChassisMpu                     OBJECT IDENTIFIER ::= { ibevtModuleCommonCards 4 }
ibevtModuleLPU48GE                        OBJECT IDENTIFIER ::= { ibevtModuleCommonCards 5 }
ibevtModuleLPU4GE4Serial                  OBJECT IDENTIFIER ::= { ibevtModuleCommonCards 6 }
ibevtModuleLPU4GE4Pos                     OBJECT IDENTIFIER ::= { ibevtModuleCommonCards 7 }
ibevtModuleLPU4GE4E1                      OBJECT IDENTIFIER ::= { ibevtModuleCommonCards 8 }
ibevtModuleBox-MXCA                       OBJECT IDENTIFIER ::= { ibevtModuleCommonCards 9 }
ibevtModuleBox-GPFA                       OBJECT IDENTIFIER ::= { ibevtModuleCommonCards 10 }


-- ibevtModuleRouterType cards are slot-cards specific to the Router.
ibevtModuleRouterType      OBJECT IDENTIFIER ::= { ibevtModule 3 }

--ibevtModuleRt-Unavailable               OBJECT IDENTIFIER ::= { ibevtModuleRouterType 1 }
ibevtModuleRt-As                          OBJECT IDENTIFIER ::= { ibevtModuleRouterType 2 }
ibevtModuleRt-Sa                          OBJECT IDENTIFIER ::= { ibevtModuleRouterType 3 }
ibevtModuleRt-Bi                          OBJECT IDENTIFIER ::= { ibevtModuleRouterType 4 }
ibevtModuleRt-E12                         OBJECT IDENTIFIER ::= { ibevtModuleRouterType 5 }
ibevtModuleRt-E14                         OBJECT IDENTIFIER ::= { ibevtModuleRouterType 6 }
ibevtModuleRt-Fe1                         OBJECT IDENTIFIER ::= { ibevtModuleRouterType 7 }
ibevtModuleRt-E1                          OBJECT IDENTIFIER ::= { ibevtModuleRouterType 8 }
ibevtModuleRt-Fe2                         OBJECT IDENTIFIER ::= { ibevtModuleRouterType 9 }
ibevtModuleRt-Vi2                         OBJECT IDENTIFIER ::= { ibevtModuleRouterType 11 }
ibevtModuleRt-Vi4                         OBJECT IDENTIFIER ::= { ibevtModuleRouterType 12 }
ibevtModuleRt-Vi30                        OBJECT IDENTIFIER ::= { ibevtModuleRouterType 13 }
ibevtModuleRt-S1b                         OBJECT IDENTIFIER ::= { ibevtModuleRouterType 14 }
ibevtModuleRt-Sa2                         OBJECT IDENTIFIER ::= { ibevtModuleRouterType 15 }
ibevtModuleRt-As16                        OBJECT IDENTIFIER ::= { ibevtModuleRouterType 16 }
ibevtModuleRt-New8as                      OBJECT IDENTIFIER ::= { ibevtModuleRouterType 17 }
ibevtModuleRt-Sa1                         OBJECT IDENTIFIER ::= { ibevtModuleRouterType 18 }
ibevtModuleRt-Fxs2                        OBJECT IDENTIFIER ::= { ibevtModuleRouterType 19 }
ibevtModuleRt-Fxo2                        OBJECT IDENTIFIER ::= { ibevtModuleRouterType 20 }
ibevtModuleRt-Em2                         OBJECT IDENTIFIER ::= { ibevtModuleRouterType 21 }
ibevtModuleRt-Fxs4                        OBJECT IDENTIFIER ::= { ibevtModuleRouterType 22 }
ibevtModuleRt-Fxo4                        OBJECT IDENTIFIER ::= { ibevtModuleRouterType 23 }
ibevtModuleRt-Em4                         OBJECT IDENTIFIER ::= { ibevtModuleRouterType 24 }
ibevtModuleRt-Sab                         OBJECT IDENTIFIER ::= { ibevtModuleRouterType 25 }
ibevtModuleRt-E1vi                        OBJECT IDENTIFIER ::= { ibevtModuleRouterType 26 }
ibevtModuleRt-Am12                        OBJECT IDENTIFIER ::= { ibevtModuleRouterType 27 }
ibevtModuleRt-Am6                         OBJECT IDENTIFIER ::= { ibevtModuleRouterType 28 }
ibevtModuleRt-Ndec                        OBJECT IDENTIFIER ::= { ibevtModuleRouterType 29 }
ibevtModuleRt-Newsa2                      OBJECT IDENTIFIER ::= { ibevtModuleRouterType 30 }
ibevtModuleRt-Aux                         OBJECT IDENTIFIER ::= { ibevtModuleRouterType 31 }
ibevtModuleRt-Console                     OBJECT IDENTIFIER ::= { ibevtModuleRouterType 32 }
ibevtModuleRt-Sic-wan                     OBJECT IDENTIFIER ::= { ibevtModuleRouterType 33 }
ibevtModuleRt-Sic-1fe                     OBJECT IDENTIFIER ::= { ibevtModuleRouterType 34 }
ibevtModuleRt-Sic-1sa                     OBJECT IDENTIFIER ::= { ibevtModuleRouterType 35 }
ibevtModuleRt-Sic-3as                     OBJECT IDENTIFIER ::= { ibevtModuleRouterType 36 }
ibevtModuleRt-Sic-1e1                     OBJECT IDENTIFIER ::= { ibevtModuleRouterType 37 }
ibevtModuleRt-Sic-1t1                     OBJECT IDENTIFIER ::= { ibevtModuleRouterType 38 }
ibevtModuleRt-Sic-1bu                     OBJECT IDENTIFIER ::= { ibevtModuleRouterType 39 }
ibevtModuleRt-Sic-2bu                     OBJECT IDENTIFIER ::= { ibevtModuleRouterType 40 }
ibevtModuleRt-Sic-1bs                     OBJECT IDENTIFIER ::= { ibevtModuleRouterType 41 }
ibevtModuleRt-Sic-2bs                     OBJECT IDENTIFIER ::= { ibevtModuleRouterType 42 }
ibevtModuleRt-Sic-1am                     OBJECT IDENTIFIER ::= { ibevtModuleRouterType 43 }
ibevtModuleRt-Sic-2am                     OBJECT IDENTIFIER ::= { ibevtModuleRouterType 44 }
ibevtModuleRt-Sic-1em                     OBJECT IDENTIFIER ::= { ibevtModuleRouterType 45 }
ibevtModuleRt-Sic-2em                     OBJECT IDENTIFIER ::= { ibevtModuleRouterType 46 }
ibevtModuleRt-Sic-1fxs                    OBJECT IDENTIFIER ::= { ibevtModuleRouterType 47 }
ibevtModuleRt-Sic-2fxs                    OBJECT IDENTIFIER ::= { ibevtModuleRouterType 48 }
ibevtModuleRt-Sic-1fxo                    OBJECT IDENTIFIER ::= { ibevtModuleRouterType 49 }
ibevtModuleRt-Sic-2fxo                    OBJECT IDENTIFIER ::= { ibevtModuleRouterType 50 }
ibevtModuleRt-Fcm6                        OBJECT IDENTIFIER ::= { ibevtModuleRouterType 51 }
ibevtModuleRt-Sa8                         OBJECT IDENTIFIER ::= { ibevtModuleRouterType 52 }
ibevtModuleRt-T11                         OBJECT IDENTIFIER ::= { ibevtModuleRouterType 53 }
ibevtModuleRt-T12                         OBJECT IDENTIFIER ::= { ibevtModuleRouterType 54 }
ibevtModuleRt-T14                         OBJECT IDENTIFIER ::= { ibevtModuleRouterType 55 }
ibevtModuleRt-T1vi                        OBJECT IDENTIFIER ::= { ibevtModuleRouterType 56 }
ibevtModuleRt-Fcm4                        OBJECT IDENTIFIER ::= { ibevtModuleRouterType 57 }
ibevtModuleRt-Fcm2                        OBJECT IDENTIFIER ::= { ibevtModuleRouterType 58 }
ibevtModuleRt-Rtb21ce3                    OBJECT IDENTIFIER ::= { ibevtModuleRouterType 59 }
ibevtModuleRt-Ame6                        OBJECT IDENTIFIER ::= { ibevtModuleRouterType 60 }
ibevtModuleRt-Ame12                       OBJECT IDENTIFIER ::= { ibevtModuleRouterType 61 }
ibevtModuleRt-E11-f                       OBJECT IDENTIFIER ::= { ibevtModuleRouterType 65 }
ibevtModuleRt-E12-f                       OBJECT IDENTIFIER ::= { ibevtModuleRouterType 66 }
ibevtModuleRt-E14-f                       OBJECT IDENTIFIER ::= { ibevtModuleRouterType 67 }
ibevtModuleRt-T11-f                       OBJECT IDENTIFIER ::= { ibevtModuleRouterType 68 }
ibevtModuleRt-T12-f                       OBJECT IDENTIFIER ::= { ibevtModuleRouterType 69 }
ibevtModuleRt-T14-f                       OBJECT IDENTIFIER ::= { ibevtModuleRouterType 70 }
ibevtModuleRt-E11-f-17                    OBJECT IDENTIFIER ::= { ibevtModuleRouterType 71 }
ibevtModuleRt-T11-f-17                    OBJECT IDENTIFIER ::= { ibevtModuleRouterType 72 }
ibevtModuleRt-Rtb21ct3                    OBJECT IDENTIFIER ::= { ibevtModuleRouterType 73 }
ibevtModuleRt-Atmadsl1                    OBJECT IDENTIFIER ::= { ibevtModuleRouterType 74 }
ibevtModuleRt-Atmadsl2                    OBJECT IDENTIFIER ::= { ibevtModuleRouterType 75 }
ibevtModuleRt-Atm155m                     OBJECT IDENTIFIER ::= { ibevtModuleRouterType 76 }
ibevtModuleRt-Ase8                        OBJECT IDENTIFIER ::= { ibevtModuleRouterType 77 }
ibevtModuleRt-Ase16                       OBJECT IDENTIFIER ::= { ibevtModuleRouterType 78 }
ibevtModuleRt-Sae4                        OBJECT IDENTIFIER ::= { ibevtModuleRouterType 79 }
ibevtModuleRt-Sae2                        OBJECT IDENTIFIER ::= { ibevtModuleRouterType 80 }
ibevtModuleRt-Atmshdsl1                   OBJECT IDENTIFIER ::= { ibevtModuleRouterType 90 }
ibevtModuleRt-Atmshdsl2                   OBJECT IDENTIFIER ::= { ibevtModuleRouterType 91 }
ibevtModuleRt-Atmshdsl4                   OBJECT IDENTIFIER ::= { ibevtModuleRouterType 92 }
ibevtModuleRt-Atm25m                      OBJECT IDENTIFIER ::= { ibevtModuleRouterType 93 }
ibevtModuleRt-Atme3                       OBJECT IDENTIFIER ::= { ibevtModuleRouterType 94 }
ibevtModuleRt-Atmt3                       OBJECT IDENTIFIER ::= { ibevtModuleRouterType 95 }
ibevtModuleRt-Xdsl-fec                    OBJECT IDENTIFIER ::= { ibevtModuleRouterType 96 }
ibevtModuleRt-Xdsl-adsl                   OBJECT IDENTIFIER ::= { ibevtModuleRouterType 97 }
ibevtModuleRt-Xdsl-gshdsl                 OBJECT IDENTIFIER ::= { ibevtModuleRouterType 98 }
ibevtModuleRt-Xdsl-bri                    OBJECT IDENTIFIER ::= { ibevtModuleRouterType 99 }
ibevtModuleRt-Xdsl-scc                    OBJECT IDENTIFIER ::= { ibevtModuleRouterType 100 }
ibevtModuleRt-Ge1                         OBJECT IDENTIFIER ::= { ibevtModuleRouterType 101 }
ibevtModuleRt-Pos155m                     OBJECT IDENTIFIER ::= { ibevtModuleRouterType 102 }
ibevtModuleRt-Cpos                        OBJECT IDENTIFIER ::= { ibevtModuleRouterType 103 }
ibevtModuleRt-Fe1op                       OBJECT IDENTIFIER ::= { ibevtModuleRouterType 104 }
ibevtModuleRt-Sae8                        OBJECT IDENTIFIER ::= { ibevtModuleRouterType 105 }
ibevtModuleRt-Atm155m-mm                  OBJECT IDENTIFIER ::= { ibevtModuleRouterType 106 }
ibevtModuleRt-Atm155m-sm                  OBJECT IDENTIFIER ::= { ibevtModuleRouterType 107 }
ibevtModuleRt-Atm155m-sml                 OBJECT IDENTIFIER ::= { ibevtModuleRouterType 108 }
ibevtModuleRt-Fe1op-sfx                   OBJECT IDENTIFIER ::= { ibevtModuleRouterType 109 }
ibevtModuleRt-Fe1op-mfx                   OBJECT IDENTIFIER ::= { ibevtModuleRouterType 110 }
ibevtModuleRt-Cpos-t1                     OBJECT IDENTIFIER ::= { ibevtModuleRouterType 111 }
ibevtModuleRt-Ge1op                       OBJECT IDENTIFIER ::= { ibevtModuleRouterType 112 }
ibevtModuleRt-Ge2op                       OBJECT IDENTIFIER ::= { ibevtModuleRouterType 113 }
ibevtModuleRt-Ge2                         OBJECT IDENTIFIER ::= { ibevtModuleRouterType 114 }
ibevtModuleRt-Fix-1wan                    OBJECT IDENTIFIER ::= { ibevtModuleRouterType 115 }
ibevtModuleRt-Fix-1sae                    OBJECT IDENTIFIER ::= { ibevtModuleRouterType 116 }
ibevtModuleRt-Cavium                      OBJECT IDENTIFIER ::= { ibevtModuleRouterType 117 }
ibevtModuleRt-Sic1Eth                     OBJECT IDENTIFIER ::= { ibevtModuleRouterType 118 }
ibevtModuleRt-atm1ADSLI                   OBJECT IDENTIFIER ::= { ibevtModuleRouterType 119 }
ibevtModuleRt-atm2ADSLI                   OBJECT IDENTIFIER ::= { ibevtModuleRouterType 120 }
ibevtModuleRt-fix-e11                     OBJECT IDENTIFIER ::= { ibevtModuleRouterType 121 }
ibevtModuleRt-fix-t11                     OBJECT IDENTIFIER ::= { ibevtModuleRouterType 122 }
ibevtModuleRt-e18-75                      OBJECT IDENTIFIER ::= { ibevtModuleRouterType 123 }
ibevtModuleRt-e18-120                     OBJECT IDENTIFIER ::= { ibevtModuleRouterType 124 }
ibevtModuleRt-t18                         OBJECT IDENTIFIER ::= { ibevtModuleRouterType 125 }
ibevtModuleRt-sic-1vifxs                  OBJECT IDENTIFIER ::= { ibevtModuleRouterType 126 }
ibevtModuleRt-sic-1vifxo                  OBJECT IDENTIFIER ::= { ibevtModuleRouterType 127 }
ibevtModuleRt-sic-2vifxs                  OBJECT IDENTIFIER ::= { ibevtModuleRouterType 128 }
ibevtModuleRt-sic-2vifxo                  OBJECT IDENTIFIER ::= { ibevtModuleRouterType 129 }
ibevtModuleRt-xdsl-fec-new                OBJECT IDENTIFIER ::= { ibevtModuleRouterType 130 }
ibevtModuleRt-xdsl-sa                     OBJECT IDENTIFIER ::= { ibevtModuleRouterType 131 }
ibevtModuleRt-bs4                         OBJECT IDENTIFIER ::= { ibevtModuleRouterType 132 }
ibevtModuleRt-ima-8e175                   OBJECT IDENTIFIER ::= { ibevtModuleRouterType 133 }
ibevtModuleRt-ima-8e1120                  OBJECT IDENTIFIER ::= { ibevtModuleRouterType 134 }
ibevtModuleRt-ima-4e175                   OBJECT IDENTIFIER ::= { ibevtModuleRouterType 135 }
ibevtModuleRt-ima-4e1120                  OBJECT IDENTIFIER ::= { ibevtModuleRouterType 136 }
ibevtModuleRt-ima-8t1                     OBJECT IDENTIFIER ::= { ibevtModuleRouterType 137 }
ibevtModuleRt-ima-4t1                     OBJECT IDENTIFIER ::= { ibevtModuleRouterType 138 }
ibevtModuleRt-sic-1t1f                    OBJECT IDENTIFIER ::= { ibevtModuleRouterType 139 }
ibevtModuleRT-SIC-1E1F                    OBJECT IDENTIFIER ::= { ibevtModuleRouterType 140 }
ibevtModuleRt-VG-16fxs                    OBJECT IDENTIFIER ::= { ibevtModuleRouterType 141 }
ibevtModuleRt-VG-32fxs                    OBJECT IDENTIFIER ::= { ibevtModuleRouterType 142 }
ibevtModuleRt-VG-8fxo                     OBJECT IDENTIFIER ::= { ibevtModuleRouterType 143 }
ibevtModuleRt-VG-2fe                      OBJECT IDENTIFIER ::= { ibevtModuleRouterType 144 }
ibevtModuleRt-sib                         OBJECT IDENTIFIER ::= { ibevtModuleRouterType 145 } -- SIB card
ibevtModuleRt-cie32                       OBJECT IDENTIFIER ::= { ibevtModuleRouterType 146 } -- 32M SSRAM CIE card
ibevtModuleRt-cie64                       OBJECT IDENTIFIER ::= { ibevtModuleRouterType 147 } -- 64M SSRAM CIE card
ibevtModuleRt-cie96                       OBJECT IDENTIFIER ::= { ibevtModuleRouterType 148 } -- 96M SSRAM CIE card
ibevtModuleRt-Fe4                         OBJECT IDENTIFIER ::= { ibevtModuleRouterType 149 } -- 4FE card
ibevtModuleRt-fxs4fxo1                    OBJECT IDENTIFIER ::= { ibevtModuleRouterType 150 } -- 4 Port Foreign Exchange Station and 1 Port Foreign Exchange Office Interface
ibevtModuleRt-atm1shdsl4wire              OBJECT IDENTIFIER ::= { ibevtModuleRouterType 151 } -- G.SHDSL 4 wire MIM card, 1 port
ibevtModuleRt-atmIma4shdsl                OBJECT IDENTIFIER ::= { ibevtModuleRouterType 152 } -- G.SHDSL 8 wire MIM card, 4 ports
ibevtModuleRt-ls4                         OBJECT IDENTIFIER ::= { ibevtModuleRouterType 153 } -- 4 Ports Layer 2 Lanswitch Module
ibevtModuleRt-ls8                         OBJECT IDENTIFIER ::= { ibevtModuleRouterType 154 } -- 8 Ports Layer 2 Lanswitch Module
ibevtModuleRt-ls16                        OBJECT IDENTIFIER ::= { ibevtModuleRouterType 155 } -- 16 Ports Layer 2 Lanswitch Module
ibevtModuleRt-sic-adls2plus-isdn          OBJECT IDENTIFIER ::= { ibevtModuleRouterType 156 } -- ADLS2Plus SIC card, ISDN port
ibevtModuleRt-sic-adls2plus-pots          OBJECT IDENTIFIER ::= { ibevtModuleRouterType 157 } -- ADLS2Plus SIC card, POTS port
ibevtModuleRt-ft3                         OBJECT IDENTIFIER ::= { ibevtModuleRouterType 158 } -- 1 Port Fractional T3 module
ibevtModuleRt-ce32                        OBJECT IDENTIFIER ::= { ibevtModuleRouterType 159 } -- 2 Port Channelized E3 module
ibevtModuleRt-bsv2                        OBJECT IDENTIFIER ::= { ibevtModuleRouterType 160 } -- 2 Port BSV module
ibevtModuleRt-bsv4                        OBJECT IDENTIFIER ::= { ibevtModuleRouterType 161 } -- 4 Port BSV module
ibevtModuleRt-RPU                         OBJECT IDENTIFIER ::= { ibevtModuleRouterType 162 } -- Route processing unit
ibevtModuleRt-ERPU                        OBJECT IDENTIFIER ::= { ibevtModuleRouterType 163 } -- Enhanced route processing unit
ibevtModuleRt-SSL                         OBJECT IDENTIFIER ::= { ibevtModuleRouterType 164 } -- SSL Encrypt Card
ibevtModuleRt-NSA                         OBJECT IDENTIFIER ::= { ibevtModuleRouterType 165 } -- NSA Encrypt Card

--
-- 166 to 199 reserved for other devices
--


--
-- 200 to 399 reserved for normal routers part I
--
ibevtModuleRT-SIC-1GEC                    OBJECT IDENTIFIER ::= { ibevtModuleRouterType 200 } -- 1-Port 10M/100M/1000M COMBO Ethernet Interface SIC Module
ibevtModuleRT-24FSW                       OBJECT IDENTIFIER ::= { ibevtModuleRouterType 201 } -- 24-Port 10M/100M and 2-Port 1000BASE-T/1000BASE-X(COMBO) Ethernet L2 Switch Module
ibevtModuleRT-24FSWP                      OBJECT IDENTIFIER ::= { ibevtModuleRouterType 202 } -- 24-Port 10M/100M(WITH POE) and 2-Port 1000BASE-T/1000BASE-X(COMBO) Ethernet L2 Switch Module
ibevtModuleRT-16FSW                       OBJECT IDENTIFIER ::= { ibevtModuleRouterType 203 } -- 16-Port 10M/100M Ethernet L2 Switch Module
ibevtModuleRT-16FSWP                      OBJECT IDENTIFIER ::= { ibevtModuleRouterType 204 } -- 16-Port 10M/100M(WITH POE) Ethernet L2 Switch Module
ibevtModuleRT-1VE1                        OBJECT IDENTIFIER ::= { ibevtModuleRouterType 205 } -- 1-Port Voice E1 Module
ibevtModuleRT-1VT1                        OBJECT IDENTIFIER ::= { ibevtModuleRouterType 206 } -- 1-Port Voice T1 Module
ibevtModuleRT-2VE1                        OBJECT IDENTIFIER ::= { ibevtModuleRouterType 207 } -- 2-Port Voice E1 Module
ibevtModuleRT-2VT1                        OBJECT IDENTIFIER ::= { ibevtModuleRouterType 208 } -- 2-Port Voice T1 Module
ibevtModuleRT-SIC-4FSW                    OBJECT IDENTIFIER ::= { ibevtModuleRouterType 209 } -- 4-Port 10M/100M Ethernet L2 Switch Module (RJ45)
ibevtModuleRT-SIC-4FSWP                   OBJECT IDENTIFIER ::= { ibevtModuleRouterType 210 } -- 4-Port 10M/100M Ethernet L2 Switch Module(RJ45,WITH POE)
ibevtModuleRT-DSIC-9FSW                   OBJECT IDENTIFIER ::= { ibevtModuleRouterType 211 } -- 9-Port 10M/100M Ethernet L2 Switch Module(RJ45)
ibevtModuleRT-DSIC-9FSWP                  OBJECT IDENTIFIER ::= { ibevtModuleRouterType 212 } -- 9-Port 10M/100M Ethernet L2 Switch Module(RJ45,WITH POE)
ibevtModuleRT-SIC-1VE1                    OBJECT IDENTIFIER ::= { ibevtModuleRouterType 213 } -- 1-Port Voice E1 SIC Interface Module
ibevtModuleRT-SIC-1VT1                    OBJECT IDENTIFIER ::= { ibevtModuleRouterType 214 } -- 1-Port Voice T1 SIC Interface Module
ibevtModuleRT-VCPM                        OBJECT IDENTIFIER ::= { ibevtModuleRouterType 215 } -- Voice Co-Processing Module
ibevtModuleRT-VPM                         OBJECT IDENTIFIER ::= { ibevtModuleRouterType 216 } -- 32-Channels Voice Processing Module
ibevtModuleRT-VPMA                        OBJECT IDENTIFIER ::= { ibevtModuleRouterType 217 } -- 16-Channels Voice Processing Module
ibevtModuleRT-VPMB                        OBJECT IDENTIFIER ::= { ibevtModuleRouterType 218 } -- 8-Channels Voice Processing Module
ibevtModuleRT-VPMC                        OBJECT IDENTIFIER ::= { ibevtModuleRouterType 219 } -- 24-Channels Voice Processing Module
ibevtModuleRt-fe18-75                     OBJECT IDENTIFIER ::= { ibevtModuleRouterType 220 } -- 8 Port FE1(75 O) module
ibevtModuleRt-fe18-120                    OBJECT IDENTIFIER ::= { ibevtModuleRouterType 221 } -- 8 Port FE1(120 O) module
ibevtModuleRt-ft18                        OBJECT IDENTIFIER ::= { ibevtModuleRouterType 222 } -- 8 Port FT1 module
ibevtModuleRt-CF                          OBJECT IDENTIFIER ::= { ibevtModuleRouterType 223 } -- Compact Flash Card
ibevtModuleRt-bsv2-v2                     OBJECT IDENTIFIER ::= { ibevtModuleRouterType 224 } -- 2 Port BSV Version 2
ibevtModuleRt-e1vi1-v2                    OBJECT IDENTIFIER ::= { ibevtModuleRouterType 225 } -- E1VI Version 2
ibevtModuleRt-e1vi2                       OBJECT IDENTIFIER ::= { ibevtModuleRouterType 226 } -- 2 Port E1VI
ibevtModuleRt-t1vi1-v2                    OBJECT IDENTIFIER ::= { ibevtModuleRouterType 227 } -- T1VI Version 2
ibevtModuleRt-t1vi2                       OBJECT IDENTIFIER ::= { ibevtModuleRouterType 228 } -- 2 Port T1VI
ibevtModuleRt-osm                         OBJECT IDENTIFIER ::= { ibevtModuleRouterType 229 } -- Open Service Module
ibevtModuleRt-sd707                       OBJECT IDENTIFIER ::= { ibevtModuleRouterType 230 } -- Encryption Accelerator
ibevtModuleRt-dm-epri                     OBJECT IDENTIFIER ::= { ibevtModuleRouterType 231 } -- E1 Pri Digital Modem
ibevtModuleRt-dm-tpri                     OBJECT IDENTIFIER ::= { ibevtModuleRouterType 232 } -- T1 Pri Digital Modem
ibevtModuleRt-ERPU-H                      OBJECT IDENTIFIER ::= { ibevtModuleRouterType 233 } -- Enhanced route processing unit with only one optic GE interface
ibevtModuleRT-SIC-1BSV                    OBJECT IDENTIFIER ::= { ibevtModuleRouterType 234 } -- 1-Port Bri S/T VoiceInterface SIC Module
ibevtModuleRT-SIC-2BSV                    OBJECT IDENTIFIER ::= { ibevtModuleRouterType 235 } -- 2-Port Bri S/T VoiceInterface SIC Module
ibevtModuleRt-gbe8                        OBJECT IDENTIFIER ::= { ibevtModuleRouterType 236 } -- 8-Port Gigabit Ethernet interface card
ibevtModuleRt-gbe4                        OBJECT IDENTIFIER ::= { ibevtModuleRouterType 237 } -- 4-Port Gigabit Ethernet interface card
ibevtModuleRt-cpos2-v2                    OBJECT IDENTIFIER ::= { ibevtModuleRouterType 238 } -- 2-Port Channelized Low speed POS interface card
ibevtModuleRt-cpos1-v2                    OBJECT IDENTIFIER ::= { ibevtModuleRouterType 239 } -- 1-Port Channelized Low speed POS interface card
ibevtModuleRt-oap                         OBJECT IDENTIFIER ::= { ibevtModuleRouterType 240 } -- Open Application Platform
ibevtModuleRT-48FSWP                      OBJECT IDENTIFIER ::= { ibevtModuleRouterType 241 } -- 46-Port 10M/100M(With PoE) and 2-Port 1000BASE-T(With PoE) Ethernet L2 Switch Module
ibevtModuleRT-48FSW                       OBJECT IDENTIFIER ::= { ibevtModuleRouterType 242 } -- 46-Port 10M/100M and 2-Port 1000BASE-T Ethernet L2 Switch Module
ibevtModuleRT-ASM                         OBJECT IDENTIFIER ::= { ibevtModuleRouterType 243 } -- Anti-virus Security Module
ibevtModuleRT-SIC-1FEF                    OBJECT IDENTIFIER ::= { ibevtModuleRouterType 244 } -- 1-Port 100M SFP Interface SIC Module
ibevtModuleRT-XMIM-24FSW                  OBJECT IDENTIFIER ::= { ibevtModuleRouterType 245 } -- 24-Port 10M/100MBASE-TX Ethernet L2 Switch Interface XMIM-Module
ibevtModuleRT-WLAN-AG-1RADIO              OBJECT IDENTIFIER ::= { ibevtModuleRouterType 246 } -- Mini PCI Interface 802.11ag Radio Frequency Adapter Card
ibevtModuleRT-1CE3                        OBJECT IDENTIFIER ::= { ibevtModuleRouterType 247 } -- 1-port E3/CE3/FE3 Compatible Interface Module,(M)
ibevtModuleRT-XMIM-16FSW                  OBJECT IDENTIFIER ::= { ibevtModuleRouterType 248 } -- 16-Port 10M/100MBASE-TX Ethernet L2 Switch Interface XMIM-Module
ibevtModuleRT-OAPS                        OBJECT IDENTIFIER ::= { ibevtModuleRouterType 249 } -- Open Application System-Smart
ibevtModuleRT-NAM                         OBJECT IDENTIFIER ::= { ibevtModuleRouterType 250 } -- Network Analysis Module
ibevtModuleRT-RPE-X1                      OBJECT IDENTIFIER ::= { ibevtModuleRouterType 251 } -- Route Processing Engine
ibevtModuleRT-FIP-100                     OBJECT IDENTIFIER ::= { ibevtModuleRouterType 252 } -- Flexible Interface Platform-100
ibevtModuleRT-FIP-200                     OBJECT IDENTIFIER ::= { ibevtModuleRouterType 253 } -- Flexible Interface Platform-200
ibevtModuleRT-SIC-8AS                     OBJECT IDENTIFIER ::= { ibevtModuleRouterType 254 } -- 8-Port Asynchronous Serial
ibevtModuleRT-WAAM                        OBJECT IDENTIFIER ::= { ibevtModuleRouterType 255 } -- WAN Application Acceleration Module
ibevtModuleRt-msp4p-OC3c                  OBJECT IDENTIFIER ::= { ibevtModuleRouterType 256 } -- 4 Port Multi-Speed POS Interface Module (OC-3c Mode)
ibevtModuleRt-1pos-oc48                   OBJECT IDENTIFIER ::= { ibevtModuleRouterType 257 } -- 1 Port Super-Speed POS Interface Card
ibevtModuleRt-xgbe                        OBJECT IDENTIFIER ::= { ibevtModuleRouterType 258 } -- 1-Port 10GBASE-R/W Ethernet Optical Interface Card
ibevtModuleRT-EADM                        OBJECT IDENTIFIER ::= { ibevtModuleRouterType 259 } -- EAD Integrated Module
ibevtModuleRT-VCM                         OBJECT IDENTIFIER ::= { ibevtModuleRouterType 260 } -- Voice Convergence Module
ibevtModuleRT-SIC-2FXS1FXO                OBJECT IDENTIFIER ::= { ibevtModuleRouterType 261 } -- 2FXS+1FXO Interface SIC-Module
ibevtModuleRT-8FXS8FXO                    OBJECT IDENTIFIER ::= { ibevtModuleRouterType 262 } -- 8FXS+8FXO Interface Module
ibevtModuleRT-16FXS                       OBJECT IDENTIFIER ::= { ibevtModuleRouterType 263 } -- 16-port FXS Interface Module
ibevtModuleRT-OAPS-ICM                    OBJECT IDENTIFIER ::= { ibevtModuleRouterType 264 } -- OAPS Information Communication Module
ibevtModuleRT-OAP-ICM                     OBJECT IDENTIFIER ::= { ibevtModuleRouterType 265 } -- OAP Information Communication Module
ibevtModuleRT-8fe                         OBJECT IDENTIFIER ::= { ibevtModuleRouterType 266 } -- 8-Port 100M Ethernet Electrical Interface Module
ibevtModuleRT-4gbp                        OBJECT IDENTIFIER ::= { ibevtModuleRouterType 267 } -- 4-Port GigaBit Ethernet Optical Interface Module(SFP)
ibevtModuleRT-MPU-G2                      OBJECT IDENTIFIER ::= { ibevtModuleRouterType 268 } -- Main Processor Unit
ibevtModuleRT-OAPS-OCE                    OBJECT IDENTIFIER ::= { ibevtModuleRouterType 269 } -- OAPS Office Communication Engine
ibevtModuleRT-OAP-OCE                     OBJECT IDENTIFIER ::= { ibevtModuleRouterType 270 } -- OAP Office Communication Engine
ibevtModuleRT-OAPS-ICE                    OBJECT IDENTIFIER ::= { ibevtModuleRouterType 271 } -- OAPS Information Communication Engine
ibevtModuleRT-OAP-ICE                     OBJECT IDENTIFIER ::= { ibevtModuleRouterType 272 } -- OAP Information Communication Module
ibevtModuleRT-SIC-16AS                    OBJECT IDENTIFIER ::= { ibevtModuleRouterType 273 } -- 16-Port Asynchronous Serial
ibevtModuleRT-SPE-FWM                     OBJECT IDENTIFIER ::= { ibevtModuleRouterType 274 } -- Gigabit Firewall Module
ibevtModuleRT-cls2p                       OBJECT IDENTIFIER ::= { ibevtModuleRouterType 275 } -- 2 Port Channelized 155M POS to E3/T3 Interface Module
ibevtModuleRT-cls1p                       OBJECT IDENTIFIER ::= { ibevtModuleRouterType 276 } -- 1 Port Channelized 155M POS to E3/T3 Interface Module
ibevtModuleRT-SIC-2E1-F                   OBJECT IDENTIFIER ::= { ibevtModuleRouterType 277 } -- 2-Port Fractional E1 Interface SIC-Module
ibevtModuleRT-SIC-1E1-F-V2                OBJECT IDENTIFIER ::= { ibevtModuleRouterType 278 } -- 1-Port Fractional E1 Interface SIC-Module
ibevtModuleRT-MCU                         OBJECT IDENTIFIER ::= { ibevtModuleRouterType 279 } -- Main Control Unit
ibevtModuleRT-ACU                         OBJECT IDENTIFIER ::= { ibevtModuleRouterType 280 } -- Access Control Unit
ibevtModuleRT-1ATM-OC3                    OBJECT IDENTIFIER ::= { ibevtModuleRouterType 281 } -- 1-Port Asynchronous Transfer Mode OC3 Board
ibevtModuleRT-RSE-X1                      OBJECT IDENTIFIER ::= { ibevtModuleRouterType 282 } -- Main Processing Unit With XAUI Switch
ibevtModuleRT-FIP-210                     OBJECT IDENTIFIER ::= { ibevtModuleRouterType 283 } -- Multi-core CPU Line Processing Board with 2 Combo GE Ports
ibevtModuleRT-1expa                       OBJECT IDENTIFIER ::= { ibevtModuleRouterType 284 } -- 1 Port Ten Gigabit Interface Module
ibevtModuleRT-WLAN-SIC-N-1RADIO           OBJECT IDENTIFIER ::= { ibevtModuleRouterType 285 } -- 1 wlan-radio 802.11n sic Interface Board
ibevtModuleRT-WLAN-SIC-BG-1RADIO          OBJECT IDENTIFIER ::= { ibevtModuleRouterType 286 } -- 1 wlan-radio 802.11b/g sic Interface Board
ibevtModuleRT-al2p                        OBJECT IDENTIFIER ::= { ibevtModuleRouterType 287 } -- 2 Port 155M ATM Interface Module
ibevtModuleRT-msp2p-OC3c                  OBJECT IDENTIFIER ::= { ibevtModuleRouterType 288 } -- 2-Port Multi-speed POS Interface Module (OC-3c Mode)
ibevtModuleRT-8gbp                        OBJECT IDENTIFIER ::= { ibevtModuleRouterType 289 } -- 8-Port GigaBit Ethernet Optical Interface Module(SFP)
ibevtModuleRT-SIC-EPON                    OBJECT IDENTIFIER ::= { ibevtModuleRouterType 290 } -- 1-Port Ethernet Passive Optical Network SIC Card(SFF)
ibevtModuleRT-SIC-3G-GSM-H3               OBJECT IDENTIFIER ::= { ibevtModuleRouterType 291 } -- 3G Wireless WAN Interface SIC Module Supporting GPRS/EDGE/UMTS/HSDPA
ibevtModuleRT-msp2p-OC12c                 OBJECT IDENTIFIER ::= { ibevtModuleRouterType 292 } -- 2-Port Multi-speed POS Interface Module (OC-12c Mode)
ibevtModuleRt-msp4p-OC12c                 OBJECT IDENTIFIER ::= { ibevtModuleRouterType 293 } -- 4-Port Multi-Speed POS Interface Module (OC-12c Mode)
ibevtModuleRt-al1p                        OBJECT IDENTIFIER ::= { ibevtModuleRouterType 294 } -- 1-Port 155M ATM Interface Module
ibevtModuleRt-OAP-100                     OBJECT IDENTIFIER ::= { ibevtModuleRouterType 295 } -- Open Application Platform Module
ibevtModuleRt-FIP-110                     OBJECT IDENTIFIER ::= { ibevtModuleRouterType 296 } -- Flexible Interface Platform-110
ibevtModuleRt-OSM-SSM                     OBJECT IDENTIFIER ::= { ibevtModuleRouterType 297 } -- OSM Security Services Module
ibevtModuleRt-OAP-SSM                     OBJECT IDENTIFIER ::= { ibevtModuleRouterType 298 } -- OAP Security Services Module
ibevtModuleRt-rs2p                        OBJECT IDENTIFIER ::= { ibevtModuleRouterType 299 } -- 2-Port OC-48c/STM-16c RPR Interface Module
ibevtModuleRt-SAP-48GBE                   OBJECT IDENTIFIER ::= { ibevtModuleRouterType 300 } -- 48-Port 1000Base-T Gigabit Ethernet Interface Module
ibevtModuleRt-SAP-48GBP                   OBJECT IDENTIFIER ::= { ibevtModuleRouterType 301 } -- 48-Port 1000BASE Ethernet Optical Interface Module
ibevtModuleRt-SAP-24GBP                   OBJECT IDENTIFIER ::= { ibevtModuleRouterType 302 } -- 24-Port 1000BASE Ethernet Optical Interface Module
ibevtModuleRt-SPE-SSL                     OBJECT IDENTIFIER ::= { ibevtModuleRouterType 303 } -- SSL VPN Module
ibevtModuleRt-SIC-AUDIO                   OBJECT IDENTIFIER ::= { ibevtModuleRouterType 304 } -- MOH and PAGE Interface SIC Module Supporting MOH/PAGE/DOOR RELAY
ibevtModuleRt-FIC-1E1POS-H3               OBJECT IDENTIFIER ::= { ibevtModuleRouterType 305 } -- 1-Port E1 POS Interface FIC Module
ibevtModuleRt-DSIC-4FXS1FXO               OBJECT IDENTIFIER ::= { ibevtModuleRouterType 306 } -- 4FXS+1FXO Interface DSIC-Module
ibevtModuleRt-FIC-CPOS                    OBJECT IDENTIFIER ::= { ibevtModuleRouterType 307 } -- 1-Port CPOS Interface Module
ibevtModuleRt-DSIC-1SHDSL-8W              OBJECT IDENTIFIER ::= { ibevtModuleRouterType 308 } -- 1-Port 8 Wire SHDSL Interface DSIC Module
ibevtModuleRt-SIC-3G-TD                   OBJECT IDENTIFIER ::= { ibevtModuleRouterType 309 } -- 1 Port TD-Cellular Interface SIC-Module
ibevtModuleRt-SIC-3G-CDMA                 OBJECT IDENTIFIER ::= { ibevtModuleRouterType 310 } -- 1 Port CDMA-Cellular Interface SIC-Module
ibevtModuleRt-SIC-3G-HSPA                 OBJECT IDENTIFIER ::= { ibevtModuleRouterType 311 } -- 1 Port HSPA-Cellular Interface SIC-Module
ibevtModuleRt-FIC-OAP-V2                  OBJECT IDENTIFIER ::= { ibevtModuleRouterType 312 } -- Open Application Platform V2 FIC Module
ibevtModuleRt-MIM-OAP-V2                  OBJECT IDENTIFIER ::= { ibevtModuleRouterType 313 } -- Open Application Platform V2 MIM Module
ibevtModuleRt-MIM-OAPS-V2                 OBJECT IDENTIFIER ::= { ibevtModuleRouterType 314 } -- Open Application System-Smart V2 MIM Module
ibevtModuleRt-HMIM-1CT3                   OBJECT IDENTIFIER ::= { ibevtModuleRouterType 315 } -- 1 Port Channelized T3 Interface HMIM Module
ibevtModuleRt-HMIM-1CE3                   OBJECT IDENTIFIER ::= { ibevtModuleRouterType 316 } -- 1 Port Channelized E3 Interface HMIM Module
ibevtModuleRt-HMIM-1POS                   OBJECT IDENTIFIER ::= { ibevtModuleRouterType 317 } -- 1 Port POS Interface HMIM Module
ibevtModuleRt-HMIM-2SAE                   OBJECT IDENTIFIER ::= { ibevtModuleRouterType 318 } -- 2 Port SAE Interface HMIM Module
ibevtModuleRt-HMIM-4SAE                   OBJECT IDENTIFIER ::= { ibevtModuleRouterType 319 } -- 4 Port SAE Interface HMIM Module
ibevtModuleRt-HMIM-8SAE                   OBJECT IDENTIFIER ::= { ibevtModuleRouterType 320 } -- 8 Port SAE Interface HMIM Module
ibevtModuleRt-HMIM-8ASE                   OBJECT IDENTIFIER ::= { ibevtModuleRouterType 321 } -- 8 Port ASE Interface HMIM Module
ibevtModuleRt-HMIM-16ASE                  OBJECT IDENTIFIER ::= { ibevtModuleRouterType 322 } -- 16 Port ASE Interface HMIM Module
ibevtModuleRt-HMIM-1E1                    OBJECT IDENTIFIER ::= { ibevtModuleRouterType 323 } -- 1 Port E1 Interface HMIM Module
ibevtModuleRt-HMIM-2E1                    OBJECT IDENTIFIER ::= { ibevtModuleRouterType 324 } -- 2 Port E1 Interface HMIM Module
ibevtModuleRt-HMIM-4E1                    OBJECT IDENTIFIER ::= { ibevtModuleRouterType 325 } -- 4 Port E1 Interface HMIM Module
ibevtModuleRt-HMIM-8E1-75                 OBJECT IDENTIFIER ::= { ibevtModuleRouterType 326 } -- 8 Port E1(75 o) Interface HMIM Module
ibevtModuleRt-HMIM-1E1-F                  OBJECT IDENTIFIER ::= { ibevtModuleRouterType 327 } -- 1 Port E1-F Interface HMIM Module
ibevtModuleRt-HMIM-2E1-F                  OBJECT IDENTIFIER ::= { ibevtModuleRouterType 328 } -- 2 Port E1-F Interface HMIM Module
ibevtModuleRt-HMIM-4E1-F                  OBJECT IDENTIFIER ::= { ibevtModuleRouterType 329 } -- 4 Port E1-F Interface HMIM Module
ibevtModuleRt-HMIM-8E1-F-75               OBJECT IDENTIFIER ::= { ibevtModuleRouterType 330 } -- 8 Port E1-F(75 o) Interface HMIM Module
ibevtModuleRt-HMIM-6AM                    OBJECT IDENTIFIER ::= { ibevtModuleRouterType 331 } -- 6 Port AM Interface HMIM Module
ibevtModuleRt-HMIM-6FCM                   OBJECT IDENTIFIER ::= { ibevtModuleRouterType 332 } -- 6 Port FCM Interface HMIM Module
ibevtModuleRt-HMIM-2T1                    OBJECT IDENTIFIER ::= { ibevtModuleRouterType 333 } -- 2 Port T1 Interface HMIM Module
ibevtModuleRt-HMIM-4T1-F                  OBJECT IDENTIFIER ::= { ibevtModuleRouterType 334 } -- 4 Port T1-F Interface HMIM Module
ibevtModuleRt-HMIM-8T1                    OBJECT IDENTIFIER ::= { ibevtModuleRouterType 335 } -- 8 Port T1 Interface HMIM Module
ibevtModuleRt-HMIM-8T1-F                  OBJECT IDENTIFIER ::= { ibevtModuleRouterType 336 } -- 8 Port T1-F Interface HMIM Module
ibevtModuleRt-HMIM-1VE1                   OBJECT IDENTIFIER ::= { ibevtModuleRouterType 337 } -- 1 Port Voice E1 Interface HMIM Module
ibevtModuleRt-HMIM-1VT1                   OBJECT IDENTIFIER ::= { ibevtModuleRouterType 338 } -- 1 Port Voice T1 Interface HMIM Module
ibevtModuleRt-HMIM-2VE1                   OBJECT IDENTIFIER ::= { ibevtModuleRouterType 339 } -- 2 Port Voice E1 Interface HMIM Module
ibevtModuleRt-HMIM-2VT1                   OBJECT IDENTIFIER ::= { ibevtModuleRouterType 340 } -- 2 Port Voice T1 Interface HMIM Module
ibevtModuleRt-HMIM-8FXS8FXO               OBJECT IDENTIFIER ::= { ibevtModuleRouterType 341 } -- 8FXS + 8FXO Interface HMIM Module
ibevtModuleRt-HMIM-16FXS                  OBJECT IDENTIFIER ::= { ibevtModuleRouterType 342 } -- 16 Port FXS Interface HMIM Module
ibevtModuleRt-HMIM-4FXS                   OBJECT IDENTIFIER ::= { ibevtModuleRouterType 343 } -- 4 Port FXS Interface HMIM Module
ibevtModuleRt-HMIM-4FXO                   OBJECT IDENTIFIER ::= { ibevtModuleRouterType 344 } -- 4 Port FXO Interface HMIM Module
ibevtModuleRt-HMIM-4EM                    OBJECT IDENTIFIER ::= { ibevtModuleRouterType 345 } -- 4 Port E&M Interface HMIM Module
ibevtModuleRt-HMIM-4BSV                   OBJECT IDENTIFIER ::= { ibevtModuleRouterType 346 } -- 4 Port Bri S/T Voice Interface HMIM Module
ibevtModuleRt-SIC-CNDE                    OBJECT IDENTIFIER ::= { ibevtModuleRouterType 347 } -- CNDE Crypto Engine SIC-Module
ibevtModuleRt-ESM-CNDE                    OBJECT IDENTIFIER ::= { ibevtModuleRouterType 348 } -- CNDE Crypto Engine ESM-Module
ibevtModuleRt-ESM-CNDE-M                  OBJECT IDENTIFIER ::= { ibevtModuleRouterType 349 } -- CNDE Crypto Engine MiniPCI-ESM-Module
ibevtModuleRt-SR6602-X1                   OBJECT IDENTIFIER ::= { ibevtModuleRouterType 350 } -- 2U Router Host(4GE Combo/2 HIM slot)
ibevtModuleRt-SR6602-X2                   OBJECT IDENTIFIER ::= { ibevtModuleRouterType 351 } -- 2U Router Host(4GE Combo/2 10G SFP+/2 HIM slot)
ibevtModuleRt-MCP-X1                      OBJECT IDENTIFIER ::= { ibevtModuleRouterType 352 } -- Main Controller and Processor X1
ibevtModuleRt-MCP-X2                      OBJECT IDENTIFIER ::= { ibevtModuleRouterType 353 } -- Main Controller and Processor X2
ibevtModuleRt-FIP-10                      OBJECT IDENTIFIER ::= { ibevtModuleRouterType 354 } -- Flexible Interface Platform 10
ibevtModuleRt-FIP-20                      OBJECT IDENTIFIER ::= { ibevtModuleRouterType 355 } -- Flexible Interface Platform 20
ibevtModuleRt-RSE-X2                      OBJECT IDENTIFIER ::= { ibevtModuleRouterType 356 } -- Route Switch Engine X2
ibevtModuleRt-FIP-600                     OBJECT IDENTIFIER ::= { ibevtModuleRouterType 357 } -- Flexible Interface Platform 600
ibevtModuleRt-SAP-4EXP                    OBJECT IDENTIFIER ::= { ibevtModuleRouterType 358 } -- 4-Port 10GBASE-R/W Ethernet Optical Interface Module(SFP+)
ibevtModuleRt-SFE-X1                      OBJECT IDENTIFIER ::= { ibevtModuleRouterType 359 } -- Switch Fabric Engine X1
ibevtModuleRt-SFE-A1                      OBJECT IDENTIFIER ::= { ibevtModuleRouterType 360 } -- Switch Fabric Engine A1
ibevtModuleRt-HMIM-24GSW                  OBJECT IDENTIFIER ::= { ibevtModuleRouterType 361 } -- 24-Port 10M/100M/1000MBASE-T Ethernet L2 Switch Interface HMIM_Module
ibevtModuleRt-HMIM-24GSWP                 OBJECT IDENTIFIER ::= { ibevtModuleRouterType 362 } -- 24-Port 10M/100M/1000MBASE-T(WITH POE) Ethernet L2 Switch Interface HMIM_Module
ibevtModuleRt-MPU100                      OBJECT IDENTIFIER ::= { ibevtModuleRouterType 363 } -- Main Processing Unit 100
ibevtModuleRt-SPU100                      OBJECT IDENTIFIER ::= { ibevtModuleRouterType 364 } -- Service Processing Unit 100
ibevtModuleRt-SPU200                      OBJECT IDENTIFIER ::= { ibevtModuleRouterType 365 } -- Service Processing Unit 200
ibevtModuleRt-WLAN-N-1RADIO               OBJECT IDENTIFIER ::= { ibevtModuleRouterType 366 } -- Mini PCI Interface 802.11n Radio Frequency Adapter Card
ibevtModuleRt-3G-CDMA                     OBJECT IDENTIFIER ::= { ibevtModuleRouterType 367 } -- 1 Port CDMA-Cellular Interface Adapter Card
ibevtModuleRt-3G-WCDMA                    OBJECT IDENTIFIER ::= { ibevtModuleRouterType 368 } -- 1 Port WCDMA-Cellular Interface Adapter Card
ibevtModuleRt-3G-HSPAPLUS                 OBJECT IDENTIFIER ::= { ibevtModuleRouterType 369 } -- 1 Port HSPA+-Cellular Interface Adapter Card
ibevtModuleRt-VPM-128                     OBJECT IDENTIFIER ::= { ibevtModuleRouterType 370 } -- 128-VoiceChannel VPM Module
ibevtModuleRt-VPM-256                     OBJECT IDENTIFIER ::= { ibevtModuleRouterType 371 } -- 256-VoiceChannel VPM Module
ibevtModuleRt-VPM-512                     OBJECT IDENTIFIER ::= { ibevtModuleRouterType 372 } -- 512-VoiceChannel VPM Module
ibevtModuleRt-HMIM-8GEE                   OBJECT IDENTIFIER ::= { ibevtModuleRouterType 373 } -- 8-port copper GigabitEthernet HMIM Module
ibevtModuleRt-HMIM-4GEE                   OBJECT IDENTIFIER ::= { ibevtModuleRouterType 374 } -- 4-port copper GigabitEthernet HMIM Module
ibevtModuleRt-HMIM-2GEE                   OBJECT IDENTIFIER ::= { ibevtModuleRouterType 375 } -- 2-port copper GigabitEthernet HMIM Module
ibevtModuleRt-HMIM-8GEF                   OBJECT IDENTIFIER ::= { ibevtModuleRouterType 376 } -- 8-port fiber GigabitEthernet HMIM Module
ibevtModuleRt-HMIM-4GEF                   OBJECT IDENTIFIER ::= { ibevtModuleRouterType 377 } -- 4-port fiber GigabitEthernet HMIM Module
ibevtModuleRt-HMIM-2GEF                   OBJECT IDENTIFIER ::= { ibevtModuleRouterType 378 } -- 2-port fiber GigabitEthernet HMIM Module
ibevtModuleRt-SPU300                      OBJECT IDENTIFIER ::= { ibevtModuleRouterType 379 } -- Service Processing Unit 300
ibevtModuleRt-HMIM-1CPOS                  OBJECT IDENTIFIER ::= { ibevtModuleRouterType 380 } -- 1-port CPOS Interface HMIM Module
ibevtModuleRt-HMIM-2CPOS                  OBJECT IDENTIFIER ::= { ibevtModuleRouterType 381 } -- 2-port CPOS Interface HMIM Module
ibevtModuleRt-SPU100-5080                 OBJECT IDENTIFIER ::= { ibevtModuleRouterType 382 } -- Service Processing Unit 100
ibevtModuleRt-SPU200-5080                 OBJECT IDENTIFIER ::= { ibevtModuleRouterType 383 } -- Service Processing Unit 200
ibevtModuleRt-SPU300-5080                 OBJECT IDENTIFIER ::= { ibevtModuleRouterType 384 } -- Service Processing Unit 300
ibevtModuleRt-4G-LTE-Verizon              OBJECT IDENTIFIER ::= { ibevtModuleRouterType 385 } -- 1 Port 4G-LTE-Verizon-Cellular Interface Adapter Card
ibevtModuleRt-4G-LTE-Global               OBJECT IDENTIFIER ::= { ibevtModuleRouterType 386 } -- 1 Port 4G-LTE-Global-Cellular Interface Adapter Card
ibevtModuleRt-HMIM-1ATM-OC3               OBJECT IDENTIFIER ::= { ibevtModuleRouterType 387 } -- 1-Port OC3 ATM MM/SM/SML HMIM Module
ibevtModuleRt-SIC-1E1-V2                  OBJECT IDENTIFIER ::= { ibevtModuleRouterType 388 } -- 1-Port E1/CE1/PRI Interface SIC Module
ibevtModuleRt-FIP-300                     OBJECT IDENTIFIER ::= { ibevtModuleRouterType 389 } -- Flexible Interface Platform 300
ibevtModuleRt-FIP-310                     OBJECT IDENTIFIER ::= { ibevtModuleRouterType 390 } -- Flexible Interface Platform 310
ibevtModuleRt-TS8P                        OBJECT IDENTIFIER ::= { ibevtModuleRouterType 391 } -- 8-Port OC-3c/OC-12c POS or Gigabit Ethernet Optical Interface Module(SFP)
ibevtModuleRt-4G4P                        OBJECT IDENTIFIER ::= { ibevtModuleRouterType 392 } -- 4-Port Gigabit Ethernet Optical Interface and 4-Port OC-3c POS Interface Module(SFP)
ibevtModuleRt-SIC-4G-LTE-V                OBJECT IDENTIFIER ::= { ibevtModuleRouterType 393 } -- 1 Port 4G-LTE-Verizon-Cellular Interface SIC-Module
ibevtModuleRt-SIC-4G-LTE-A                OBJECT IDENTIFIER ::= { ibevtModuleRouterType 394 } -- 1 Port 4G-LTE-AT&T-Cellular Interface SIC-Module
ibevtModuleRt-SIC-4G-LTE-G                OBJECT IDENTIFIER ::= { ibevtModuleRouterType 395 } -- 1 Port 4G-LTE-Global-Cellular Interface SIC-Module
ibevtModuleRt-SIC-2SAE                    OBJECT IDENTIFIER ::= { ibevtModuleRouterType 396 } -- 2 Port SAE Interface SIC Module
ibevtModuleRt-SIC-4SAE                    OBJECT IDENTIFIER ::= { ibevtModuleRouterType 397 } -- 4 Port SAE Interface SIC Module
ibevtModuleRt-HMIM-OAP                    OBJECT IDENTIFIER ::= { ibevtModuleRouterType 398 } -- Open Application Platform HMIM Interface Module with Cloud Virtualization Kernel
ibevtModuleRt-HMIM-8GSW                   OBJECT IDENTIFIER ::= { ibevtModuleRouterType 399 } -- 8-Port 10M/100M/1000MBASE-T Ethernet L2 Switch Interface HMIM-Module,including 2 Combo Ports

--
-- 400 to 599 reserved for security routers
--
ibevtModuleRt-IPU                         OBJECT IDENTIFIER ::= { ibevtModuleRouterType 400 } -- IPS Processing Unit
ibevtModuleRt-MIM2GEBE-PCIE               OBJECT IDENTIFIER ::= { ibevtModuleRouterType 401 } -- 2-port UTM GigabitEthernet Interface Module
ibevtModuleRt-HIM12GE-PCIE                OBJECT IDENTIFIER ::= { ibevtModuleRouterType 402 } -- 12-port GigabitEthernet Interface Module
ibevtModuleRt-HIM2XGE-PCIE                OBJECT IDENTIFIER ::= { ibevtModuleRouterType 403 } -- 2-port Ten-GigabitEthernet Interface Module
ibevtModuleRt-IPU-T1000-M                 OBJECT IDENTIFIER ::= { ibevtModuleRouterType 404 } -- IPS Processing Unit for T1000-M Mainboard Module
ibevtModuleRt-IPU-GX4C                    OBJECT IDENTIFIER ::= { ibevtModuleRouterType 405 } -- 4 Port Gigabit Fiber Module
ibevtModuleRt-IPU-GT4C                    OBJECT IDENTIFIER ::= { ibevtModuleRouterType 406 } -- 4 Port 1000BASE-T Module
ibevtModuleRt-RPU-IAG2000-A               OBJECT IDENTIFIER ::= { ibevtModuleRouterType 407 } -- Intelligence Application Gateway Module
ibevtModuleRt-RPU-AFD1000-A               OBJECT IDENTIFIER ::= { ibevtModuleRouterType 408 } -- Anomaly Flow Detector Module
ibevtModuleRt-RPU-F5000-A                 OBJECT IDENTIFIER ::= { ibevtModuleRouterType 409 } -- Advanced Firewall Module
ibevtModuleRt-ACG-8800S3-MPU              OBJECT IDENTIFIER ::= { ibevtModuleRouterType 410 } -- Main Control Unit,with 24 1000BASE-X/100BASE-FX Optical Ports,including 8 Combo Ports,SFP Req
ibevtModuleRt-T5000S3-MPU                 OBJECT IDENTIFIER ::= { ibevtModuleRouterType 411 } -- Main Control Unit,with 24 1000BASE-X/100BASE-FX Optical Ports,including 8 Combo Ports,SFP Req
ibevtModuleRt-NS21S2MSPB0                 OBJECT IDENTIFIER ::= { ibevtModuleRouterType 412 } -- Multi Service Processing Module
ibevtModuleRt-NS11S2MSPB0                 OBJECT IDENTIFIER ::= { ibevtModuleRouterType 413 } -- Multi Service Processing Module
ibevtModuleRt-NSQ1WLAN                    OBJECT IDENTIFIER ::= { ibevtModuleRouterType 414 } -- Dual-Band,Multi-Mode 802.11a/b/g Wireless LAN card
ibevtModuleRt-NSQ1GP4U0                   OBJECT IDENTIFIER ::= { ibevtModuleRouterType 415 } -- 4 Port Gigabit Fiber Module
ibevtModuleRt-NSQ1GP8C40                  OBJECT IDENTIFIER ::= { ibevtModuleRouterType 416 } -- 12-Port GigabitEthernet Interface Module,with 4 Combo Ports,8 Fiber Ports
ibevtModuleRt-NSQ1XS2U0                   OBJECT IDENTIFIER ::= { ibevtModuleRouterType 417 } -- 2-Port Ten GigabitEthernet Interface Module
ibevtModuleRt-NSQ1G24XS60                 OBJECT IDENTIFIER ::= { ibevtModuleRouterType 418 } -- 12-copper 12-fiber and 6-XGE Interface Module
ibevtModuleRt-NSQ1TGX4EA0                 OBJECT IDENTIFIER ::= { ibevtModuleRouterType 419 } -- 4-XGE Fabric Interface Module
ibevtModuleRt-NSQ1FAB08D0                 OBJECT IDENTIFIER ::= { ibevtModuleRouterType 420 } -- Switch Module
ibevtModuleRt-NSQ1TGS32SF0                OBJECT IDENTIFIER ::= { ibevtModuleRouterType 421 } -- 32-XGE Fabric Interface Module
ibevtModuleRt-NSQ1QGS4SF0                 OBJECT IDENTIFIER ::= { ibevtModuleRouterType 422 } -- 4-XGE Fabric Interface Module
ibevtModuleRt-NSQ1GP24TXEA0               OBJECT IDENTIFIER ::= { ibevtModuleRouterType 423 } -- 16-GE Fabric,8-GE Combo,2-XGE Interface Module
ibevtModuleRt-NSQ1GP48EB0                 OBJECT IDENTIFIER ::= { ibevtModuleRouterType 424 } -- 48-GE Fabric Interface Module
ibevtModuleRt-NSQ1FWCEA0                  OBJECT IDENTIFIER ::= { ibevtModuleRouterType 425 } -- Firewall Module
ibevtModuleRt-NSQ1GT48EA0                 OBJECT IDENTIFIER ::= { ibevtModuleRouterType 426 } -- 48-GE Copper Interface
ibevtModuleRt-NSQ1TGS8EA0                 OBJECT IDENTIFIER ::= { ibevtModuleRouterType 427 } -- 8-XGE Fabric Interface
ibevtModuleRt-NSQ1FAB04B0                 OBJECT IDENTIFIER ::= { ibevtModuleRouterType 428 } -- Switch Module
ibevtModuleRt-NSQ1FAB12D0                 OBJECT IDENTIFIER ::= { ibevtModuleRouterType 429 } -- Switch Module
ibevtModuleRt-NSQ1SUPB0                   OBJECT IDENTIFIER ::= { ibevtModuleRouterType 430 } -- Main Control Module
ibevtModuleRt-VFW1000                     OBJECT IDENTIFIER ::= { ibevtModuleRouterType 431 } -- Virtual Firwall Gateway module over virtual machine
ibevtModuleRt-NSQ1CGC2SE0                 OBJECT IDENTIFIER ::= { ibevtModuleRouterType 432 } -- 2 Port 100GBASE Ethernet Optical Interface Board(CFP)(SE)
ibevtModuleRt-VLB1000                     OBJECT IDENTIFIER ::= { ibevtModuleRouterType 433 } -- Virtual LB module over virtual machine
ibevtModuleRt-NSQM1GT4PFC                 OBJECT IDENTIFIER ::= { ibevtModuleRouterType 434 } -- 4 Port GigabitEthernet Interface
ibevtModuleRt-NSQM1FWDFG0                 OBJECT IDENTIFIER ::= { ibevtModuleRouterType 435 } -- Firewall Module
ibevtModuleRt-NSQM1NATDFGA0               OBJECT IDENTIFIER ::= { ibevtModuleRouterType 436 } -- NAT A module
ibevtModuleRt-NSQM1NATDFGB0               OBJECT IDENTIFIER ::= { ibevtModuleRouterType 437 } -- NAT B module
ibevtModuleRt-VFW2000                     OBJECT IDENTIFIER ::= { ibevtModuleRouterType 438 } -- Virtual Firwall Gateway module over physical machine
ibevtModuleRt-VLB2000                     OBJECT IDENTIFIER ::= { ibevtModuleRouterType 439 } -- Virtual LB module ver physical machine
ibevtModuleRt-NSQM1IPSDFG0                OBJECT IDENTIFIER ::= { ibevtModuleRouterType 440 } -- NSQM1IPSDFG0
ibevtModuleRt-NSQM1FWDFGB0                OBJECT IDENTIFIER ::= { ibevtModuleRouterType 441 } -- NSQM1FWDFGB0-SecBlade IV
ibevtModuleRt-NSQM1FWDFGC0                OBJECT IDENTIFIER ::= { ibevtModuleRouterType 442 } -- NSQM1FWDFGC0-SecBlade IV
ibevtModuleRt-NSQM1FWDFGA1                OBJECT IDENTIFIER ::= { ibevtModuleRouterType 443 } -- NSQM1FWDFGA1-SecBlade IV
ibevtModuleRt-NSQM1FWDFGB1                OBJECT IDENTIFIER ::= { ibevtModuleRouterType 444 } -- NSQM1FWDFGB1-SecBlade IV
ibevtModuleRt-NSQM1FWDFGC1                OBJECT IDENTIFIER ::= { ibevtModuleRouterType 445 } -- NSQM1FWDFGC1-SecBlade IV
ibevtModuleRt-NSQM1FWDFGD1                OBJECT IDENTIFIER ::= { ibevtModuleRouterType 446 } -- NSQM1FWDFGD1-SecBlade IV
ibevtModuleRt-NSQM1SUPC0                  OBJECT IDENTIFIER ::= { ibevtModuleRouterType 447 } -- SecPath T9000-NSQM1SUPC0
ibevtModuleRt-NSQM1TG4FBA                 OBJECT IDENTIFIER ::= { ibevtModuleRouterType 448 } -- SecPath F1000-NSQM1TG4FBA
ibevtModuleRt-NSQM1GP4FBA                 OBJECT IDENTIFIER ::= { ibevtModuleRouterType 449 } -- SecPath F1000-NSQM1GP4FBA
ibevtModuleRt-NSQM2MPUC0                  OBJECT IDENTIFIER ::= { ibevtModuleRouterType 450 } -- M9008-S FW  NSQM2MPUC0
ibevtModuleRt-NSQM2TGS16SF0               OBJECT IDENTIFIER ::= { ibevtModuleRouterType 451 } -- M9008-S FW  NSQM2TGS16SF0
ibevtModuleRt-NSQM2QGS4SC0                OBJECT IDENTIFIER ::= { ibevtModuleRouterType 452 } -- M9008-S FW  NSQM2QGS4SC0
ibevtModuleRt-NSQM2GP24TSSC0              OBJECT IDENTIFIER ::= { ibevtModuleRouterType 453 } -- M9008-S FW  NSQM2GP24TSSC0
ibevtModuleRt-NSQM2FWDSC0                 OBJECT IDENTIFIER ::= { ibevtModuleRouterType 454 } -- M9008-S FW  NSQM2FWDSC0
ibevtModuleRt-NSQM1ADEDFGA0               OBJECT IDENTIFIER ::= { ibevtModuleRouterType 455 } -- NSQM1ADEDFGA0-SecBlade IV ADE A module
ibevtModuleRt-NSQM2FWDSCA0                OBJECT IDENTIFIER ::= { ibevtModuleRouterType 456 } -- M9000-S FW NSQM2FWDSCA0-SecBlade IV
ibevtModuleRt-NSQM1TGS32QSSG0             OBJECT IDENTIFIER ::= { ibevtModuleRouterType 457 } -- SecPath M9000-NSQM1TGS32QSSG0
ibevtModuleRt-NSQM1GT4PFCA                OBJECT IDENTIFIER ::= { ibevtModuleRouterType 458 } -- 4 Port GigabitEthernet Interface Module
ibevtModuleRt-NSQM1TG8A                   OBJECT IDENTIFIER ::= { ibevtModuleRouterType 459 } -- 8 Port Ten-GigabitEthernet Interface Module
ibevtModuleRt-NSQM1QG2A                   OBJECT IDENTIFIER ::= { ibevtModuleRouterType 460 } -- 2 Port Forty-GigabitEthernet Interface Module
ibevtModuleRt-NSQM1GT8A                   OBJECT IDENTIFIER ::= { ibevtModuleRouterType 461 } -- 8-Port Gigabit Ethernet interface Module
ibevtModuleRt-NSQM1GP8A                   OBJECT IDENTIFIER ::= { ibevtModuleRouterType 462 } -- 8 Port Fabric GigabitEthernet Interface Module
ibevtModuleRt-NSQM1MBFE0                  OBJECT IDENTIFIER ::= { ibevtModuleRouterType 463 } -- SecPath M9008-S  NSQM1MBFE0
ibevtModuleRt-NSQM2MBFDA0                 OBJECT IDENTIFIER ::= { ibevtModuleRouterType 464 } -- SecPath M9008-S NSQM2MBFDA0
ibevtModuleRt-NSQM2QG2TG8GP40             OBJECT IDENTIFIER ::= { ibevtModuleRouterType 465 } -- SecPath M9008-S  NSQM2QG2TG8GP40
ibevtModuleRt-NSQM2QG4GP40                OBJECT IDENTIFIER ::= { ibevtModuleRouterType 466 } -- SecPath M9008-S  NSQM2QG4GP40
ibevtModuleRt-NSQM2TG16GP40               OBJECT IDENTIFIER ::= { ibevtModuleRouterType 467 } -- SecPath M9008-S  NSQM2TG16GP40
ibevtModuleRt-NSQM1CGQ20                  OBJECT IDENTIFIER ::= { ibevtModuleRouterType 468 } -- SecPath M9008-S  NSQM1CGQ20
ibevtModuleRt-NSQM2FWDFG0                 OBJECT IDENTIFIER ::= { ibevtModuleRouterType 469 } -- M9000-S FW NSQM2FWDFG0-SecBlade IV
ibevtModuleRt-NSQM2TMPUC0                 OBJECT IDENTIFIER ::= { ibevtModuleRouterType 470 } -- SecPath T9000-S-NSQM2TMPUC0
ibevtModuleRt-NSQM2IPSDSCA0               OBJECT IDENTIFIER ::= { ibevtModuleRouterType 471 } -- SecPath T9000-S-NSQM2IPSDSCA0-SecBlade IV
ibevtModuleRt-NSQM2AC1400                 OBJECT IDENTIFIER ::= { ibevtModuleRouterType 472 } -- SecPath M9000-S-NSQM2AC1400
ibevtModuleRt-NSQM2DC1400                 OBJECT IDENTIFIER ::= { ibevtModuleRouterType 473 } -- SecPath M9000-S-NSQM2DC1400
ibevtModuleRt-NSQM1F1KGM0                 OBJECT IDENTIFIER ::= { ibevtModuleRouterType 474} -- F1000 GM Crypto Module
ibevtModuleRt-NSQM1F1KGM0-context         OBJECT IDENTIFIER ::= { ibevtModuleRouterType 475} -- F1000 GM Crypto Module
ibevtModuleRt-NSQM1F5KGM0                 OBJECT IDENTIFIER ::= { ibevtModuleRouterType 476} -- F5000 GM Crypto Module
ibevtModuleRt-NSQM1F5KGM0-context         OBJECT IDENTIFIER ::= { ibevtModuleRouterType 477} -- F5000 GM Crypto Module
ibevtModuleRt-NSQM2QG2GP40                OBJECT IDENTIFIER ::= { ibevtModuleRouterType 478 } -- SecPath M9000-NSQM2QG2GP40
ibevtModuleRt-NSQM2TG8GP40                OBJECT IDENTIFIER ::= { ibevtModuleRouterType 479 } -- SecPath M9000-NSQM2TG8GP40

ibevtModuleRt-NSQM2ADEDSCA0               OBJECT IDENTIFIER ::= { ibevtModuleRouterType 482 } -- M9000-S FW NSQM2ADEDSCA0-SecBlade IV
ibevtModuleRt-NSQM2IPSDSCB0               OBJECT IDENTIFIER ::= { ibevtModuleRouterType 483 } -- M9000-S FW NSQM2IPSDSCB0-SecBlade IV
ibevtModuleRt-NSQM1G4XS4                  OBJECT IDENTIFIER ::= { ibevtModuleRouterType 484 } -- 4-GE Fabric,4-XGE Fabric Interface Module
ibevtModuleRt-NSUM1GT4PFCA                OBJECT IDENTIFIER ::= { ibevtModuleRouterType 485 } -- 4 Port GigabitEthernet Interface Module
ibevtModuleRt-NSUM1TG8A                   OBJECT IDENTIFIER ::= { ibevtModuleRouterType 486 } -- 8 Port Ten-GigabitEthernet Interface Module
ibevtModuleRt-NSUM1QG2A                   OBJECT IDENTIFIER ::= { ibevtModuleRouterType 487 } -- 2 Port Forty-GigabitEthernet Interface Module
ibevtModuleRt-NSUM1GT8A                   OBJECT IDENTIFIER ::= { ibevtModuleRouterType 488 } -- 8-Port Gigabit Ethernet interface Module
ibevtModuleRt-NSUM1GP8A                   OBJECT IDENTIFIER ::= { ibevtModuleRouterType 489 } -- 8 Port Fabric GigabitEthernet Interface Module

ibevtModuleRt-NSQM2MPUD0                  OBJECT IDENTIFIER ::= { ibevtModuleRouterType 491 } -- SecPath M9000-S- NSQM2MPUD0
ibevtModuleRt-NSQM1GMDSCA1                OBJECT IDENTIFIER ::= { ibevtModuleRouterType 492 } -- SecPath M9000-GM- NSQM1GMDSCA1
ibevtModuleRt-NSQM1MPULA                  OBJECT IDENTIFIER ::= { ibevtModuleRouterType 493} -- SecPath F50X0-D NSQM1MPULA
ibevtModuleRt-NSQM1MPULA2                 OBJECT IDENTIFIER ::= { ibevtModuleRouterType 494} -- SecPath F5000-AK515 NSQM1MPULA2
ibevtModuleRt-NSQM1GT8A2                  OBJECT IDENTIFIER ::= { ibevtModuleRouterType 495} -- SecPath F5000-AK515 NSQM1GT8A2
ibevtModuleRt-NSQM1GP4TG4A2               OBJECT IDENTIFIER ::= { ibevtModuleRouterType 496} -- SecPath F5000-AK515 NSQM1GP4TG4A2
ibevtModuleRt-NSQM1GP2TG6A2               OBJECT IDENTIFIER ::= { ibevtModuleRouterType 497} -- SecPath F5000-AK515 NSQM1GP2TG6A2
ibevtModuleRt-NSQM1TG4FBA7                OBJECT IDENTIFIER ::= { ibevtModuleRouterType 498} -- SecPath F1000-AK-NSQM1TG4FBA7

ibevtModuleRt-NSQM1F1KGMB                 OBJECT IDENTIFIER ::= { ibevtModuleRouterType 499} -- F1000 GM Crypto Module
ibevtModuleRt-NSQM1F1KGMC                 OBJECT IDENTIFIER ::= { ibevtModuleRouterType 500} -- F1000 GM Crypto Module
ibevtModuleRt-NSQM1F5KGMC                 OBJECT IDENTIFIER ::= { ibevtModuleRouterType 501} -- F1000 GM Crypto Module
ibevtModuleRt-NSQM5SUP08H0                OBJECT IDENTIFIER ::= { ibevtModuleRouterType 502 } -- SecPath M9000-E8-NSQM5SUP08H0
ibevtModuleRt-NSQM5SUP16C0                OBJECT IDENTIFIER ::= { ibevtModuleRouterType 503 } -- SecPath M9000-E16-NSQM5SUP16C0
ibevtModuleRt-NS-FWEMPA0                  OBJECT IDENTIFIER ::= { ibevtModuleRouterType 504 } -- SecPath M9000-E-NS-FWEMPA0
ibevtModuleRt-NSQM5MBSHA0                 OBJECT IDENTIFIER ::= { ibevtModuleRouterType 505 } -- SecPath M9000-E-NSQM5MBSHA0
ibevtModuleRt-NS-C600-CGQ6A0              OBJECT IDENTIFIER ::= { ibevtModuleRouterType 506 } -- SecPath M9000-E-NS-C600-CGQ6A0
ibevtModuleRt-NS-C300-CGQ2TG16A0          OBJECT IDENTIFIER ::= { ibevtModuleRouterType 507 } -- SecPath M9000-E-NS-C300-CGQ2TG16A0
ibevtModuleRt-NS-C300-TG24A0              OBJECT IDENTIFIER ::= { ibevtModuleRouterType 508 } -- SecPath M9000-E-NS-C300-TG24A0
ibevtModuleRt-NS-C300-QG4TG16A0           OBJECT IDENTIFIER ::= { ibevtModuleRouterType 509 } -- SecPath M9000-E-NS-C300-QG4TG16A0
ibevtModuleRt-NSQM5FAB08A0                OBJECT IDENTIFIER ::= { ibevtModuleRouterType 510 } -- SecPath M9000-E-NSQM5FAB08A0
ibevtModuleRt-NSQM5FAB16A0                OBJECT IDENTIFIER ::= { ibevtModuleRouterType 511 } -- SecPath M9000-E-NSQM5FAB16A0
ibevtModuleRt-NSQM5SL16UA0                OBJECT IDENTIFIER ::= { ibevtModuleRouterType 512 } -- SecPath M9000-E-NSQM5SL16UA0
ibevtModuleRt-NSQM5SL16LA0                OBJECT IDENTIFIER ::= { ibevtModuleRouterType 513 } -- SecPath M9000-E-NSQM5SL16LA0
ibevtModuleRt-NSQM2MPU12E0                OBJECT IDENTIFIER ::= { ibevtModuleRouterType 514 } -- SecPath M9000-S-NSQM2MPU12E0
ibevtModuleRt-NSQM2MBFEA0                 OBJECT IDENTIFIER ::= { ibevtModuleRouterType 515 } -- SecPath M9000-S-NSQM2MBFEA0
ibevtModuleRt-NSQM2AC2500HD               OBJECT IDENTIFIER ::= { ibevtModuleRouterType 516 } -- SecPath M9000-S-NSQM2AC2500HD
ibevtModuleRt-NSQM2DC2500                 OBJECT IDENTIFIER ::= { ibevtModuleRouterType 517 } -- SecPath M9000-S-NSQM2DC2500
ibevtModuleRt-NSQM1HTIMGMG2A              OBJECT IDENTIFIER ::= { ibevtModuleRouterType 518 } -- F5080 GM Crypto Module
ibevtModuleRt-NSQM1HTIMGMG2B              OBJECT IDENTIFIER ::= { ibevtModuleRouterType 519 } -- F5080-D GM Crypto Module
ibevtModuleRt-NSQM2V6DSCA0                OBJECT IDENTIFIER ::= { ibevtModuleRouterType 520 } -- SecPath M9000-S-6GW-NSQM2V6DSCA0
ibevtModuleRt-NSQM1AFC2000GDFGA0          OBJECT IDENTIFIER ::= { ibevtModuleRouterType 521 } -- SecPath NSQM1AFC2000GDFGA0
ibevtModuleRt-NSQM2AFC2000GDFGA0          OBJECT IDENTIFIER ::= { ibevtModuleRouterType 522 } -- SecPath NSQM2AFC2000GDFGA0
ibevtModuleRt-NSQM1FWDFGD1-Z              OBJECT IDENTIFIER ::= { ibevtModuleRouterType 523 } -- SecPath NSQM1FWDFGD1
ibevtModuleRt-NSQM1FAB12D0                OBJECT IDENTIFIER ::= { ibevtModuleRouterType 524 } -- SecPath NSQM1FAB12D0
ibevtModuleRt-NSQM1MBFEA0                 OBJECT IDENTIFIER ::= { ibevtModuleRouterType 525 } -- SecPath NSQM1MBFEA0
ibevtModuleRt-NSQM2TG16GP40-Z             OBJECT IDENTIFIER ::= { ibevtModuleRouterType 526 } -- SecPath NSQM2TG16GP40
ibevtModuleRt-NSQM2QG4GP40-Z              OBJECT IDENTIFIER ::= { ibevtModuleRouterType 527 } -- SecPath NSQM2QG4GP40
ibevtModuleRt-NSQM1CGQ20-Z                OBJECT IDENTIFIER ::= { ibevtModuleRouterType 528 } -- SecPath NSQM1CGQ20
ibevtModuleRt-NSQM1TGS32QSSG0-Z           OBJECT IDENTIFIER ::= { ibevtModuleRouterType 529 } -- SecPath NSQM1TGS32QSSG0
ibevtModuleRt-NSQM1AFC2000GDFGA0-Z        OBJECT IDENTIFIER ::= { ibevtModuleRouterType 530 } -- SecPath NSQM1AFC2000GDFGA0
ibevtModuleRt-NSQM5AIASKA1                OBJECT IDENTIFIER ::= { ibevtModuleRouterType 531 } -- SecPath M9000-AI-E- NSQM5AIASKA1
ibevtModuleRt-NSQM1FWEFGA0                OBJECT IDENTIFIER ::= { ibevtModuleRouterType 532 } -- SecPath M9000-NSQM1FMEFGA0
ibevtModuleRt-NS-ADEEMPA0                 OBJECT IDENTIFIER ::= { ibevtModuleRouterType 533 } -- SecPath M9000-AD-NSQM6ADEEMPA0-SecBlade V
ibevtModuleRt-NSQM2QG2TG8A0               OBJECT IDENTIFIER ::= { ibevtModuleRouterType 534 } -- SecPath M9000-AD-NSQM2QG2TG8A0
ibevtModuleRt-NS-ADEEMPB0                 OBJECT IDENTIFIER ::= { ibevtModuleRouterType 535 } -- SecPath M9000-AD-NSQM6ADEEMPB0-SecBlade V
ibevtModuleRt-NSQM2TG16A0                 OBJECT IDENTIFIER ::= { ibevtModuleRouterType 536 } -- SecPath M9000-AD-NSQM2TG16A0
ibevtModuleRt-NSQM6SUP04A0                OBJECT IDENTIFIER ::= { ibevtModuleRouterType 537 } -- SecPath M9000-AD-NSQM6SUP04A0
ibevtModuleRt-NSQM2QG4A0                  OBJECT IDENTIFIER ::= { ibevtModuleRouterType 538 } -- SecPath M9000-AD-NSQM2QG4A0
ibevtModuleRt-NSQM1SUPD0                  OBJECT IDENTIFIER ::= { ibevtModuleRouterType 539 } -- SecPath M9000-NSQM1SUPD0
ibevtModuleRt-NSQM1FAB08E0                OBJECT IDENTIFIER ::= { ibevtModuleRouterType 540 } -- SecPath M9016-V-NSQM1FAB08E0
ibevtModuleRt-NSQM1CGQ4TG24SHA0           OBJECT IDENTIFIER ::= { ibevtModuleRouterType 541 } -- SecPath M9000-NSQM1CGQ4TG24SHA0
ibevtModuleRt-NSQM2MPUF0                  OBJECT IDENTIFIER ::= { ibevtModuleRouterType 542 } -- SecPath M9000-S-V-NSQM2MPUF0
ibevtModuleRt-NSQM2FWDFGD0                OBJECT IDENTIFIER ::= { ibevtModuleRouterType 543 } -- SecPath M9000-S-V-NSQM2FWDFGD0-SecBlade IV
ibevtModuleRt-NSQM2MBFDB0                 OBJECT IDENTIFIER ::= { ibevtModuleRouterType 544 } -- SecPath M9000-S-V-NSQM2MBFDB0
ibevtModuleRt-NSQM2QG2TG8GP4B0            OBJECT IDENTIFIER ::= { ibevtModuleRouterType 545 } -- SecPath M9000系列-NSQM2QG2TG8GP4B0
ibevtModuleRt-NSQM2FAN08B                 OBJECT IDENTIFIER ::= { ibevtModuleRouterType 546 } -- SecPath M9000-S-V-NSQM2FAN08B
ibevtModuleRt-NSQM5TSUP08A0               OBJECT IDENTIFIER ::= { ibevtModuleRouterType 547 } -- SecPath T9000-E8-NSQM5TSUP08A0
ibevtModuleRt-NSQM5TIPSEMPA0              OBJECT IDENTIFIER ::= { ibevtModuleRouterType 548 } -- SecPath T9000-E-NS-IPSEMPA0
ibevtModuleRt-NSQM5AIASKB1                OBJECT IDENTIFIER ::= { ibevtModuleRouterType 549 } -- SecPath M9000-AI-E-NSQM5AIASKB1
ibevtModuleRt-NSQM1G4XS4-Z                OBJECT IDENTIFIER ::= { ibevtModuleRouterType 550 } -- 4-GE Fabric,4-XGE Fabric Interface Module
ibevtModuleRt-NSQM5TIPSEMPB0              OBJECT IDENTIFIER ::= { ibevtModuleRouterType 551 } -- SecPath T9000-E-NS-IPSEMPB0
ibevtModuleRt-NSQM5SUP04A1                OBJECT IDENTIFIER ::= { ibevtModuleRouterType 552 } -- SecPath M9000-E-NSQM5SUP04A1
ibevtModuleRt-NS-FWEMPB1                  OBJECT IDENTIFIER ::= { ibevtModuleRouterType 553 } -- SecPath M9000-E-NSQM5FWEMPB1
ibevtModuleRt-NS-AFC2000EMPB1             OBJECT IDENTIFIER ::= { ibevtModuleRouterType 554 } -- SecPath M9000-E-NSQM5AFC2000EMPB1
ibevtModuleRt-NS-AFC2000EMPA1             OBJECT IDENTIFIER ::= { ibevtModuleRouterType 555 } -- SecPath M9000-E-NSQM5AFC2000EMPA1
ibevtModuleRt-NS-ADEEMPC0                 OBJECT IDENTIFIER ::= { ibevtModuleRouterType 556 } -- SecPath M9000-AD-NSQM6ADEEMPC0-SecBlade V
ibevtModuleRt-NSQM1CGQ6SH0                OBJECT IDENTIFIER ::= { ibevtModuleRouterType 557 } -- SecPath NSQM1CGQ6SH0
ibevtModuleRt-NSQM7SUPB0                  OBJECT IDENTIFIER ::= { ibevtModuleRouterType 558 } -- SecPath M9000-X06-NSQM7SUPB0
ibevtModuleRt-NSQM7FAB06A0                OBJECT IDENTIFIER ::= { ibevtModuleRouterType 559 } -- SecPath M9000-X06-NS-NSQM7FAB06A0
ibevtModuleRt-NSQM7SUPA0                  OBJECT IDENTIFIER ::= { ibevtModuleRouterType 560 } -- SecPath M9000-X10-NSQM7SUPA0
ibevtModuleRt-NSQM7FAB10A0                OBJECT IDENTIFIER ::= { ibevtModuleRouterType 561 } -- SecPath M9000-X10-NSQM7FAB10A0
ibevtModuleRt-FAN-120B-3-A10              OBJECT IDENTIFIER ::= { ibevtModuleRouterType 562 } -- SecPath M9000-X10-FAN-120B-3-A10
ibevtModuleRt-NSQM7MBSHB0                 OBJECT IDENTIFIER ::= { ibevtModuleRouterType 563 } -- SecPath M9000-X-NSQM7MBSHB0
ibevtModuleRt-NSQM7MBSHA0                 OBJECT IDENTIFIER ::= { ibevtModuleRouterType 564 } -- SecPath M9000-X-NSQM7MBSHA0
ibevtModuleRt-NS-FWFFGA0                  OBJECT IDENTIFIER ::= { ibevtModuleRouterType 565 } -- SecPath M9000-X-NS-FWFFGA0
ibevtModuleRt-NS-FWFFGB0                  OBJECT IDENTIFIER ::= { ibevtModuleRouterType 566 } -- SecPath M9000-X-NS-FWFFGB0
ibevtModuleRt-NS-FWFAMA1                  OBJECT IDENTIFIER ::= { ibevtModuleRouterType 567 } -- SecPath NS-FWAAMA0
ibevtModuleRt-NSQM1AIASKA1                OBJECT IDENTIFIER ::= { ibevtModuleRouterType 568 } -- SecPath M9000-NSQM1AIASKA1
ibevtModuleRt-NSQM5TG16B1                 OBJECT IDENTIFIER ::= { ibevtModuleRouterType 569 } -- SecPath M9000-AI-E-NSQM5TG16B1
ibevtModuleRt-NSQM5QG4A1                  OBJECT IDENTIFIER ::= { ibevtModuleRouterType 570 } -- SecPath M9000-AI-E-NSQM5QG4A1
ibevtModuleRt-NSQM5QG2TG8A1               OBJECT IDENTIFIER ::= { ibevtModuleRouterType 571 } -- SecPath M9000-AI-E-NSQM5QG2TG8A1
ibevtModuleRt-NSQM5QG4GP4A1               OBJECT IDENTIFIER ::= { ibevtModuleRouterType 572 } -- SecPath M9000-AI-E-NSQM5QG4GP4A1
ibevtModuleRt-NSQM5TG16A1                 OBJECT IDENTIFIER ::= { ibevtModuleRouterType 573 } -- SecPath M9000-AI-E-NSQM5TG16A1
ibevtModuleRt-NSQM5CGQ2A1                 OBJECT IDENTIFIER ::= { ibevtModuleRouterType 574 } -- SecPath M9000-AI-E-NSQM5CGQ2A1
ibevtModuleRt-NSQM2CGQ2B0                 OBJECT IDENTIFIER ::= { ibevtModuleRouterType 575 } -- SecPath M9000-NSQM2CGQ2B0
ibevtModuleRt-NSQM2MBFEB0                 OBJECT IDENTIFIER ::= { ibevtModuleRouterType 576 } -- SecPath M9000-S-NSQM2MBFEB0
ibevtModuleRt-NS-FWFFGC0                  OBJECT IDENTIFIER ::= { ibevtModuleRouterType 577 } -- SecPath M9000-X-NS-FWFFGC0
ibevtModuleRt-NS-FWFFGD0                  OBJECT IDENTIFIER ::= { ibevtModuleRouterType 578 } -- SecPath M9000-X-NS-FWFFGD0
ibevtModuleRt-NSQM7FWFFGB0                OBJECT IDENTIFIER ::= { ibevtModuleRouterType 579 } -- SecPath M9000-X-NS-FWFFGB0
ibevtModuleBoxNSQM7FAB06B1                OBJECT IDENTIFIER ::= { ibevtModuleRouterType 580 } -- SecPath M9000-AI-X06-NSQM7FAB06B1
ibevtModuleBoxNS-C300-CGQ2TG16B1          OBJECT IDENTIFIER ::= { ibevtModuleRouterType 581 } -- SecPath M9000-AI-X-NS-C300-CGQ2TG16B1
ibevtModuleBoxNS-C300-QG4TG16B1           OBJECT IDENTIFIER ::= { ibevtModuleRouterType 582 } -- SecPath M9000-AI-X-NS-C300-QG4TG16B1
ibevtModuleBoxNS-FWFFGB1                  OBJECT IDENTIFIER ::= { ibevtModuleRouterType 583 } -- SecPath M9000-AI-X-NS-FWFFGB1
ibevtModuleBoxNSQM7FAB10B1                OBJECT IDENTIFIER ::= { ibevtModuleRouterType 584 } -- SecPath M9000-AI-X10-NSQM7FAB10B1
ibevtModuleBoxNSQM7MBSHC1                 OBJECT IDENTIFIER ::= { ibevtModuleRouterType 585 } -- SecPath M9000-AI-X-NSQM7MBSHC1
ibevtModuleBoxNSQM7SUPC1                  OBJECT IDENTIFIER ::= { ibevtModuleRouterType 586 } -- SecPath M9000-AI-X-NSQM7SUPC1
ibevtModuleBoxNSQM7SUPD1                  OBJECT IDENTIFIER ::= { ibevtModuleRouterType 587 } -- SecPath M9000-AI-X-NSQM7SUPD1
ibevtModuleBoxNS-C300-TG24B1              OBJECT IDENTIFIER ::= { ibevtModuleRouterType 588 } -- SecPath M9000-AI-X-NS-C300-TG24B1
ibevtModuleBoxNS-FWFFGA1                  OBJECT IDENTIFIER ::= { ibevtModuleRouterType 589 } -- SecPath M9000-AI-X-NS-FWFFGA1
ibevtModuleBoxNS-C600-CGQ6B1              OBJECT IDENTIFIER ::= { ibevtModuleRouterType 590 } -- SecPath M9000-AI-X-NS-C600-CGQ6B1
ibevtModuleBoxNS-FWFFGC1                  OBJECT IDENTIFIER ::= { ibevtModuleRouterType 591 } -- SecPath M9000-AI-X-NS-FWFFGC1
ibevtModuleBoxNS-FWFFGD1                  OBJECT IDENTIFIER ::= { ibevtModuleRouterType 592 } -- SecPath M9000-AI-X-NS-FWFFGD1
ibevtModuleBoxNS-FWFFGE1                  OBJECT IDENTIFIER ::= { ibevtModuleRouterType 593 } -- SecPath M9000-AI-X-NS-FWFFGE1
ibevtModuleRt-NSQM7MBSHC0                 OBJECT IDENTIFIER ::= { ibevtModuleRouterType 594 } -- SecPath L5000-AD930-NSQM7MBSHC0
ibevtModuleRt-NS-ADEFFGA0                 OBJECT IDENTIFIER ::= { ibevtModuleRouterType 595 } -- SecPath L5000-AD930-NSQM7ADEFGA0-SecBlade VI
ibevtModuleRt-NS-C300-QG4TG16B0           OBJECT IDENTIFIER ::= { ibevtModuleRouterType 596 } -- SecPath L5000-AD-NSQM7QG4TG16B0
ibevtModuleRt-NSQM7SUPC0                  OBJECT IDENTIFIER ::= { ibevtModuleRouterType 597 } -- SecPath L5000-AD930-NSQM7SUPC0
ibevtModuleRt-NS-FWFAMA1-CN               OBJECT IDENTIFIER ::= { ibevtModuleRouterType 598 } -- SecPath M9000-X-NSQM7FWFAMA1-CN-SecBlade VI
ibevtModuleRt-NSC800CGQ8A0                OBJECT IDENTIFIER ::= { ibevtModuleRouterType 599 } -- SecPath M9000-X-NSQM7CGQ8A0

-- 600 to 799 reserved for voice router--
ibevtModuleRt-VG-8fxs                     OBJECT IDENTIFIER ::= { ibevtModuleRouterType 600 } -- 8 Port Foreign Exchange Station module
ibevtModuleRt-VG-24fxs                    OBJECT IDENTIFIER ::= { ibevtModuleRouterType 601 } -- 24 Port Foreign Exchange Station module
ibevtModuleRt-VG-24fxs24fxo               OBJECT IDENTIFIER ::= { ibevtModuleRouterType 602 } -- 24 Port Foreign Exchange Station and 24 Port Foreign Exchange Office module
ibevtModuleRt-VG-MPU                      OBJECT IDENTIFIER ::= { ibevtModuleRouterType 603 } -- Media Processing Unit
ibevtModuleRt-MIM-VCX-CONNECT-P-3C        OBJECT IDENTIFIER ::= { ibevtModuleRouterType 604 } -- MIM VCX Connect Primary module
ibevtModuleRt-MIM-VCX-CONNECT-S-3C        OBJECT IDENTIFIER ::= { ibevtModuleRouterType 605 } -- MIM VCX Connect Secondary module
ibevtModuleRt-MIM-VCX-3C                  OBJECT IDENTIFIER ::= { ibevtModuleRouterType 606 } -- MIM VCX Enterprise module
ibevtModuleRt-VNIC-VMXNET3                OBJECT IDENTIFIER ::= { ibevtModuleRouterType 607 } -- 1 Port Gigabit Ethernet interface virtual VMXNET3 module
ibevtModuleRt-VNIC-E1000                  OBJECT IDENTIFIER ::= { ibevtModuleRouterType 608 } -- 1 Port Gigabit Ethernet interface virtual E1000 module
ibevtModuleRt-VNIC-VIRTIO                 OBJECT IDENTIFIER ::= { ibevtModuleRouterType 609 } -- 1 Port Gigabit Ethernet interface virtual VIRTIO module
ibevtModuleRt-VNIC-RTL8139                OBJECT IDENTIFIER ::= { ibevtModuleRouterType 610 } -- 1 Port Gigabit Ethernet interface virtual RTL8139 module
ibevtModuleRt-VNIC-IXGBEVF                OBJECT IDENTIFIER ::= { ibevtModuleRouterType 611 } -- 1 Port Ten-Gigabit Ethernet interface virtual IXGBEVF module
ibevtModuleRt-IXGBE-2XGE                  OBJECT IDENTIFIER ::= { ibevtModuleRouterType 612 } -- 2 Port Ten-Gigabit Ethernet interface IXGBE module
ibevtModuleRt-TG3-4GE                     OBJECT IDENTIFIER ::= { ibevtModuleRouterType 613 } -- 4 Port Gigabit Ethernet interface TG3 module
ibevtModuleRt-MPUV16                      OBJECT IDENTIFIER ::= { ibevtModuleRouterType 614 } -- Main Processing Unit over virtual machine
ibevtModuleRt-MPUP6                       OBJECT IDENTIFIER ::= { ibevtModuleRouterType 615 } -- Main Processing Unit over physical machine
ibevtModuleRt-IGB-1GE                     OBJECT IDENTIFIER ::= { ibevtModuleRouterType 616 } -- 1 Port Gigabit Ethernet interface IGB module
ibevtModuleRt-IGB-2GE                     OBJECT IDENTIFIER ::= { ibevtModuleRouterType 617 } -- 2 Port Gigabit Ethernet interface IGB module
ibevtModuleRt-IGB-4GE                     OBJECT IDENTIFIER ::= { ibevtModuleRouterType 618 } -- 4 Port Gigabit Ethernet interface IGB module
ibevtModuleRt-VLNS1000                    OBJECT IDENTIFIER ::= { ibevtModuleRouterType 619 } -- Virtual L2TP Network Server over virtual machine
ibevtModuleRt-VLNS2000                    OBJECT IDENTIFIER ::= { ibevtModuleRouterType 620 } -- Virtual L2TP Network Server over physical machine
ibevtModuleRt-NS-MIM-GP4A2                OBJECT IDENTIFIER ::= { ibevtModuleRouterType 621 } -- 4 Port GigabitEthernet Interface Module
ibevtModuleRt-NS-MIM-GT4PFCA2             OBJECT IDENTIFIER ::= { ibevtModuleRouterType 622 } -- 4 Port GigabitEthernet Interface Module
ibevtModuleRt-NS-NIM-TG6A2                OBJECT IDENTIFIER ::= { ibevtModuleRouterType 623 } -- 6 Port Ten-GigabitEthernet Interface Module
ibevtModuleRt-NS-SIM-GT4PFCA2             OBJECT IDENTIFIER ::= { ibevtModuleRouterType 624 } -- 4 Port GigabitEthernet Interface Module
ibevtModuleRt-NS-NIM-TG6A-Z               OBJECT IDENTIFIER ::= { ibevtModuleRouterType 625 } -- 6 Port Ten-GigabitEthernet Interface Module
ibevtModuleRt-DH-SACG8000-H-4SFP4SFPPlus  OBJECT IDENTIFIER ::= { ibevtModuleRouterType 626 } -- 4-GE Fabric,4-XGE Fabric Interface Module
ibevtModuleRt-DH-SACG8000-H-8SFPPlus      OBJECT IDENTIFIER ::= { ibevtModuleRouterType 627 } -- 8 Port Ten-GigabitEthernet Interface Module
ibevtModuleRt-DH-SACG8000-H-4PFC          OBJECT IDENTIFIER ::= { ibevtModuleRouterType 628 } -- 4 Port GigabitEthernet Interface Module
ibevtModuleRt-DH-SACG8000-H-8SFP          OBJECT IDENTIFIER ::= { ibevtModuleRouterType 629 } -- 8 Port Fabric GigabitEthernet Interface Module
ibevtModuleRt-DH-SACG8000-H-8GE           OBJECT IDENTIFIER ::= { ibevtModuleRouterType 630 } -- 8 Port Gigabit Ethernet interface Module
ibevtModuleRt-DH-NGFW-4SFP                OBJECT IDENTIFIER ::= { ibevtModuleRouterType 631 } -- 4 Port Fabric GigabitEthernet Interface Module
ibevtModuleRt-DH-NGFW-6SFPPlus            OBJECT IDENTIFIER ::= { ibevtModuleRouterType 632 } -- 6 Port Ten-GigabitEthernet Interface Module
ibevtModuleRt-NIC-ADC-GE-TX8              OBJECT IDENTIFIER ::= { ibevtModuleRouterType 633 } -- 8 Port GigabitEthernet Interface Module
ibevtModuleRt-NIC-ADC-GE-SFP4             OBJECT IDENTIFIER ::= { ibevtModuleRouterType 634 } -- 4 Port Fabric GigabitEthernet Interface Module
ibevtModuleRt-NIC-ADC-10GE-SFPP6          OBJECT IDENTIFIER ::= { ibevtModuleRouterType 635 } -- 6 Port Ten-GigabitEthernet Interface Module
ibevtModuleRt-NIC-ADC-10GE-SFPP8          OBJECT IDENTIFIER ::= { ibevtModuleRouterType 636 } -- 8 Port Ten-GigabitEthernet Interface Module
ibevtModuleRt-AIS-SEC-4SFP                OBJECT IDENTIFIER ::= { ibevtModuleRouterType 637 } -- 4 Port Fabric GigabitEthernet Interface
ibevtModuleRt-AIS-SEC-8GE                 OBJECT IDENTIFIER ::= { ibevtModuleRouterType 638 } -- 8 Port Gigabit Ethernet interface Module
ibevtModuleRt-AIS-SEC-GMA                 OBJECT IDENTIFIER ::= { ibevtModuleRouterType 639 } -- AIS GM Crypto Module
ibevtModuleRt-AIS-SEC-8SFP                OBJECT IDENTIFIER ::= { ibevtModuleRouterType 640 } -- 8 Port Fabric GigabitEthernet Interface
ibevtModuleRt-AIS-SEC-6SFPP               OBJECT IDENTIFIER ::= { ibevtModuleRouterType 641 } -- 6 Port Ten-GigabitEthernet Interface Module
ibevtModuleRt-AIS-SEC-GMC                 OBJECT IDENTIFIER ::= { ibevtModuleRouterType 642 } -- AIS GM Crypto Module
ibevtModuleRt-AIS-SEC-4PFC                OBJECT IDENTIFIER ::= { ibevtModuleRouterType 643 } -- 4 Port GigabitEthernet Interface Module
ibevtModuleRt-AIS-SEC-8SFPP               OBJECT IDENTIFIER ::= { ibevtModuleRouterType 644 } -- 8 Port Ten-GigabitEthernet Interface Module
ibevtModuleRt-AIS-SEC-2U-4PFC             OBJECT IDENTIFIER ::= { ibevtModuleRouterType 645 } -- 4 Port GigabitEthernet Interface Module
ibevtModuleRt-AIS-SEC-SEM100              OBJECT IDENTIFIER ::= { ibevtModuleRouterType 646 } -- 2-Port 10/100/1000BASE-T and 2-Port 1000BASE-X SFP Interface Module
ibevtModuleRt-AIS-SEC-2QSFPP              OBJECT IDENTIFIER ::= { ibevtModuleRouterType 647 } -- 2 Port Forty-GigabitEthernet Interface Module
ibevtModuleRt-AIS-SEC-4SFP4SFPP           OBJECT IDENTIFIER ::= { ibevtModuleRouterType 648 } -- 4-GE Fabric,4-XGE Fabric Interface Module
ibevtModuleRt-AIS-SEC-SEM200              OBJECT IDENTIFIER ::= { ibevtModuleRouterType 649 } -- 2-Port 10/100/1000BASE-T and 2-Port 1000BASE-X SFP Interface Module
ibevtModuleRt-NSFWFFGC0-CONTEXT           OBJECT IDENTIFIER ::= { ibevtModuleRouterType 650 } -- SecPath M9000-X-NS-FWFFGC0
ibevtModuleRt-NSFWFFGD0-CONTEXT           OBJECT IDENTIFIER ::= { ibevtModuleRouterType 651 } -- SecPath M9000-X-NS-FWFFGD0
ibevtModuleRt-NSFWFFGC1-CONTEXT           OBJECT IDENTIFIER ::= { ibevtModuleRouterType 652 } -- SecPath M9000-AI-X-NS-FWFFGC1
ibevtModuleRt-NSFWFFGD1-CONTEXT           OBJECT IDENTIFIER ::= { ibevtModuleRouterType 653 } -- SecPath M9000-AI-X-NS-FWFFGD1
ibevtModuleRt-NSFWFFGE1-CONTEXT           OBJECT IDENTIFIER ::= { ibevtModuleRouterType 654 } -- SecPath M9000-AI-X-NS-FWFFGE1
ibevtModuleRt-NSFWFFGA0-CONTEXT           OBJECT IDENTIFIER ::= { ibevtModuleRouterType 655 } -- SecPath M9000-X-BLADE6-A-CONTEXT
ibevtModuleRt-NSFWFFGB0-CONTEXT           OBJECT IDENTIFIER ::= { ibevtModuleRouterType 656 } -- SecPath M9000-X-BLADE6-B-CONTEXT
ibevtModuleRt-NS-NIM-GT4GP4A-Z            OBJECT IDENTIFIER ::= { ibevtModuleRouterType 657 } -- 4 Port Fabric and 4 Port Copper GigabitEthernet Interface
ibevtModuleRt-NS-ADEGMFAMA0               OBJECT IDENTIFIER ::= { ibevtModuleRouterType 658 } -- SecPath M9000-AD-NSQM7ADEGMFAMA0-SecBlade VI
ibevtModuleRt-NS-TIM-GMG2A                OBJECT IDENTIFIER ::= { ibevtModuleRouterType 659 } -- F5080 GM Crypto Module
ibevtModuleRt-NS-SecCenter-CSAP-SA-C      OBJECT IDENTIFIER ::= { ibevtModuleRouterType 660 } -- 2-Port 10/100/1000BASE-T and 2-Port 1000BASE-X SFP Interface Module
ibevtModuleBoxNSQM8FAB10A1                OBJECT IDENTIFIER ::= { ibevtModuleRouterType 661 } -- F5000-X10-NSQM8FAB10A1
ibevtModuleBoxNSQM8FAB06A1                OBJECT IDENTIFIER ::= { ibevtModuleRouterType 662 } -- F5000-X06-NSQM8FAB06A1
ibevtModuleBoxNS-FWFFGA1-Z                OBJECT IDENTIFIER ::= { ibevtModuleRouterType 663 } -- F5000-X-NSQM8FWFFGA1-SecBlade VI
ibevtModuleBoxNS-FWFFGB1-Z                OBJECT IDENTIFIER ::= { ibevtModuleRouterType 664 } -- F5000-X-NSQM8FWFFGB1-SecBlade VI
ibevtModuleBoxNSQM8MBSHA1                 OBJECT IDENTIFIER ::= { ibevtModuleRouterType 665 } -- F5000-X-NSQM8MBSHA1
ibevtModuleBoxNS-C300-TG24A1-Z            OBJECT IDENTIFIER ::= { ibevtModuleRouterType 666 } -- F5000-X-NSQM8TG24A1-24
ibevtModuleBoxNS-C300-CGQ2TG16A1-Z        OBJECT IDENTIFIER ::= { ibevtModuleRouterType 667 } -- F5000-X-NSQM8CGQ2TG16A1-2
ibevtModuleBoxNS-C300-QG4TG16A1-Z         OBJECT IDENTIFIER ::= { ibevtModuleRouterType 668 } -- F5000-X-NSQM8QG4TG16A1-4
ibevtModuleBoxNS-C600-CGQ6A1-Z            OBJECT IDENTIFIER ::= { ibevtModuleRouterType 669 } -- F5000-X-NSQM8CGQ6A1-6
ibevtModuleBoxFAN-120B-3-A10-Z            OBJECT IDENTIFIER ::= { ibevtModuleRouterType 670 } -- F5000-X-NSQM8FAN10A
ibevtModuleBoxFAN-120B-2-A6-Z             OBJECT IDENTIFIER ::= { ibevtModuleRouterType 671 } -- F5000-X-NSQM8FAN06A
ibevtModuleBoxPSR2400-54A-CN              OBJECT IDENTIFIER ::= { ibevtModuleRouterType 672 } -- F5000-X-NSQM8PSRA2400
ibevtModuleBoxPSR2400-54D-CN              OBJECT IDENTIFIER ::= { ibevtModuleRouterType 673 } -- F5000-X-NSQM8PSRD2400
ibevtModuleBoxPSR3000-54AHD-CN            OBJECT IDENTIFIER ::= { ibevtModuleRouterType 674 } -- F5000-X-NSQM8PSRD3000
ibevtModuleBoxNSQM8SUPA1                  OBJECT IDENTIFIER ::= { ibevtModuleRouterType 675 } -- F5000-X-NSQM8SUPA1
ibevtModuleBoxNSQM8SUPB1                  OBJECT IDENTIFIER ::= { ibevtModuleRouterType 676 } -- F5000-X-NSQM8SUPB1
ibevtModuleBoxNSQM8SUPA1-Z-CN             OBJECT IDENTIFIER ::= { ibevtModuleRouterType 677 } -- F5000-X-NSQM8SUPA1-Z-CN
ibevtModuleBoxNSQM8SUPB1-Z-CN             OBJECT IDENTIFIER ::= { ibevtModuleRouterType 678 } -- F5000-X-NSQM8SUPB1-Z-CN
ibevtModuleBox-NSFWFAMB1                  OBJECT IDENTIFIER ::= { ibevtModuleRouterType 679 } -- SecPath M9000-X-NSFWFAMB1
ibevtModuleRt-NSQM5SUP08A0-CN             OBJECT IDENTIFIER ::= { ibevtModuleRouterType 680 } -- SecPath M9000-E8-NSQM5SUP08A0-CN
ibevtModuleRt-NSQM5AFCEMPC0               OBJECT IDENTIFIER ::= { ibevtModuleRouterType 681 } -- SecPath M9000-E8 SecBlade V-NSQM5AFCEMPC0
ibevtModuleRt-NSQM7SUPC0-CN               OBJECT IDENTIFIER ::= { ibevtModuleRouterType 682 } -- SecPath L5000-AD930-NSQM7SUPC0-CN
ibevtModuleRt-NSQ1F1X86BA1                OBJECT IDENTIFIER ::= { ibevtModuleRouterType 684 } -- 2-Port 10/100/1000BASE-T and 2-Port 1000BASE-X SFP Interface Module
ibevtModuleRt-NSQM6SUP04B1                OBJECT IDENTIFIER ::= { ibevtModuleRouterType 685 } -- SecPath M9000-CN04-NSQM6SUP04B1
ibevtModuleRt-NSQM6TG24A1                 OBJECT IDENTIFIER ::= { ibevtModuleRouterType 686 } -- SecPath M9000-CN04-NSQM6TG24A1-24
ibevtModuleRt-NSQM6CGQ6A1                 OBJECT IDENTIFIER ::= { ibevtModuleRouterType 687 } -- SecPath M9000-CN04-NSQM6CGQ6A1-6
ibevtModuleRt-NSQM6CGQ2TG16A1             OBJECT IDENTIFIER ::= { ibevtModuleRouterType 688 } -- SecPath M9000-CN04-NSQM6CGQ2TG16A1-2
ibevtModuleRt-NS-ADEFXA0-CN               OBJECT IDENTIFIER ::= { ibevtModuleRouterType 689 } -- SecPath L5000-CN SecBlade VI Application Dilevery Engine A Module(X) (CN)
ibevtModuleRt-NSQM7SUPB0-CN               OBJECT IDENTIFIER ::= { ibevtModuleRouterType 690 } -- SecPath M9000-X-NSQM7SUPB0-CN
ibevtModuleRt-NSQM7MBCTA0-CN              OBJECT IDENTIFIER ::= { ibevtModuleRouterType 691 } -- SecPath M9000-X-NSQ1M9XMBCTCA
ibevtModuleRt-NSQ1M9XFAB06A               OBJECT IDENTIFIER ::= { ibevtModuleRouterType 692 } -- SecPath M9000-X-NSQ1M9XFAB06A
ibevtModuleRt-C500-CGQ4TG16A0             OBJECT IDENTIFIER ::= { ibevtModuleRouterType 693 } -- M9000-E-NSQ1M9ECGQ4TG16A
ibevtModuleRt-NS-C800-CGQ8A0              OBJECT IDENTIFIER ::= { ibevtModuleRouterType 694 } -- M9000-E-NSQ1M9ECGQ8A
ibevtModuleRt-LSWM1AC1600                 OBJECT IDENTIFIER ::= { ibevtModuleRouterType 695 } -- S9820-LSWM1AC1600-1600W
ibevtModuleRt-LSEM1PSR2000DB              OBJECT IDENTIFIER ::= { ibevtModuleRouterType 696 } -- S10500X-G-LSEM1PSR2000DB-2000W
ibevtModuleRt-NS-FWEMPB2                  OBJECT IDENTIFIER ::= { ibevtModuleRouterType 697 } -- SecPath M9000-AK001-NSQM1FWEMPB2-SecBlade V
ibevtModuleRt-NSQM1SUP04A2                OBJECT IDENTIFIER ::= { ibevtModuleRouterType 698 } -- SecPath M9000-AK001-NSQM1SUP04A2
ibevtModuleRt-NS-C100-TG16B2              OBJECT IDENTIFIER ::= { ibevtModuleRouterType 699 } -- SecPath M9000-AK001-NSQM1TG16B2
ibevtModuleRt-NSQM5TTG24A0                OBJECT IDENTIFIER ::= { ibevtModuleRouterType 700 } -- SecPath M9000-NSQM5TTG24A0
ibevtModuleRt-NS-C300-TG24A2              OBJECT IDENTIFIER ::= { ibevtModuleRouterType 701 } -- SecPath M9000-NSQM5TTG24A2
ibevtModuleRt-NS-C300-TG24A3              OBJECT IDENTIFIER ::= { ibevtModuleRouterType 702 } -- SecPath M9000-NSQM5TTG24A3
ibevtModuleRt-NS-C600-CGQ6A2              OBJECT IDENTIFIER ::= { ibevtModuleRouterType 703 } -- SecPath M9000-NSQM5TCGQ6A2
ibevtModuleRt-NS-C600-CGQ6A3              OBJECT IDENTIFIER ::= { ibevtModuleRouterType 704 } -- SecPath M9000-NSQM5TCGQ6A3
ibevtModuleRt-NSQM5TSUP08A0-CN            OBJECT IDENTIFIER ::= { ibevtModuleRouterType 705 } -- SecPath T9000-E8-CN-NSQM5TSUP08A0-CN
ibevtModuleRt-NSQM5TSUP08B0-CN            OBJECT IDENTIFIER ::= { ibevtModuleRouterType 706 } -- SecPath T9000-E8-B-CN-NSQM5TSUP08B0-CN
ibevtModuleRt-NS-IPSEMPA1                 OBJECT IDENTIFIER ::= { ibevtModuleRouterType 707 } -- SecPath T9000-E-NSQM5TIPSEMPA1-SecBlade V
ibevtModuleRt-NS-IPSEMPB1                 OBJECT IDENTIFIER ::= { ibevtModuleRouterType 708 } -- SecPath T9000-E-NSQM5TIPSEMPB1-SecBlade V
ibevtModuleRt-NS-IPSEMPC1                 OBJECT IDENTIFIER ::= { ibevtModuleRouterType 709 } -- SecPath T9000-E-NSQM5TIPSEMPC1-SecBlade V
ibevtModuleRt-NSQM5TSUP04A0               OBJECT IDENTIFIER ::= { ibevtModuleRouterType 710 } -- SecPath T9000-E4-NSQM5TSUP04A0
ibevtModuleRt-NSQM5TSUP08B0               OBJECT IDENTIFIER ::= { ibevtModuleRouterType 711 } -- SecPath T9000-E8-B-NSQM5TSUP08B0
ibevtModuleRt-NS-C300-TG24A4              OBJECT IDENTIFIER ::= { ibevtModuleRouterType 712 } -- SecPath M9000-X-NSQM7TG24A4
ibevtModuleRt-NS-C300-TG24A5              OBJECT IDENTIFIER ::= { ibevtModuleRouterType 713 } -- SecPath M9000-X-NSQM7TG24A5
ibevtModuleRt-NSQM7CGQ6A0                 OBJECT IDENTIFIER ::= { ibevtModuleRouterType 714 } -- SecPath M9000-X-NSQM7CGQ6A0
ibevtModuleRt-NS-C800-CGQ8A1              OBJECT IDENTIFIER ::= { ibevtModuleRouterType 715 } -- SecPath M9000-X-NSQM7CGQ8A1
ibevtModuleRt-NSQM7SUPD0-CN               OBJECT IDENTIFIER ::= { ibevtModuleRouterType 716 } -- SecPath M9000-X-NSQM7SUPD0-CN
ibevtModuleRt-NSQM7SUPD0                  OBJECT IDENTIFIER ::= { ibevtModuleRouterType 717 } -- SecPath M9000-X-NSQM7SUPD0
ibevtModuleRt-NS-FWEMPB2-CONTEXT          OBJECT IDENTIFIER ::= { ibevtModuleRouterType 718 } -- SecPath M9000-AK001-NSQM1FWEMPB2-SecBlade V-CONTEXT
ibevtModuleRt-NS-IPSEMPA1-CONTEXT         OBJECT IDENTIFIER ::= { ibevtModuleRouterType 719 } -- SecPath T9000-E-NSQM5TIPSEMPA1-SecBlade V-CONTEXT
ibevtModuleRt-NS-IPSEMPB1-CONTEXT         OBJECT IDENTIFIER ::= { ibevtModuleRouterType 720 } -- SecPath T9000-E-NSQM5TIPSEMPB1-SecBlade V-CONTEXT
ibevtModuleRt-NS-IPSEMPC1-CONTEXT         OBJECT IDENTIFIER ::= { ibevtModuleRouterType 721 } -- SecPath T9000-E-NSQM5TIPSEMPC1-SecBlade V-CONTEXT
ibevtModuleRt-NSQM7SUPA0-CN             OBJECT IDENTIFIER ::= { ibevtModuleRouterType 722 } -- SecPath M9000-X-NSQM7SUPA0-CN
ibevtModuleRt-NS-ADEEMPC1                 OBJECT IDENTIFIER ::= { ibevtModuleRouterType 723 } -- SecPath M9000-AD-NSQM6ADEEMPC1-SecBlade V
--
-- 800 to 999 reserved for normal routers part II
--
ibevtModuleRt-SIC-4GSW                    OBJECT IDENTIFIER ::= { ibevtModuleRouterType 800 } -- 4-Port 10M/100M/1000MBASE-T Ethernet L2 Switch Interface SIC-Module
ibevtModuleRt-SIC-4GSWP                   OBJECT IDENTIFIER ::= { ibevtModuleRouterType 801 } -- 4-Port 10M/100M/1000MBASE-T(WITH POE) Ethernet L2 Switch Interface SIC-Module
ibevtModuleRt-SIC-1GEC-V2                 OBJECT IDENTIFIER ::= { ibevtModuleRouterType 802 } -- 1-Port Combo Gigabit Ethernet Interface SIC-Module
ibevtModuleRt-4G-LTE-ATT                  OBJECT IDENTIFIER ::= { ibevtModuleRouterType 803 } -- 1 Port 4G-LTE-ATT-Cellular Interface Adapter Card
ibevtModuleRt-4G-TD-LTE                   OBJECT IDENTIFIER ::= { ibevtModuleRouterType 804 } -- 1 Port 4G-TD-LTE-Cellular Interface Adapter Card
ibevtModuleRt-FIP-240                     OBJECT IDENTIFIER ::= { ibevtModuleRouterType 805 } -- Flexible Interface Platform 240
ibevtModuleRt-8GBP-V2                     OBJECT IDENTIFIER ::= { ibevtModuleRouterType 806 } -- 8-Port GigaBit Ethernet Optical Interface Module(SFP) V2
ibevtModuleRt-HMIM-CNDE                   OBJECT IDENTIFIER ::= { ibevtModuleRouterType 807 } -- CNDE Crypto Engine HMIM-Module
ibevtModuleRt-4G-LTE-Mobile               OBJECT IDENTIFIER ::= { ibevtModuleRouterType 808 } -- 1 Port 4G-LTE-Mobile-Cellular Interface Adapter Card
ibevtModuleRt-SIC-4G-LTE-M                OBJECT IDENTIFIER ::= { ibevtModuleRouterType 809 } -- 1 Port 4G-LTE/TD-SCDMA/WCDMA Cellular Interface SIC-Module
ibevtModuleRt-CRSE-X3                     OBJECT IDENTIFIER ::= { ibevtModuleRouterType 810 } -- Carrier Route Switch Engine X3
ibevtModuleRt-CFIP-300                    OBJECT IDENTIFIER ::= { ibevtModuleRouterType 811 } -- Carrier Flexible Interface Platform 300
ibevtModuleRt-CFIP-310                    OBJECT IDENTIFIER ::= { ibevtModuleRouterType 812 } -- Carrier Flexible Interface Platform 310
ibevtModuleRt-CSAP-4EXP                   OBJECT IDENTIFIER ::= { ibevtModuleRouterType 813 } -- Carrier 4-Port 10GBASE-R/W Ethernet Optical Interface Module(SFP+)
ibevtModuleRt-RSU                         OBJECT IDENTIFIER ::= { ibevtModuleRouterType 814 } -- Route Switch Unit
ibevtModuleRt-CFIP-610                    OBJECT IDENTIFIER ::= { ibevtModuleRouterType 815 } -- Carrier Flexible Interface Platform 610
ibevtModuleRt-2EXP                        OBJECT IDENTIFIER ::= { ibevtModuleRouterType 816 } -- 2-Port 10GBASE-R/W Ethernet Optical Interface Module(SFP+)
ibevtModuleRt-16GBP                       OBJECT IDENTIFIER ::= { ibevtModuleRouterType 817 } -- 16-Port Gigabit Ethernet Optical Interface Module(SFP)
ibevtModuleRt-CFIP-240                    OBJECT IDENTIFIER ::= { ibevtModuleRouterType 818 } -- Carrier Flexible Interface Platform 240
ibevtModuleRt-RSE-X3                      OBJECT IDENTIFIER ::= { ibevtModuleRouterType 819 } -- Route Switch Engine X3
ibevtModuleRt-SAP-8EXP                    OBJECT IDENTIFIER ::= { ibevtModuleRouterType 820 } -- 8-Port 10GBASE-R/W Ethernet Optical Interface Module(SFP+)
ibevtModuleRt-SAP-16EXP                   OBJECT IDENTIFIER ::= { ibevtModuleRouterType 821 } -- 16-Port 10GBASE-R/W Ethernet Optical Interface Module(SFP+)
ibevtModuleRt-PU1P                        OBJECT IDENTIFIER ::= { ibevtModuleRouterType 822 } -- 1-Port 10G POS/RPR Interface Module(XFP)
ibevtModuleRt-RSU100                      OBJECT IDENTIFIER ::= { ibevtModuleRouterType 823 } -- Router Switch Unit 100
ibevtModuleRt-SAP-2QGP                    OBJECT IDENTIFIER ::= { ibevtModuleRouterType 824 } -- 2-Port 40GBASE Ethernet Optical Interface Module(QSFP+)
ibevtModuleRt-CSFE-X1                     OBJECT IDENTIFIER ::= { ibevtModuleRouterType 825 } -- Carrier Switch Fabric Engine X1
ibevtModuleRt-RIC-4GEE                    OBJECT IDENTIFIER ::= { ibevtModuleRouterType 826 } -- 4-Port 10M/100M/1000MBASE-T Ethernet Interface RIC-Module
ibevtModuleRt-RIC-4GEF                    OBJECT IDENTIFIER ::= { ibevtModuleRouterType 827 } -- 4-Port 1000M Base-F Optical Ethernet Interface RIC-Module
ibevtModuleRt-RIC-8GEE                    OBJECT IDENTIFIER ::= { ibevtModuleRouterType 828 } -- 8-Port 10M/100M/1000MBASE-T Ethernet Interface RIC-Module
ibevtModuleRt-RIC-8GEF                    OBJECT IDENTIFIER ::= { ibevtModuleRouterType 829 } -- 8-Port 1000M Base-F Optical Ethernet Interface RIC-Module
ibevtModuleRt-RIC-1XGEF                   OBJECT IDENTIFIER ::= { ibevtModuleRouterType 830 } -- 1-Port Ten-GigabitEthernet Optical Interface RIC-Module
ibevtModuleRt-HMIM-1E1POS                 OBJECT IDENTIFIER ::= { ibevtModuleRouterType 831 } -- 1 PORT E1 Interface HMIM-Module
ibevtModuleRt-DHMIM-1DM                   OBJECT IDENTIFIER ::= { ibevtModuleRouterType 832 } -- 1 PORT E1 Interface DHMIM-Module
ibevtModuleRt-DHMIM-1E1POS1DM             OBJECT IDENTIFIER ::= { ibevtModuleRouterType 833 } -- 1 PORT E1 Interface DHMIM-Module
ibevtModuleRt-RPE-X3                      OBJECT IDENTIFIER ::= { ibevtModuleRouterType 834 } -- Route Processing Engine X3
ibevtModuleRt-CRPE-X3                     OBJECT IDENTIFIER ::= { ibevtModuleRouterType 835 } -- Carrier Route Processing Engine X3
ibevtModuleRt-SAP-28GE                    OBJECT IDENTIFIER ::= { ibevtModuleRouterType 836 } -- 16-Port SFP and 12-Port Combo GE Module
ibevtModuleRt-SAP-20GE2XP                 OBJECT IDENTIFIER ::= { ibevtModuleRouterType 837 } -- 16-Port SFP 4-Port Combo GE and 2-Port 10GE Module
ibevtModuleRt-SFE-L1                      OBJECT IDENTIFIER ::= { ibevtModuleRouterType 838 } -- Switch Fabric Engine L1
ibevtModuleRt-FIP-640                     OBJECT IDENTIFIER ::= { ibevtModuleRouterType 839 } -- Flexible Interface Platform 640
ibevtModuleRt-HMIM-8GSWF                  OBJECT IDENTIFIER ::= { ibevtModuleRouterType 840 } -- 8-Port 1000M Base-F Optical Ethernet L2 Switch Interface HMIM_Module, including 4 Combo Ports
ibevtModuleRt-HMIM-8E1T1                  OBJECT IDENTIFIER ::= { ibevtModuleRouterType 841 } -- 8-port E1/CE1/T1/CT1/PRI HMIM Module
ibevtModuleRt-HMIM-4E1T1                  OBJECT IDENTIFIER ::= { ibevtModuleRouterType 842 } -- 4-port E1/CE1/T1/CT1/PRI HMIM Module
ibevtModuleRt-HMIM-2E1T1                  OBJECT IDENTIFIER ::= { ibevtModuleRouterType 843 } -- 2-port E1/CE1/T1/CT1/PRI HMIM Module
ibevtModuleRt-HMIM-8E1T1-F                OBJECT IDENTIFIER ::= { ibevtModuleRouterType 844 } -- 8-port E1/T1/Fractional E1/T1 HMIM Module
ibevtModuleRt-HMIM-4E1T1-F                OBJECT IDENTIFIER ::= { ibevtModuleRouterType 845 } -- 4-port E1/T1/Fractional E1/T1 HMIM Module
ibevtModuleRt-HMIM-2E1T1-F                OBJECT IDENTIFIER ::= { ibevtModuleRouterType 846 } -- 2-port E1/T1/Fractional E1/T1 HMIM Module
ibevtModuleRt-SIC-3G-HSPA-V2              OBJECT IDENTIFIER ::= { ibevtModuleRouterType 847 } -- 1 Port HSPA-Cellular Interface SIC-Module V2
ibevtModuleRt-SIC-4GSWF                   OBJECT IDENTIFIER ::= { ibevtModuleRouterType 848 } -- 4-Port 1000M Base-F Optical Ethernet L2 Switch Interface SIC-Module
ibevtModuleRt-SIC-4G-LTE-G-V2             OBJECT IDENTIFIER ::= { ibevtModuleRouterType 849 } -- 1 Port 4G-LTE-G-V2 Cellular Interface SIC-Module
ibevtModuleRt-SIC-4G-LTE-A-V2             OBJECT IDENTIFIER ::= { ibevtModuleRouterType 850 } -- 1 Port 4G-LTE-A-V2 Cellular Interface SIC-Module
ibevtModuleRt-SIC-4G-LTE-V-V2             OBJECT IDENTIFIER ::= { ibevtModuleRouterType 851 } -- 1 Port 4G-LTE-V-V2 Cellular Interface SIC-Module
ibevtModuleRt-MPU60                       OBJECT IDENTIFIER ::= { ibevtModuleRouterType 852 } -- Main Processing Unit 60
ibevtModuleRt-SPU                         OBJECT IDENTIFIER ::= { ibevtModuleRouterType 853 } -- Service Processing Unit
ibevtModuleRt-SIC-1VE1T1                  OBJECT IDENTIFIER ::= { ibevtModuleRouterType 854 } -- 1-Port E1/T1 Voice SIC Module,Domestic&Overseas Version
ibevtModuleRt-CFIP-700                    OBJECT IDENTIFIER ::= { ibevtModuleRouterType 855 } -- Carrier Flexible Interface Platform 700
ibevtModuleRt-HIM-20GBP-H3                OBJECT IDENTIFIER ::= { ibevtModuleRouterType 856 } -- 20-Port Gigabit Ethernet Optical Interface Module(SFP)
ibevtModuleRt-HIM-4EXP-H3                 OBJECT IDENTIFIER ::= { ibevtModuleRouterType 857 } -- 4-Port 10GBASE-R/W Ethernet Optical Interface Module(SFP+)
ibevtModuleRt-HIM-2EXP-H3                 OBJECT IDENTIFIER ::= { ibevtModuleRouterType 858 } -- 2-Port 10GBASE-R/W Ethernet Optical Interface Module(SFP+)
ibevtModuleRt-HIM-8GBE-V3                 OBJECT IDENTIFIER ::= { ibevtModuleRouterType 859 } -- 8-port GigaBit Ethernet Electrical Interface Module
ibevtModuleRt-HIM-4GBE-V3                 OBJECT IDENTIFIER ::= { ibevtModuleRouterType 860 } -- 4-port GigaBit Ethernet Electrical Interface Module
ibevtModuleRt-HIM-8GBP-V3                 OBJECT IDENTIFIER ::= { ibevtModuleRouterType 861 } -- 8-Port GigaBit Ethernet Optical Interface Module(SFP)
ibevtModuleRt-HIM-4GBP-V3                 OBJECT IDENTIFIER ::= { ibevtModuleRouterType 862 } -- 4-Port GigaBit Ethernet Optical Interface Module(SFP)
ibevtModuleRt-SIC-AP                      OBJECT IDENTIFIER ::= { ibevtModuleRouterType 863 } -- 1-Port AP SIC Module,Domestic&Overseas Version
ibevtModuleRt-CR-MPU-04B                  OBJECT IDENTIFIER ::= { ibevtModuleRouterType 864 } -- CR Main Processing Unit B for 04 Chassis
ibevtModuleRt-CR-MPU-16B                  OBJECT IDENTIFIER ::= { ibevtModuleRouterType 865 } -- CR Main Processing Unit B for 08 and 16 Chassis
ibevtModuleRt-CR-MPU-16E                  OBJECT IDENTIFIER ::= { ibevtModuleRouterType 866 } -- CR Main Processing Unit E for 08 and 16 Chassis
ibevtModuleRt-CR-SFU-04D-H                OBJECT IDENTIFIER ::= { ibevtModuleRouterType 867 } -- CR Switching Fabric Unit(HD) for 04 Chassis
ibevtModuleRt-CR-SFU-08C-H                OBJECT IDENTIFIER ::= { ibevtModuleRouterType 868 } -- CR Switching Fabric Unit(HC) for 08 Chassis
ibevtModuleRt-CR-SFU-08D-H                OBJECT IDENTIFIER ::= { ibevtModuleRouterType 869 } -- CR Switching Fabric Unit(HD) for 08 Chassis
ibevtModuleRt-CR-SFU-16B-H                OBJECT IDENTIFIER ::= { ibevtModuleRouterType 870 } -- CR Switching Fabric Unit(HB) for 16 Chassis
ibevtModuleRt-CR-SFU-16C-H                OBJECT IDENTIFIER ::= { ibevtModuleRouterType 871 } -- CR Switching Fabric Unit(HC) for 16 Chassis
ibevtModuleRt-CR-LPU-CQ12                 OBJECT IDENTIFIER ::= { ibevtModuleRouterType 872 } -- CR 12-Port 100G Ethernet Optical Interface Module
ibevtModuleRt-CR-LPU-4004                 OBJECT IDENTIFIER ::= { ibevtModuleRouterType 873 } -- CR Flexible Interface Module 4004
ibevtModuleRt-CR-HIC-PU02                 OBJECT IDENTIFIER ::= { ibevtModuleRouterType 874 } -- CR 2-Port 10G POS Optical Interface Card
ibevtModuleRt-CR-HIC-XP12                 OBJECT IDENTIFIER ::= { ibevtModuleRouterType 875 } -- CR 12-Port 10G Ethernet Optical Interface Card
ibevtModuleRt-CR-HIC-GP12                 OBJECT IDENTIFIER ::= { ibevtModuleRouterType 876 } -- CR 12-Port Gigabit Ethernet Optical Interface Card
ibevtModuleRt-CR-HIC-QQ03                 OBJECT IDENTIFIER ::= { ibevtModuleRouterType 877 } -- CR 3-Port 40G Ethernet Optical Interface Card(QSFP+)
ibevtModuleRt-CR-HIC-CC01                 OBJECT IDENTIFIER ::= { ibevtModuleRouterType 878 } -- CR 1-Port 100G Ethernet Optical Interface Card(CFP2)
ibevtModuleRt-CR-HIC-CP01                 OBJECT IDENTIFIER ::= { ibevtModuleRouterType 879 } -- CR 1-Port 100G Ethernet Optical Interface Card(CFP)
ibevtModuleRt-CR-MPU-16C                  OBJECT IDENTIFIER ::= { ibevtModuleRouterType 880 } -- CR Main Processing Unit C for 08 and 16 Chassis
ibevtModuleRt-MPU-100-X1                  OBJECT IDENTIFIER ::= { ibevtModuleRouterType 881 } -- Main Processing Unit 100-X1
ibevtModuleRt-SPU-100-X1                  OBJECT IDENTIFIER ::= { ibevtModuleRouterType 882 } -- Service Processing Unit 100-X1
ibevtModuleRt-SPU-200-X1                  OBJECT IDENTIFIER ::= { ibevtModuleRouterType 883 } -- Service Processing Unit 200-X1
ibevtModuleRt-SPU-400-X1                  OBJECT IDENTIFIER ::= { ibevtModuleRouterType 884 } -- Service Processing Unit 400-X1
ibevtModuleRt-HIM-10GB2EXP-H3             OBJECT IDENTIFIER ::= { ibevtModuleRouterType 885 } -- 10-port 1000BASE-X Ethernet Optical Interface(SFP)+2-port 10GBASE-R/W Ethernet Optical Interface Card(SFP+)
ibevtModuleRt-HIM-11GB1EXP-H3             OBJECT IDENTIFIER ::= { ibevtModuleRouterType 886 } -- 11-port 1000BASE-X Ethernet Optical Interface(SFP)+1-port 10GBASE-R/W Ethernet Optical Interface Card(SFP+)
ibevtModuleRt-HMIM-1E3T3                  OBJECT IDENTIFIER ::= { ibevtModuleRouterType 887 } -- 1-port T3 HMIM-Module
ibevtModuleRt-SIC-4G-CNDE                 OBJECT IDENTIFIER ::= { ibevtModuleRouterType 888 } -- 1-port 4G LTE and CNDE SIC Module
ibevtModuleRt-SIC-D4G-CNDE                OBJECT IDENTIFIER ::= { ibevtModuleRouterType 889 } -- 2-port 4G LTE and CNDE SIC Module
ibevtModuleRt-CR-LPU-CC08                 OBJECT IDENTIFIER ::= { ibevtModuleRouterType 890 } -- CR 8-Port 100G Ethernet Optical Interface Module
ibevtModuleRt-CR-LPU-2002                 OBJECT IDENTIFIER ::= { ibevtModuleRouterType 891 } -- CR Flexible Interface Module 2002
ibevtModuleRt-CR-LPU-XP20CC02             OBJECT IDENTIFIER ::= { ibevtModuleRouterType 892 } -- CR 20-Port 10G Ethernet Optical Interface Module and 2-Port 100G Ethernet Optical Interface Module
ibevtModuleRt-CR-LPU-XP40                 OBJECT IDENTIFIER ::= { ibevtModuleRouterType 893 } -- CR 40-Port 10G Ethernet Optical Interface Module
ibevtModuleRt-CR-LPU-CC04                 OBJECT IDENTIFIER ::= { ibevtModuleRouterType 894 } -- CR 4-Port 100G Ethernet Optical Interface Module
ibevtModuleRt-FIP-680                     OBJECT IDENTIFIER ::= { ibevtModuleRouterType 895 } -- Service Processing Unit(680)
ibevtModuleRt-MIC-XP4L                    OBJECT IDENTIFIER ::= { ibevtModuleRouterType 896 } -- 4-port 10GBASE-R/W Ethernet Optical Interface Card(SFP+,LC)
ibevtModuleRt-MIM-1T3-V2                  OBJECT IDENTIFIER ::= { ibevtModuleRouterType 897 } -- 1-port T3 Interface Card
ibevtModuleRt-MIC-GP4L                    OBJECT IDENTIFIER ::= { ibevtModuleRouterType 898 } -- 4-Port 1000BASE-X COMBO Interface Card,(SFP,LC)
ibevtModuleRt-MIC-GP8L                    OBJECT IDENTIFIER ::= { ibevtModuleRouterType 899 } -- 8-Port 1000BASE-X Optical Interface Card,(SFP,LC)
ibevtModuleRt-CR-19K-MPU-20A              OBJECT IDENTIFIER ::= { ibevtModuleRouterType 900 } -- CR Main Processing Unit A for 19 Chassis
ibevtModuleRt-CR-19K-MPU-20B              OBJECT IDENTIFIER ::= { ibevtModuleRouterType 901 } -- CR Main Processing Unit B for 19 Chassis
ibevtModuleRt-CR-19K-SFU-20C              OBJECT IDENTIFIER ::= { ibevtModuleRouterType 902 } -- CR Switching Fabric Unit(HC) for 20 Chassis
ibevtModuleRt-CR-19K-MSFU-20B             OBJECT IDENTIFIER ::= { ibevtModuleRouterType 903 } -- CR Multi-Switching Fabric Unit(HB) for 20 Chassis
ibevtModuleRt-CR-19K-MSFU-20C             OBJECT IDENTIFIER ::= { ibevtModuleRouterType 904 } -- CR Multi-Switching Fabric Unit(HC) for 20 Chassis
ibevtModuleRt-CR-19K-MCCU                 OBJECT IDENTIFIER ::= { ibevtModuleRouterType 905 } -- CR Multi-Control Connection A Unit for 24 Chassis
ibevtModuleRt-CR-19K-MFCU                 OBJECT IDENTIFIER ::= { ibevtModuleRouterType 906 } -- CR Multi-Fabric Connection A Unit for 24 Chassis
ibevtModuleRt-RIC-8E1                     OBJECT IDENTIFIER ::= { ibevtModuleRouterType 907 } -- 8-Port E1/CE1/PRI Interface RIC-Module
ibevtModuleRt-RIC-1XGEF4GEF               OBJECT IDENTIFIER ::= { ibevtModuleRouterType 908 } -- 1-Port 10M/100M/1000M/10000MBASE-F and 4-Port 10M/100M/1000MBASE-F Ethernet Interface 1XGEF4GEFModule
ibevtModuleRt-RIC-TU01A                   OBJECT IDENTIFIER ::= { ibevtModuleRouterType 909 } -- 1-Port 10M/100M/1000M/10000MBASE-F and 4-Port 10M/100M/1000MBASE-F Ethernet Interface TU01AModule
ibevtModuleRt-SPE-S1                      OBJECT IDENTIFIER ::= { ibevtModuleRouterType 910 } -- Service Processing Engine S1
ibevtModuleRt-SPE-S3                      OBJECT IDENTIFIER ::= { ibevtModuleRouterType 911 } -- Service Processing Engine S3
ibevtModuleRt-SPU-600-X1                  OBJECT IDENTIFIER ::= { ibevtModuleRouterType 912 } -- Service Processing Unit 600-X1
ibevtModuleRt-RIC-CP08                    OBJECT IDENTIFIER ::= { ibevtModuleRouterType 913 } -- 8-Port E1/CE1/PRI Interface RIC-Module
ibevtModuleRt-MIC-SP4L                    OBJECT IDENTIFIER ::= { ibevtModuleRouterType 914 } -- 4-Port OC-3/STM-1 POS/CPOS/ATM or 1-Port OC-12/STM-4 POS/ATM Optical Interface Card,(SFP,LC)
ibevtModuleRt-MIC-ET16L                   OBJECT IDENTIFIER ::= { ibevtModuleRouterType 915 } -- 16-Port E1/T1 Electrical Interface Card
ibevtModuleRt-MIC-CLP4L                   OBJECT IDENTIFIER ::= { ibevtModuleRouterType 916 } -- 4-Port OC-3/STM-1 CPOS/POS Optical Interface Card,(SFP,LC)
ibevtModuleRt-MIC-CLP2L                   OBJECT IDENTIFIER ::= { ibevtModuleRouterType 917 } -- 2-Port OC-3/STM-1 CPOS/POS Optical Interface Card,(SFP,LC)
ibevtModuleRt-MIC-SP8L                    OBJECT IDENTIFIER ::= { ibevtModuleRouterType 918 } -- 8-Port OC-3c/STM-1c POS Optical Interface Card
ibevtModuleRt-HMIM-8EM                    OBJECT IDENTIFIER ::= { ibevtModuleRouterType 919 } -- 8-Port E&M Interface HMIM-Module
ibevtModuleRt-SFU                         OBJECT IDENTIFIER ::= { ibevtModuleRouterType 920 } -- Switching Fabric Unit
ibevtModuleRt-SFE-L2                      OBJECT IDENTIFIER ::= { ibevtModuleRouterType 921 } -- Switching Fabric Engine L2
ibevtModuleRt-SFU-UNFIXED                 OBJECT IDENTIFIER ::= { ibevtModuleRouterType 922 } -- Unfixed Switching Fabric Unit
ibevtModuleRt-FIP-380                     OBJECT IDENTIFIER ::= { ibevtModuleRouterType 923 } -- Flexible Interface Platform-380
ibevtModuleRt-CR-19K-MPU-08A              OBJECT IDENTIFIER ::= { ibevtModuleRouterType 924 } -- CR Main Processing Unit A for 08 Chassis
ibevtModuleRt-CR-19K-MPU-16A              OBJECT IDENTIFIER ::= { ibevtModuleRouterType 925 } -- CR Main Processing Unit A for 16 Chassis
ibevtModuleRt-CR-19K-SFU-08C              OBJECT IDENTIFIER ::= { ibevtModuleRouterType 926 } -- CR Switching Fabric Unit(HC) for 08 Chassis
ibevtModuleRt-CR-19K-SFU-16C              OBJECT IDENTIFIER ::= { ibevtModuleRouterType 927 } -- CR Switching Fabric Unit(HC) for 16 Chassis
ibevtModuleRt-CR-19K-LPU-CC08             OBJECT IDENTIFIER ::= { ibevtModuleRouterType 928 } -- CR 8-Port 100G Ethernet Optical Interface Module
ibevtModuleRt-CR-19K-LPU-2002             OBJECT IDENTIFIER ::= { ibevtModuleRouterType 929 } -- CR Flexible Interface Module 2002
ibevtModuleRt-CR-19K-LPU-XP20CC02         OBJECT IDENTIFIER ::= { ibevtModuleRouterType 930 } -- CR 20-Port 10G Ethernet Optical Interface Module and 2-Port 100G Ethernet Optical Interface Module
ibevtModuleRt-CR-19K-LPU-XP40             OBJECT IDENTIFIER ::= { ibevtModuleRouterType 931 } -- CR 40-Port 10G Ethernet Optical Interface Module
ibevtModuleRt-CR-19K-LPU-CC04             OBJECT IDENTIFIER ::= { ibevtModuleRouterType 932 } -- CR 4-Port 100G Ethernet Optical Interface Module
ibevtModuleRt-CR-19K-LPU-CQ12             OBJECT IDENTIFIER ::= { ibevtModuleRouterType 933 } -- CR 12-Port 100G Ethernet Optical Interface Module
ibevtModuleRt-MIC-X-GT8                   OBJECT IDENTIFIER ::= { ibevtModuleRouterType 934 } -- 8-Port 10/100/1000BASE-T Electronic Multi-functional Interface Card
ibevtModuleRt-MIC-X-GP4GT4                OBJECT IDENTIFIER ::= { ibevtModuleRouterType 935 } -- 4-Port 10/100/1000BASE-T Electronic + 4-Port 1000BASE-X Optical Multi-functional Interface Card
ibevtModuleRt-MIC-X-GP10                  OBJECT IDENTIFIER ::= { ibevtModuleRouterType 936 } -- 10-Port 1000BASE-X Optical Multi-functional Interface Card
ibevtModuleRt-MIC-X-GP8                   OBJECT IDENTIFIER ::= { ibevtModuleRouterType 937 } -- 8-Port 1000BASE-X Optical Multi-functional Interface Card
ibevtModuleRt-CR-19K-LPU-4004             OBJECT IDENTIFIER ::= { ibevtModuleRouterType 938 } -- CR Flexible Interface Module 4004
ibevtModuleRt-FIP-260                     OBJECT IDENTIFIER ::= { ibevtModuleRouterType 939 } -- Flexible Interface Platform-260
ibevtModuleRt-CR-LPU-XP72                 OBJECT IDENTIFIER ::= { ibevtModuleRouterType 940 } -- CR 72-Port 10G Ethernet Optical Interface Module
ibevtModuleRt-CR-LPU-XP48                 OBJECT IDENTIFIER ::= { ibevtModuleRouterType 941 } -- CR 48-Port 10G Ethernet Optical Interface Module
ibevtModuleRt-CR-LPU-CC04B                OBJECT IDENTIFIER ::= { ibevtModuleRouterType 942 } -- CR 4-Port 100G Ethernet Optical Interface Module
ibevtModuleRt-CR-LPU-2002B                OBJECT IDENTIFIER ::= { ibevtModuleRouterType 943 } -- CR Flexible Interface Module 2002B
ibevtModuleRt-LPU-1001B                   OBJECT IDENTIFIER ::= { ibevtModuleRouterType 944 } -- CR Flexible Interface Module 1001B
ibevtModuleRt-CR-19K-MSFU-08A             OBJECT IDENTIFIER ::= { ibevtModuleRouterType 945 } -- CR Multi-Switching Fabric Unit for 8 Chassis
ibevtModuleRt-Sic-AP220                   OBJECT IDENTIFIER ::= { ibevtModuleRouterType 946 } -- SIC-AP220 External Antennas 3 Streams Dual Radio
ibevtModuleRt-FIP-660                     OBJECT IDENTIFIER ::= { ibevtModuleRouterType 947 } -- Flexible Interface Platform 660
ibevtModuleRT-MIC-X-ET16                  OBJECT IDENTIFIER ::= { ibevtModuleRouterType 948 } -- 16-Port E1/T1 Electrical Interface Card,(RJ45)
ibevtModuleRT-MIC-X-SP4                   OBJECT IDENTIFIER ::= { ibevtModuleRouterType 949 } -- 4-Port OC-3/STM-1 POS or 1-Port OC-12/STM-4 POS Optical Interface Card,(SFP)
ibevtModuleRT-MIC-X-SP8                   OBJECT IDENTIFIER ::= { ibevtModuleRouterType 950 } -- 8-Port OC-3c/STM-1c POS Optical Interface Card,(SFP)
ibevtModuleRT-MIC-X-CLP2                  OBJECT IDENTIFIER ::= { ibevtModuleRouterType 951 } -- 2-Port OC-3/STM-1 CPOS Optical Interface Card,(SFP)
ibevtModuleRT-MIC-X-CLP4                  OBJECT IDENTIFIER ::= { ibevtModuleRouterType 952 } -- 4-Port OC-3/STM-1 CPOS Optical Interface Card,(SFP)
ibevtModuleRt-SPU-300                     OBJECT IDENTIFIER ::= { ibevtModuleRouterType 953 } -- ICG Service Processing Unit 300(10GE Combo)
ibevtModuleRt-CR-19K-LPU-XP72             OBJECT IDENTIFIER ::= { ibevtModuleRouterType 954 } -- 72-Port 10G Ethernet Optical Interface Module for 19 chassis
ibevtModuleRt-CR-19K-LPU-XP48             OBJECT IDENTIFIER ::= { ibevtModuleRouterType 955 } -- 48-Port 10G Ethernet Optical Interface Module for 19 chassis
ibevtModuleRt-CR-19K-LPU-2002B            OBJECT IDENTIFIER ::= { ibevtModuleRouterType 956 } -- Flexible Interface Module 2002B for 19 chassis
ibevtModuleRt-CR-19K-LPU-CC04B            OBJECT IDENTIFIER ::= { ibevtModuleRouterType 957 } -- 4-Port 100G Ethernet Optical Interface Module for 19 chassis
ibevtModuleRt-CR-19K-MPU-16B              OBJECT IDENTIFIER ::= { ibevtModuleRouterType 958 } -- Main Processing Unit B for 19016 Chassis
ibevtModuleRT-RPE-X5                      OBJECT IDENTIFIER ::= { ibevtModuleRouterType 959 } -- Route Processing Engine X5
ibevtModuleRT-RPE-X5E                     OBJECT IDENTIFIER ::= { ibevtModuleRouterType 960 } -- Route Processing Engine X5E
ibevtModuleRt-CR-HIC-PS04                 OBJECT IDENTIFIER ::= { ibevtModuleRouterType 961 } -- CR 4-Port non-channelized POS(155M/622M/2.5G) Interface Card,Sub Module
ibevtModuleRt-CR-HIC-PL08                 OBJECT IDENTIFIER ::= { ibevtModuleRouterType 962 } -- CR 8-Port non-channelized POS(155M) Interface Card,Sub Module
ibevtModuleRT-MIC-X-XP2                   OBJECT IDENTIFIER ::= { ibevtModuleRouterType 963 } -- 2-Port 1000BASE-R-SFP+ Optical Multi-functional Interface Card
ibevtModuleRT-MIC-X-XP4                   OBJECT IDENTIFIER ::= { ibevtModuleRouterType 964 } -- 4-Port 1000BASE-R-SFP+ Optical Multi-functional Interface Card
ibevtModuleRT-MIC-X-XP4W                  OBJECT IDENTIFIER ::= { ibevtModuleRouterType 965 } -- 4-Port 1000BASE-R-SFP+ Optical Multi-functional Interface Card(Support LAN/WAN mode)
ibevtModuleRT-SIC-CNDE-SJK                OBJECT IDENTIFIER ::= { ibevtModuleRouterType 966 } -- SJK CNDE SIC Module
ibevtModuleRT-SIC-4G-CNDE-SJK             OBJECT IDENTIFIER ::= { ibevtModuleRouterType 967 } -- SJK 4G LTE and CNDE SIC Module
ibevtModuleRT-SIC-D4G-CNDE-SJK            OBJECT IDENTIFIER ::= { ibevtModuleRouterType 968 } -- SJK Double 4G LTE and CNDE SIC Module
ibevtModuleRt-CR-19K-MSFU-16A             OBJECT IDENTIFIER ::= { ibevtModuleRouterType 969 } -- CR Multi-Switching Fabric Unit(A) for 16 Chassis
ibevtModuleRT-HMIM-CNDE-SJK               OBJECT IDENTIFIER ::= { ibevtModuleRouterType 970 } -- SJK CNDE HMIM Module
ibevtModuleRT-MIBIF-MINI-CNDE-SJK         OBJECT IDENTIFIER ::= { ibevtModuleRouterType 971 } -- SJK MINI CNDE Module
ibevtModuleRT-SIC-AP320-FIT               OBJECT IDENTIFIER ::= { ibevtModuleRouterType 972 } -- AP320 FIT SIC Module
ibevtModuleRT-SAP-XP4GE32                 OBJECT IDENTIFIER ::= { ibevtModuleRouterType 973 } -- 4-Port 10G and 32-Port G Ethernet Optical Interface Module(SFP+)
ibevtModuleRT-SIC-4E1-F-Z                 OBJECT IDENTIFIER ::= { ibevtModuleRouterType 974 } -- 4-Port Fractional E1 Interface SIC-Module
ibevtModuleRT-HRIC-CLGQ2                  OBJECT IDENTIFIER ::= { ibevtModuleRouterType 975 } -- 1-Port 50-100-GE and 1-Port 50-GE Optical Interface HRIC-Module
ibevtModuleRT-HRIC-YGS4                   OBJECT IDENTIFIER ::= { ibevtModuleRouterType 976 } -- 4-Port 25-GE Optical Interface HRIC-Module
ibevtModuleRT-HRIC-XP8                    OBJECT IDENTIFIER ::= { ibevtModuleRouterType 977 } -- 8-Port Ten-GigabitEthernet Optical Interface HRIC-Module
ibevtModuleRT-HRIC-GP8                    OBJECT IDENTIFIER ::= { ibevtModuleRouterType 978 } -- 8-Port 1000M Base-F Optical Ethernet Interface HRIC-Module
ibevtModuleRT-HRIC-GT8                    OBJECT IDENTIFIER ::= { ibevtModuleRouterType 979 } -- 8-Port 1000M Base-T Ethernet Interface HRIC-Module

ibevtModuleRT-MIC-X-CNDE-SJK             OBJECT IDENTIFIER ::= { ibevtModuleRouterType 980 } -- SJK CNDE MIC-X Module
ibevtModuleRt-CR-19K-LPU-CQ18            OBJECT IDENTIFIER ::= { ibevtModuleRouterType 981 }
ibevtModuleRt-CR-19K-LPU-CQ12B           OBJECT IDENTIFIER ::= { ibevtModuleRouterType 982 }
ibevtModuleRt-CR-19K-LPU-SP              OBJECT IDENTIFIER ::= { ibevtModuleRouterType 983 }
ibevtModuleRt-CR-HIC-CQ01                OBJECT IDENTIFIER ::= { ibevtModuleRouterType 984 }
ibevtModuleRt-NS-NIM-TG6A                OBJECT IDENTIFIER ::= { ibevtModuleRouterType 985 }
ibevtModuleRtNS-NIM-TG4A3                OBJECT IDENTIFIER ::= { ibevtModuleRouterType 986 }
ibevtModuleRtNSQM2CGQ20                  OBJECT IDENTIFIER ::= { ibevtModuleRouterType 987 }
ibevtModuleRtNSQM2FWDFGC0                OBJECT IDENTIFIER ::= { ibevtModuleRouterType 988 }
ibevtModuleRtNSQM2FWDFGB0                OBJECT IDENTIFIER ::= { ibevtModuleRouterType 989 }
ibevtModuleRt-NS-TIM-TG8A2               OBJECT IDENTIFIER ::= { ibevtModuleRouterType 990 }
ibevtModuleRtNSQM5MBSHA1                 OBJECT IDENTIFIER ::= { ibevtModuleRouterType 991 }
ibevtModuleRtNS-C600-CGQ6A1              OBJECT IDENTIFIER ::= { ibevtModuleRouterType 992 }
ibevtModuleRtNSQM5SUP08A1                OBJECT IDENTIFIER ::= { ibevtModuleRouterType 993 }
ibevtModuleRtNSQ1M9ESL16UA0              OBJECT IDENTIFIER ::= { ibevtModuleRouterType 994 }
ibevtModuleRtNS-C300-CGQ2TG16A1          OBJECT IDENTIFIER ::= { ibevtModuleRouterType 995 }
ibevtModuleRtNS-FWEMPA1                  OBJECT IDENTIFIER ::= { ibevtModuleRouterType 996 }
ibevtModuleRtNSQM5FAB08A1                OBJECT IDENTIFIER ::= { ibevtModuleRouterType 997 }
ibevtModuleRtNS-C300-QG4TG16A1           OBJECT IDENTIFIER ::= { ibevtModuleRouterType 998 }
ibevtModuleRtNSQM5FAB16A1                OBJECT IDENTIFIER ::= { ibevtModuleRouterType 999 }
ibevtModuleRtNSQM5SUP16A1                OBJECT IDENTIFIER ::= { ibevtModuleRouterType 1000 }
ibevtModuleRtNSQ1M9ESL16LA0              OBJECT IDENTIFIER ::= { ibevtModuleRouterType 1001 }
ibevtModuleRtNS-C300-TG24A1              OBJECT IDENTIFIER ::= { ibevtModuleRouterType 1002 }
ibevtModuleRtNSQM1SSICASK1               OBJECT IDENTIFIER ::= { ibevtModuleRouterType 1003 }
ibevtModuleRtNSQM2AFC2000DGDSCA0         OBJECT IDENTIFIER ::= { ibevtModuleRouterType 1004 }
ibevtModuleRt-MPU-60-WiNet               OBJECT IDENTIFIER ::= { ibevtModuleRouterType 1005 }
ibevtModuleRtNSQM2VGDSCA0                OBJECT IDENTIFIER ::= { ibevtModuleRouterType 1006 }
ibevtModuleRt-HRIC-YGS2                  OBJECT IDENTIFIER ::= { ibevtModuleRouterType 1007 }  -- 2-Port 25-GigabitEthernet Optical Interface HRIC-Module
ibevtModuleRt-HRIC-LGQ1                  OBJECT IDENTIFIER ::= { ibevtModuleRouterType 1008 }  -- 1-Port 50-GigabitEthernet Optical Interface HRIC-Module
ibevtModuleRt-HRIC-XP4                   OBJECT IDENTIFIER ::= { ibevtModuleRouterType 1009 }  -- 4-Port Ten-GigabitEthernet Optical Interface HRIC-Module
ibevtModuleRt-RSU-300                    OBJECT IDENTIFIER ::= { ibevtModuleRouterType 1010 }
ibevtModuleRt-CR-19K-LPU-CQ06B           OBJECT IDENTIFIER ::= { ibevtModuleRouterType 1011 }
ibevtModuleRt-CR-HIC-XP10                OBJECT IDENTIFIER ::= { ibevtModuleRouterType 1012 }
ibevtModuleRt-SIC-1SSD                   OBJECT IDENTIFIER ::= { ibevtModuleRouterType 1013 }
ibevtModuleRtNSQM1AFC2000GDFGA0-Z        OBJECT IDENTIFIER ::= { ibevtModuleRouterType 1014 }
ibevtModuleRtNSQM2QG4GP40-Z              OBJECT IDENTIFIER ::= { ibevtModuleRouterType 1015 }
ibevtModuleRtNSQM1CGQ20-Z                OBJECT IDENTIFIER ::= { ibevtModuleRouterType 1016 }
ibevtModuleRtNSQM1FWDFGD1-Z              OBJECT IDENTIFIER ::= { ibevtModuleRouterType 1017 }
ibevtModuleRtNSQM1TGS32QSSG0-Z           OBJECT IDENTIFIER ::= { ibevtModuleRouterType 1018 }
ibevtModuleRtNSQM2TG16GP40-Z             OBJECT IDENTIFIER ::= { ibevtModuleRouterType 1019 }
ibevtModuleRtNSQM2TMPU12E0               OBJECT IDENTIFIER ::= { ibevtModuleRouterType 1020 }
ibevtModuleRt-HMIM-4XP                   OBJECT IDENTIFIER ::= { ibevtModuleRouterType 1021 }  -- 4-Port 10GBASE-R-SFP+ Optical Ethernet Interface Card
ibevtModuleRt-SIC-1POS-STM1              OBJECT IDENTIFIER ::= { ibevtModuleRouterType 1022 }
ibevtModuleRt-HMIM-4POS                  OBJECT IDENTIFIER ::= { ibevtModuleRouterType 1023 }
ibevtModuleRt-NSQM1MPULB                 OBJECT IDENTIFIER ::= { ibevtModuleRouterType 1024 }
ibevtModuleRt-CR-LPU-CQ12B               OBJECT IDENTIFIER ::= { ibevtModuleRouterType 1025 }
ibevtModuleRt-CR-LPU-CQ18                OBJECT IDENTIFIER ::= { ibevtModuleRouterType 1026 }
ibevtModuleRt-CR-MPU-20A                 OBJECT IDENTIFIER ::= { ibevtModuleRouterType 1027 }
ibevtModuleRt-CR-HIC-CLP04               OBJECT IDENTIFIER ::= { ibevtModuleRouterType 1028 }
ibevtModuleRt-CR-SFU-08C                 OBJECT IDENTIFIER ::= { ibevtModuleRouterType 1029 }
ibevtModuleRt-CR-HIC-PHP08               OBJECT IDENTIFIER ::= { ibevtModuleRouterType 1030 }
ibevtModuleRt-CR-MPU-08A                 OBJECT IDENTIFIER ::= { ibevtModuleRouterType 1031 }
ibevtModuleRt-CR-HIC-XP12B               OBJECT IDENTIFIER ::= { ibevtModuleRouterType 1032 }
ibevtModuleRt-CR-HIC-ET16                OBJECT IDENTIFIER ::= { ibevtModuleRouterType 1033 }
ibevtModuleRt-CR-MSFU-08A                OBJECT IDENTIFIER ::= { ibevtModuleRouterType 1034 }
ibevtModuleRt-CR-SFU-20C                 OBJECT IDENTIFIER ::= { ibevtModuleRouterType 1035 }
ibevtModuleRt-SIC-M2-SATA                OBJECT IDENTIFIER ::= { ibevtModuleRouterType 1036 }
ibevtModuleRtNSQM1MPULC                  OBJECT IDENTIFIER ::= { ibevtModuleRouterType 1037 }
ibevtModuleRt-NSUM1QG1A                  OBJECT IDENTIFIER ::= { ibevtModuleRouterType 1038 }
ibevtModuleRt-NSUM1TG4A                  OBJECT IDENTIFIER ::= { ibevtModuleRouterType 1039 }
ibevtModuleRt-NSUM1GP4A                  OBJECT IDENTIFIER ::= { ibevtModuleRouterType 1040 }
ibevtModuleRt-FIP-30                     OBJECT IDENTIFIER ::= { ibevtModuleRouterType 1041 } -- Flexible Interface Platform Module 30,2 MIC-X Slots, 4*10GBASE-R SFP+ Ports, and 16*1000BASE-X SFP Ports
ibevtModuleRt-RISER-FHFL-X16             OBJECT IDENTIFIER ::= { ibevtModuleRouterType 1042 } -- SR6602-I PCIe Riser Module(FHFL, 1 PCIe X16 Slot)
ibevtModuleRt-RISER-GPU                  OBJECT IDENTIFIER ::= { ibevtModuleRouterType 1043 } -- Graphic Processiong Unit On Riser Card
ibevtModuleRt-RISER-RAID                 OBJECT IDENTIFIER ::= { ibevtModuleRouterType 1044 } -- Redundant Arrays of Independent Disks On Riser Card
ibevtModuleRt-CR-19K-LPU-8004            OBJECT IDENTIFIER ::= { ibevtModuleRouterType 1045 } -- CR Flexible Interface Module 8004
ibevtModuleRt-CR-19K-MPU-08B             OBJECT IDENTIFIER ::= { ibevtModuleRouterType 1046 } -- CR Main Processing Unit B for 08 Chassis
ibevtModuleRt-CR-HIC-CQ02                OBJECT IDENTIFIER ::= { ibevtModuleRouterType 1047 } -- 2-Port 100-GigabitEthernet Optical Interface HIC-Module
ibevtModuleRt-NSQM1ISPAXA1               OBJECT IDENTIFIER ::= { ibevtModuleRouterType 1048 } -- 2-Port 10/100/1000BASE-T and 2-Port 1000BASE-X SFP Interface Module
ibevtModuleRt-NSQM1ISPAXB1               OBJECT IDENTIFIER ::= { ibevtModuleRouterType 1049 } -- 2-Port 10/100/1000BASE-T and 2-Port 1000BASE-X SFP Interface Module
ibevtModuleRt-CR-USBDISK                 OBJECT IDENTIFIER ::= { ibevtModuleRouterType 1050 } -- CR USB DISK
ibevtModuleRt-SIC-4RS                    OBJECT IDENTIFIER ::= { ibevtModuleRouterType 1051 } -- MSR,RTU1S4RS,4-Port Asynchronous Serial Interface SIC Interface Board,2*1
ibevtModuleRt-NSQM1MPULC-Z               OBJECT IDENTIFIER ::= { ibevtModuleRouterType 1052 }
ibevtModuleRt-CR-18K-MPU-16B             OBJECT IDENTIFIER ::= { ibevtModuleRouterType 1053 } -- CR Main Processing Unit B for 18 Chassis
ibevtModuleRt-CR-18K-SFU-16C             OBJECT IDENTIFIER ::= { ibevtModuleRouterType 1054 } -- CR Switching Fabric Unit(HC) C for 18 Chassis
ibevtModuleRt-DS-3RH-4T                  OBJECT IDENTIFIER ::= { ibevtModuleRouterType 1055 } -- H Series Enterprise Router 4 Gigabit Electrical Port SIC Module
ibevtModuleRt-HRIC-CQ1F                  OBJECT IDENTIFIER ::= { ibevtModuleRouterType 1056 } -- 1-Port 100-GigabitEthernet Optical Interface HRIC-Module
ibevtModuleRt-HRIC-LGQ2F                 OBJECT IDENTIFIER ::= { ibevtModuleRouterType 1057 } -- 2-Port 50-GE Optical Interface HRIC-Module
ibevtModuleRt-CR-HIC-CLGQ04F             OBJECT IDENTIFIER ::= { ibevtModuleRouterType 1058 } -- CR 4-Port FlexE Optical SubCard
ibevtModuleRt-NSQM1QG1A-Z                OBJECT IDENTIFIER ::= { ibevtModuleRouterType 1059 } -- 1-Port 40GBASE Ethernet Optical Interface Module(QSFP+)
ibevtModuleRt-NSQM1TG4A-Z                OBJECT IDENTIFIER ::= { ibevtModuleRouterType 1060 } -- 4-Port 10GBASE Ethernet Optical Interface Module(SFP+)
ibevtModuleRt-NSQM1GP4A-Z                OBJECT IDENTIFIER ::= { ibevtModuleRouterType 1061 } -- 4-Port Gigabit Ethernet Optical Interface Module(SFP)
ibevtModuleRt-CR-LPU-8004                OBJECT IDENTIFIER ::= { ibevtModuleRouterType 1062 } -- CR Flexible Interface Module 8004
ibevtModuleRt-MPU-100-G                  OBJECT IDENTIFIER ::= { ibevtModuleRouterType 1063 } -- MPU-100-G Main Processing Unit
ibevtModuleRt-SPU-300-G                  OBJECT IDENTIFIER ::= { ibevtModuleRouterType 1064 } -- SPU-300-G Service Processing Unit
ibevtModuleRt-CR-19K-MPU-20C             OBJECT IDENTIFIER ::= { ibevtModuleRouterType 1065 } -- CR X86 MPU  for 20 Chassis
ibevtModuleRt-CR-18K-MPU-16C             OBJECT IDENTIFIER ::= { ibevtModuleRouterType 1066 } -- CR X86 MPU  for 18 Chassis
ibevtModuleRt-SIC-5G                     OBJECT IDENTIFIER ::= { ibevtModuleRouterType 1067 } -- MSR,RTUM1S5G,5G(5G NR/NSA/SA/4G FDD/TDD LTE-A/3G WCDMA,Sub6,GNSS)SIC Module,Domestic&Overseas Version
ibevtModuleRt-RSU-400                    OBJECT IDENTIFIER ::= { ibevtModuleRouterType 1068 } -- Router Switch Unit 400
ibevtModuleRt-HRIC-XP8-H                 OBJECT IDENTIFIER ::= { ibevtModuleRouterType 1069 } -- 8-Port 10-GigabitEthernet Optical Interface HRIC-Module
ibevtModuleRt-BBU3120-MCBM2LMCMB1        OBJECT IDENTIFIER ::= { ibevtModuleRouterType 1072 } -- BBU Processing Unit
ibevtModuleRt-BBU3120-MCBM2LBBMB1        OBJECT IDENTIFIER ::= { ibevtModuleRouterType 1073 } -- BBU Processing Unit
ibevtModuleRt-HMIM-2POS                  OBJECT IDENTIFIER ::= { ibevtModuleRouterType 1074 } -- 2 Port POS-STM1/4 Interface
ibevtModuleRt-HMIM-8GEF-V2               OBJECT IDENTIFIER ::= { ibevtModuleRouterType 1075 } -- 8-Port 1000BASE-X L3 HMIM Module
ibevtModuleRt-HMIM-8GEE-V2               OBJECT IDENTIFIER ::= { ibevtModuleRouterType 1076 } -- 8-Port Gig-T L3 HMIM Module
ibevtModuleRt-HMIM-16ASE-V2              OBJECT IDENTIFIER ::= { ibevtModuleRouterType 1077 } -- MSR,RTUM1HM8ASEHS,Enhanced 16-Port Async Serial HMIM Module,Domestic&Overseas Version
ibevtModuleRt-HMIM-8ASE-V2               OBJECT IDENTIFIER ::= { ibevtModuleRouterType 1078 } -- MSR,RTUM1HM8ASEHS,Enhanced 8-Port Async Serial HMIM Module,Domestic&Overseas Version
ibevtModuleRt-HMIM-4GEF-V2               OBJECT IDENTIFIER ::= { ibevtModuleRouterType 1079 } -- 4-Port 1000BASE-X L3 HMIM Module
ibevtModuleRt-HMIM-4GEE-V2               OBJECT IDENTIFIER ::= { ibevtModuleRouterType 1080 } -- 4-Port Gig-T L3 HMIM Module
ibevtModuleRt-NS-NIM-QG1A                OBJECT IDENTIFIER ::= { ibevtModuleRouterType 1081 } -- 1-Port 40GBASE Ethernet Optical Interface Module(QSFP+)
ibevtModuleRt-NS-NIM-GP4B                OBJECT IDENTIFIER ::= { ibevtModuleRouterType 1082 } -- 4-Port Gigabit Ethernet Optical Interface Module(SFP)
ibevtModuleRt-NS-NIM-TG4B                OBJECT IDENTIFIER ::= { ibevtModuleRouterType 1083 } -- 4-Port 10GBASE Ethernet Optical Interface Module(SFP+)
ibevtModuleRt-5G-NR                      OBJECT IDENTIFIER ::= { ibevtModuleRouterType 1084 } -- MSR1004S 5G Router(2*GE(SFP),5*GE(RJ45),5G NR)
ibevtModuleRt-CR-19K-LPU-4004B           OBJECT IDENTIFIER ::= { ibevtModuleRouterType 1085 } -- CR Flexible Interface Module 4004B
ibevtModuleRt-CR-19K-LPU-8004B           OBJECT IDENTIFIER ::= { ibevtModuleRouterType 1086 } -- CR Flexible Interface Module 8004B

ibevtModuleRt-NIC-NF-10GE-SFPP6          OBJECT IDENTIFIER ::= { ibevtModuleRouterType 1087 } -- 6-Port 10GBASE Ethernet Optical Interface Module(SFP+)
ibevtModuleRt-NIC-NF-10GE-SFPP8          OBJECT IDENTIFIER ::= { ibevtModuleRouterType 1088 } -- 8-Port 10GBASE Ethernet Optical Interface Module(SFP+)
ibevtModuleRt-NIC-NF-GE-SFP4             OBJECT IDENTIFIER ::= { ibevtModuleRouterType 1089 } -- 4-Port Gigabit Ethernet Optical Interface Module(SFP)
ibevtModuleRt-NIC-NF-GE-TX8              OBJECT IDENTIFIER ::= { ibevtModuleRouterType 1090 } -- 8 Port GigabitEthernet Interface Module
ibevtModuleRt-CR-SFU-16E                 OBJECT IDENTIFIER ::= { ibevtModuleRouterType 1091 } -- CR Switching Fabric Unit(HC) 16E for 18 Chassis and 19 Chassis
ibevtModuleRt-CR-19K-LPU-CQ24            OBJECT IDENTIFIER ::= { ibevtModuleRouterType 1092 } -- CR 24-Port 100G Ethernet Optical Interface Module for 19 Chassis
ibevtModuleRt-CR-19K-LPU-CDQ06           OBJECT IDENTIFIER ::= { ibevtModuleRouterType 1093 } -- CR 6-Port 400G Ethernet Optical Interface Module for 19 Chassis
ibevtModuleRt-SIC-4G-CAT6                OBJECT IDENTIFIER ::= { ibevtModuleRouterType 1094 } -- 4G LTE(TDD/FDD LTE,WCDMA,DUAL SIM,Support CAT6)SIC Module
ibevtModuleRt-HMIM-8SAE-V2               OBJECT IDENTIFIER ::= { ibevtModuleRouterType 1095 } -- 8-Port Enhanced Sync/Async Serial HMIM Module
ibevtModuleRt-HMIM-4SAE-V2               OBJECT IDENTIFIER ::= { ibevtModuleRouterType 1096 } -- 4-Port Enhanced Sync/Async Serial HMIM Module
ibevtModuleRt-NS-NIM-TG4C                OBJECT IDENTIFIER ::= { ibevtModuleRouterType 1097 } -- 4-Port 10GBASE-R Interface Module
ibevtModuleRt-NS-NIM-GT8B                OBJECT IDENTIFIER ::= { ibevtModuleRouterType 1098 } -- 8-Port 1000BASE-T Interface Module
ibevtModuleRt-NS-NIM-GP8B                OBJECT IDENTIFIER ::= { ibevtModuleRouterType 1099 } -- 8-Port 1000BASE-X Interface Module
ibevtModuleRt-CR-19K-LPU-CQ18B           OBJECT IDENTIFIER ::= { ibevtModuleRouterType 1100 } -- CR 18-Port 100G Ethernet Optical Interface Module for 19 Chassis
ibevtModuleRt-CR-19K-LPU-CDQ02           OBJECT IDENTIFIER ::= { ibevtModuleRouterType 1101 } -- CR 2-Port 400G Ethernet Optical Interface Module for 19 Chassis
ibevtModuleRt-CR-19K-LPU-CQ16F           OBJECT IDENTIFIER ::= { ibevtModuleRouterType 1102 } -- CR 16-Port Flexible Ethernet Interface Module for 19 Chassis
ibevtModuleRt-RSU-400S                   OBJECT IDENTIFIER ::= { ibevtModuleRouterType 1103 } -- Router Switch Unit 400S
ibevtModuleRt-HMIM-8E1-V3                OBJECT IDENTIFIER ::= { ibevtModuleRouterType 1104 } -- 8-Port Fractional Channelized E1and Channeled CE1/PRI HMIM Modules
ibevtModuleRt-HMIM-4E1-V3                OBJECT IDENTIFIER ::= { ibevtModuleRouterType 1105 } -- 4-Port Fractional Channelized E1and Channeled CE1/PRI HMIM Modules
ibevtModuleRt-HMIM-2E1-V3                OBJECT IDENTIFIER ::= { ibevtModuleRouterType 1106 } -- 2-Port Fractional Channelized E1and Channeled CE1/PRI HMIM Modules
ibevtModuleRt-CR-LPU-CQ16FB              OBJECT IDENTIFIER ::= { ibevtModuleRouterType 1107 } -- CR 16-Port single J2C Flexible Ethernet Interface Module
ibevtModuleRt-CR-LPU-CQ12F               OBJECT IDENTIFIER ::= { ibevtModuleRouterType 1108 } -- CR 12-Port Flexible Ethernet Interface Module
ibevtModuleRt-CR-LPU-CQ12FB              OBJECT IDENTIFIER ::= { ibevtModuleRouterType 1109 } -- CR 12-Port single J2C Flexible Ethernet Interface Module
ibevtModuleRt-CR-LPU-CQ16F               OBJECT IDENTIFIER ::= { ibevtModuleRouterType 1110 } -- CR 16-Port Flexible Ethernet Interface Module
ibevtModuleRt-CR-19K-LPU-CQ16FB          OBJECT IDENTIFIER ::= { ibevtModuleRouterType 1111 } -- CR 16-Port single J2C Flexible Ethernet Interface Module for 19 Chassis
ibevtModuleRt-CR-19K-LPU-CQ12F           OBJECT IDENTIFIER ::= { ibevtModuleRouterType 1112 } -- CR 12-Port Flexible Ethernet Interface Module for 19 Chassis
ibevtModuleRt-CR-19K-LPU-CQ12FB          OBJECT IDENTIFIER ::= { ibevtModuleRouterType 1113 } -- CR 12-Port single J2C Flexible Ethernet Interface Module for 19 Chassis
ibevtModuleRt-SIC-4G-Z                   OBJECT IDENTIFIER ::= { ibevtModuleRouterType 1114 } -- 4G LTE (TDD/FDD LTE, TD-SCDMA, WCDMA, Full Frequency EVDO, DUAL SIM) SIC Module
ibevtModuleRt-SIC-5G-CN-Z                OBJECT IDENTIFIER ::= { ibevtModuleRouterType 1115 } -- 5G NR (NSA/SA/4G FDD/TDD LTE-A/3G WCDMA, Sub6) SIC Module
ibevtModuleRt-CR-19K-LPU-CQ16            OBJECT IDENTIFIER ::= { ibevtModuleRouterType 1116 } -- CR 16-Port 100G Ethernet Optical Interface Module (QSFP28) for 19 Chassis
ibevtModuleRt-CR-19K-LPU-CQ12C           OBJECT IDENTIFIER ::= { ibevtModuleRouterType 1117 } -- CR 12-Port 100G Ethernet Optical Interface Module C (QSFP28) for 19 Chassis
ibevtModuleRt-CR-19K-LPU-CDQ04           OBJECT IDENTIFIER ::= { ibevtModuleRouterType 1118 } -- CR 4-Port 400G Ethernet Optical Interface Module (QSFP-DD) for 19 Chassis
ibevtModuleRt-CR-19K-MPU-08B-G           OBJECT IDENTIFIER ::= { ibevtModuleRouterType 1119 } -- CR Main Processing Unit B-G for 08 Chassis
ibevtModuleRt-CR-19K-MPU-08B-E           OBJECT IDENTIFIER ::= { ibevtModuleRouterType 1120 } -- CR Main Processing Unit B-E for 08 Chassis
ibevtModuleRt-MSU-200                    OBJECT IDENTIFIER ::= { ibevtModuleRouterType 1121 } -- MSU-200 Main-control and Service-processing Unit (2*10GE(SFP+),2*GE Combo,8*GE(RJ45),1*SIC Slot)
ibevtModuleRt-MSU-100                    OBJECT IDENTIFIER ::= { ibevtModuleRouterType 1122 } -- MSU-100 Main-control and Service-processing Unit
ibevtModuleRt-XMIM-8GEE-R                OBJECT IDENTIFIER ::= { ibevtModuleRouterType 1123 } -- 8-Port 1000-GigabitEthernet Interface XMIM Modules
ibevtModuleRt-XMIM-4POS                  OBJECT IDENTIFIER ::= { ibevtModuleRouterType 1124 } -- 4-port Optical Interface Pos XMIM Modules
ibevtModuleRt-XMIM-2POS                  OBJECT IDENTIFIER ::= { ibevtModuleRouterType 1125 } -- 2-port Optical Interface Pos XMIM Modules
ibevtModuleRt-XMIM-1POS                  OBJECT IDENTIFIER ::= { ibevtModuleRouterType 1126 } -- 1-port Optical Interface Pos XMIM Modules
ibevtModuleRt-XMIM-8E1                   OBJECT IDENTIFIER ::= { ibevtModuleRouterType 1127 } -- 8-Port Fractional Channelized E1and Channeled CE1/PRI XMIM Modules
ibevtModuleRt-XMIM-4E1                   OBJECT IDENTIFIER ::= { ibevtModuleRouterType 1128 } -- 4-Port Fractional Channelized E1and Channeled CE1/PRI XMIM Modules
ibevtModuleRt-XMIM-2E1                   OBJECT IDENTIFIER ::= { ibevtModuleRouterType 1129 } -- 2-Port Fractional Channelized E1and Channeled CE1/PRI XMIM Modules
ibevtModuleRt-NIC-NF-MPU                 OBJECT IDENTIFIER ::= { ibevtModuleRouterType 1130 }
ibevtModuleRt-HMIC-XP4                   OBJECT IDENTIFIER ::= { ibevtModuleRouterType 1131 } -- 4-Port 10G Interface HMIC Modules
ibevtModuleRt-DS-3RH-M2-SATA             OBJECT IDENTIFIER ::= { ibevtModuleRouterType 1132 } -- M.2 Riser(1 SATA 3.0) SIC Module
ibevtModuleRt-HMIC-GP10                  OBJECT IDENTIFIER ::= { ibevtModuleRouterType 1133 } -- 10-Port 1G Interface HMIC Modules
ibevtModuleRt-HMIC-GT8                   OBJECT IDENTIFIER ::= { ibevtModuleRouterType 1134 } -- 8-Port 1G Interface HMIC Modules
ibevtModuleRt-XMIM-8GEF-R                OBJECT IDENTIFIER ::= { ibevtModuleRouterType 1135 } -- 8-Port 1G Interface XMIM Modules
ibevtModuleRt-RFU-560-G                  OBJECT IDENTIFIER ::= { ibevtModuleRouterType 1136 } -- RFU-560-G Route and Forwarding Unit
ibevtModuleRt-RFU-360-G                  OBJECT IDENTIFIER ::= { ibevtModuleRouterType 1137 } -- RFU-360-G Route and Forwarding Unit
ibevtModuleRt-MSU-400-G                  OBJECT IDENTIFIER ::= { ibevtModuleRouterType 1138 } -- MSU-400-G Router Switch Unit
ibevtModuleRt-HMIC-SP4                   OBJECT IDENTIFIER ::= { ibevtModuleRouterType 1139 } -- 4-port Optical Interface Pos HMIC Modules
ibevtModuleRt-HMIC-CQ1F                  OBJECT IDENTIFIER ::= { ibevtModuleRouterType 1140 } -- 1-Port 50/100GBASE-R-QSFP28 or 1-Port 40GBASE-R-QSFP+
ibevtModuleRt-HMIC-XP10                  OBJECT IDENTIFIER ::= { ibevtModuleRouterType 1141 } -- 10-Port 10GBASE-R-SFP+ L3 Interface HMIC Module
ibevtModuleRt-HMIC-GP20                  OBJECT IDENTIFIER ::= { ibevtModuleRouterType 1142 } -- 20-Port 100/1000BASE-X-CSFP or 10-Port 100/1000BASE-X-SFP L3 Interface HMIC Module
ibevtModuleRt-NSQ1F1QG2A                 OBJECT IDENTIFIER ::= { ibevtModuleRouterType 1143 } -- 2-Port 40GBASE Ethernet Optical Interface Module(QSFP+)
ibevtModuleRt-CR-19K-MPU-08D-G           OBJECT IDENTIFIER ::= { ibevtModuleRouterType 1144 } -- CR19000-8 Main Processing Unit D-G
ibevtModuleRt-CR-19K-MPU-20D-G           OBJECT IDENTIFIER ::= { ibevtModuleRouterType 1145 } -- CR19000 Main Processing Unit D-G
ibevtModuleRt-CR-MPU-16D-G               OBJECT IDENTIFIER ::= { ibevtModuleRouterType 1146 } -- CR18000 Main Processing Unit D-G
ibevtModuleRt-SEC-M-6SFP-PLUS            OBJECT IDENTIFIER ::= { ibevtModuleRouterType 1147 } -- 6 Port Ten-GigabitEthernet Interface Module
ibevtModuleRt-SEC-M-4SFP                 OBJECT IDENTIFIER ::= { ibevtModuleRouterType 1148 } -- SecPath F1000-NSQM1GP4FBA
ibevtModuleRt-SEC-M-4PFC                 OBJECT IDENTIFIER ::= { ibevtModuleRouterType 1149 } -- 4 Port GigabitEthernet Interface
ibevtModuleRt-AIS-SEC-G-4SFP-PLUS        OBJECT IDENTIFIER ::= { ibevtModuleRouterType 1150 } -- 4-Port 10GBASE Ethernet Optical Interface(SFP+)
ibevtModuleRt-AIS-SEC-G-8SFP             OBJECT IDENTIFIER ::= { ibevtModuleRouterType 1151 } -- 8-Port GE Optical Interface(SFP)
ibevtModuleRt-AIS-SEC-G-8GE              OBJECT IDENTIFIER ::= { ibevtModuleRouterType 1152 } -- 8-Port GE Optical Interface
ibevtModuleRt-XMIM-XP4                   OBJECT IDENTIFIER ::= { ibevtModuleRouterType 1153 } -- 4-Port 10GBASE-R-SFP+ L3 Interface XMIM Module
ibevtModuleRt-HMIC-ESPA                  OBJECT IDENTIFIER ::= { ibevtModuleRouterType 1154 } -- High Interface Platform Module ESPA
ibevtModuleRt-HMIC-ET16                  OBJECT IDENTIFIER ::= { ibevtModuleRouterType 1155 } -- 16-Port Fractional E1 (E1-F) -HM96 or Channelized E1 (CE1/PRI) -HM96 Interface HMIC Module,Domestic&Overseas Version
ibevtModuleRt-CR-LPU-4004B               OBJECT IDENTIFIER ::= { ibevtModuleRouterType 1156 } -- CR Flexible Interface Module B(LPU-4004B)
ibevtModuleRt-CR-LPU-8004B               OBJECT IDENTIFIER ::= { ibevtModuleRouterType 1157 } -- CR Flexible Interface Module B(LPU-8004B)
ibevtModuleRt-CR-LPU-CQ12C               OBJECT IDENTIFIER ::= { ibevtModuleRouterType 1158 } -- CR 12-Port 100G Ethernet Optical Interface Module C (QSFP28)
ibevtModuleRt-CR-LPU-CQ16                OBJECT IDENTIFIER ::= { ibevtModuleRouterType 1159 } -- CR 16-Port 100G Ethernet Optical Interface Module (QSFP28)
ibevtModuleRt-CR-LPU-CDQ02               OBJECT IDENTIFIER ::= { ibevtModuleRouterType 1160 } -- CR 2-Port 400G Ethernet Optical Interface Module (QSFP-DD)
ibevtModuleRt-CR-LPU-CDQ04               OBJECT IDENTIFIER ::= { ibevtModuleRouterType 1161 } -- CR 4-Port 400G Ethernet Optical Interface Module (QSFP-DD)

ibevtModuleRt-HMIC-CNDE-SJK              OBJECT IDENTIFIER ::= { ibevtModuleRouterType 1165 } -- SCA SM Encryption (SM1/2/3/4 Supported) HMIC Module
ibevtModuleRt-XMIM-CNDE-SJK              OBJECT IDENTIFIER ::= { ibevtModuleRouterType 1166 } -- SCA SM Encryption (SM1/2/3/4 Supported) XMIM Module
ibevtModuleRt-NS-NIM-QG2A                OBJECT IDENTIFIER ::= { ibevtModuleRouterType 1167 } -- 2-Port 40GBASE Ethernet Optical Interface Module(QSFP+)
ibevtModuleRt-NS-MIM-GP4PFCA             OBJECT IDENTIFIER ::= { ibevtModuleRouterType 1168 } -- 4 Port GigabitEthernet Interface Module
ibevtModuleRt-NS-SIM-GP4PFCA             OBJECT IDENTIFIER ::= { ibevtModuleRouterType 1169 } -- 4 Port GigabitEthernet Interface Module
ibevtModuleRt-NS-MIM-GP4PFCA-Z           OBJECT IDENTIFIER ::= { ibevtModuleRouterType 1170 } -- 4 Port GigabitEthernet Interface Module
ibevtModuleRt-NS-SIM-GP4PFCA-Z           OBJECT IDENTIFIER ::= { ibevtModuleRouterType 1171 } -- 4 Port GigabitEthernet Interface Module
ibevtModuleRt-NS-NIM-GT4GP4A             OBJECT IDENTIFIER ::= { ibevtModuleRouterType 1172 } -- 4 Port Fabric and 4 Port Copper GigabitEthernet Interface
ibevtModuleRt-NS-NIM-TG4C-Z              OBJECT IDENTIFIER ::= { ibevtModuleRouterType 1173 } -- 4-Port 10GBASE-R Interface Module
ibevtModuleRt-NS-NIM-GT8B-Z              OBJECT IDENTIFIER ::= { ibevtModuleRouterType 1174 } -- 8-Port 1000BASE-T Interface Module
ibevtModuleRt-NS-NIM-GP8B-Z              OBJECT IDENTIFIER ::= { ibevtModuleRouterType 1175 } -- 8-Port 1000BASE-X Interface Module
ibevtModuleRt-NSQM1MPULC                 OBJECT IDENTIFIER ::= { ibevtModuleRouterType 1176 } -- F5000-CN30-D Control Card
ibevtModuleRt-NSQM1MPULC-IPS             OBJECT IDENTIFIER ::= { ibevtModuleRouterType 1177 } -- F5000-CN30-D Control Card
ibevtModuleRt-NSQM1MPUPA                 OBJECT IDENTIFIER ::= { ibevtModuleRouterType 1178 } -- F5030-D Control Card
ibevtModuleRt-CR-19K-LPU-8004B-G         OBJECT IDENTIFIER ::= { ibevtModuleRouterType 1179 } -- CR Flexible Interface Module (LPU-8004B-G)
ibevtModuleRt-CR-LPU-8004B-G             OBJECT IDENTIFIER ::= { ibevtModuleRouterType 1180 } -- CR Flexible Interface Module (LPU-8004B-G)
ibevtModuleRt-RX-MPU-16D-G               OBJECT IDENTIFIER ::= { ibevtModuleRouterType 1181 } -- RX8800E Main Processing Unit D-G
ibevtModuleRt-RX-LPU-CQ16F               OBJECT IDENTIFIER ::= { ibevtModuleRouterType 1182 } -- RX 16-Port 100G FlexE Ethernet Optical Interface Module (QSFP28)
ibevtModuleRt-RX-LPU-8004                OBJECT IDENTIFIER ::= { ibevtModuleRouterType 1183 } -- RX Flexible Interface Module 8004
ibevtModuleRt-RX-HIC-XP12B               OBJECT IDENTIFIER ::= { ibevtModuleRouterType 1184 } -- RX 12-Port 10G Ethernet Optical Interface Card(SFP+)
ibevtModuleRt-RX-HIC-XP10                OBJECT IDENTIFIER ::= { ibevtModuleRouterType 1185 } -- RX 10-Port 1G/10G Ethernet Optical Interface Card(SFP+)
ibevtModuleRt-RX-SFU-16E                 OBJECT IDENTIFIER ::= { ibevtModuleRouterType 1186 } -- RX8800-16E Fabric Module (Class E)
ibevtModuleRt-NS-NIM-ISEAXB              OBJECT IDENTIFIER ::= { ibevtModuleRouterType 1187 } -- F5000 NS-NIM-ISEAXB
ibevtModuleRt-NS-NIM-ISEAXA              OBJECT IDENTIFIER ::= { ibevtModuleRouterType 1188 } -- F1000 NS-NIM-ISEAXA
ibevtModuleRt-NS-HPIM-TG4A               OBJECT IDENTIFIER ::= { ibevtModuleRouterType 1189 } -- 4SFP+
ibevtModuleRt-NS-HPIM-TG4A-Z             OBJECT IDENTIFIER ::= { ibevtModuleRouterType 1190 } -- 4SFP+
ibevtModuleRt-NS-HPIM-GP8A               OBJECT IDENTIFIER ::= { ibevtModuleRouterType 1191 } -- 8SFP
ibevtModuleRt-NS-HPIM-GP8A-Z             OBJECT IDENTIFIER ::= { ibevtModuleRouterType 1192 } -- 8SFP
ibevtModuleRt-NS-HPIM-GT8A               OBJECT IDENTIFIER ::= { ibevtModuleRouterType 1193 } -- 8GE
ibevtModuleRt-NS-HPIM-GT8A-Z             OBJECT IDENTIFIER ::= { ibevtModuleRouterType 1194 } -- 8GE
ibevtModuleRt-NS-HPIM-GT8PFCA            OBJECT IDENTIFIER ::= { ibevtModuleRouterType 1195 } -- 8PFC
ibevtModuleRt-NS-HPIM-GT8PFCA-Z          OBJECT IDENTIFIER ::= { ibevtModuleRouterType 1196 } -- 8PFC
ibevtModuleRt-NSQM1TG8B                  OBJECT IDENTIFIER ::= { ibevtModuleRouterType 1197 } -- F5000 8SFP+
-- 1000 to 4999 for united assignment
--


--
-- reserved for other brands from 5000
--
hpevtModuleRt-SIC-EPRI                     OBJECT IDENTIFIER ::= { ibevtModuleRouterType 5000 } -- 1-Port E1/CE1/PRI Interface Card
hpevtModuleRt-MIM-1E1-V2                   OBJECT IDENTIFIER ::= { ibevtModuleRouterType 5001 } -- 1-Port CE1/PRI Interface Module
hpevtModuleRt-MIM-1E1-F-V2                 OBJECT IDENTIFIER ::= { ibevtModuleRouterType 5002 } -- 1-Port E1 & Fractional E1 Interface Module
hpevtModuleRt-MIM-2E1-F-V2                 OBJECT IDENTIFIER ::= { ibevtModuleRouterType 5003 } -- 2-Port E1 & Fractional E1 Interface Module
hpevtModuleRt-MIM-4E1-F-V2                 OBJECT IDENTIFIER ::= { ibevtModuleRouterType 5004 } -- 4-Port E1 & Fractional E1 Interface Module
hpevtModuleRt-MIM-8E1-75                   OBJECT IDENTIFIER ::= { ibevtModuleRouterType 5005 } -- 8-port E1/CE1/PRI Module(75ohm)
hpevtModuleRt-MIM-8E1-75-F                 OBJECT IDENTIFIER ::= { ibevtModuleRouterType 5006 } -- 8-Port E1 Module-Fractional(75ohm)
hpevtModuleRt-MIM-8T1                      OBJECT IDENTIFIER ::= { ibevtModuleRouterType 5007 } -- 8-Port T1 Interface Module
hpevtModuleRt-MIM-8T1-F                    OBJECT IDENTIFIER ::= { ibevtModuleRouterType 5008 } -- 8-Port T1 Module-Fractional
hpevtModuleRt-MIM-IMA-8E1-75               OBJECT IDENTIFIER ::= { ibevtModuleRouterType 5009 } -- 8-Port E1 ATM IMA Interface Module(75ohm)
hpevtModuleRt-FIC-2E1-V3                   OBJECT IDENTIFIER ::= { ibevtModuleRouterType 5010 } -- 2-Port E1/CE1/PRI Interface FIC Module
hpevtModuleRt-FIC-IMA-8T1-V2               OBJECT IDENTIFIER ::= { ibevtModuleRouterType 5011 } -- 8-Port T1 ATM IMA Interface FIC Module
ibevtModuleRtCN-MSU-X3                   OBJECT IDENTIFIER ::= { ibevtModuleRouterType 5012 } -- Mainboard Switch Unit X3
ibevtModuleRtCN-FSP-660                  OBJECT IDENTIFIER ::= { ibevtModuleRouterType 5013 } -- Flexible Service Platform 660
ibevtModuleRtCN-MIC-X-XP4W               OBJECT IDENTIFIER ::= { ibevtModuleRouterType 5014 } -- 4-Port 1000BASE-R-SFP+ Optical Multi-functional Interface Card
ibevtModuleRtCN-MIC-X-GP8                OBJECT IDENTIFIER ::= { ibevtModuleRouterType 5015 } -- 8-Port 1000BASE-X Optical Multi-functional Interface Card
ibevtModuleRtCN-MIC-X-GT8                OBJECT IDENTIFIER ::= { ibevtModuleRouterType 5016 } -- 8-Port 10/100/1000BASE-T Electronic Multi-functional Interface Card

-- ibevtModuleSwitchType cards are slot-cards specific to the Switch.
ibevtModuleSwitchType  OBJECT IDENTIFIER ::= { ibevtModule 4 }

--ibevtModuleNULL(0),
ibevtModuleSw-10OR100M                    OBJECT IDENTIFIER ::= { ibevtModuleSwitchType 1 }
ibevtModuleSw-1000BASE-LX-SM              OBJECT IDENTIFIER ::= { ibevtModuleSwitchType 2 }
ibevtModuleSw-1000BASE-SX-MM              OBJECT IDENTIFIER ::= { ibevtModuleSwitchType 3 }
ibevtModuleSw-1000BASE-TX                 OBJECT IDENTIFIER ::= { ibevtModuleSwitchType 4 }
ibevtModuleSw-100M-SINGLEMODE-FX          OBJECT IDENTIFIER ::= { ibevtModuleSwitchType 5 }
ibevtModuleSw-100M-MULTIMODE-FX           OBJECT IDENTIFIER ::= { ibevtModuleSwitchType 6 }
ibevtModuleSw-100M-100BASE-TX             OBJECT IDENTIFIER ::= { ibevtModuleSwitchType 7 }
ibevtModuleSw-100M-HUB                    OBJECT IDENTIFIER ::= { ibevtModuleSwitchType 8 }
ibevtModuleSw-VDSL                        OBJECT IDENTIFIER ::= { ibevtModuleSwitchType 9 }
ibevtModuleSw-STACK                       OBJECT IDENTIFIER ::= { ibevtModuleSwitchType 10 }
ibevtModuleSw-1000BASE-ZENITH-FX          OBJECT IDENTIFIER ::= { ibevtModuleSwitchType 11 }
ibevtModuleSw-1000BASE-LONG-FX            OBJECT IDENTIFIER ::= { ibevtModuleSwitchType 12 }
ibevtModuleSw-ADSL                        OBJECT IDENTIFIER ::= { ibevtModuleSwitchType 13 }
ibevtModuleSw-4T10OR100-4FX100SM          OBJECT IDENTIFIER ::= { ibevtModuleSwitchType 14 }
ibevtModuleSw-4T10OR100-4FX100MM          OBJECT IDENTIFIER ::= { ibevtModuleSwitchType 15 }
ibevtModuleSw-VSPL                        OBJECT IDENTIFIER ::= { ibevtModuleSwitchType 16 }
ibevtModuleSw-ASPL                        OBJECT IDENTIFIER ::= { ibevtModuleSwitchType 17 }
ibevtModuleSw-1000M-SFP                   OBJECT IDENTIFIER ::= { ibevtModuleSwitchType 18 }
ibevtModuleSw-LS82O2CM                    OBJECT IDENTIFIER ::= { ibevtModuleSwitchType 19 }
ibevtModuleSw-LS82P2CM                    OBJECT IDENTIFIER ::= { ibevtModuleSwitchType 20 }
ibevtModuleSw-LS82O4GM                    OBJECT IDENTIFIER ::= { ibevtModuleSwitchType 21 }
ibevtModuleSw-LS82GB4C                    OBJECT IDENTIFIER ::= { ibevtModuleSwitchType 22 }
ibevtModuleSw-LS82GT4C                    OBJECT IDENTIFIER ::= { ibevtModuleSwitchType 23 }
ibevtModuleSw-LS82ST4C                    OBJECT IDENTIFIER ::= { ibevtModuleSwitchType 24 }
ibevtModuleSw-BOARD-LS82DSPU              OBJECT IDENTIFIER ::= { ibevtModuleSwitchType 25 }
ibevtModuleSw-BOARD-LS81GP8U              OBJECT IDENTIFIER ::= { ibevtModuleSwitchType 26 }
ibevtModuleSw-BOARD-LS82GT20              OBJECT IDENTIFIER ::= { ibevtModuleSwitchType 27 }
ibevtModuleSw-BOARD-LS82FE48              OBJECT IDENTIFIER ::= { ibevtModuleSwitchType 28 }
ibevtModuleSw-LS82T24B                    OBJECT IDENTIFIER ::= { ibevtModuleSwitchType 29 }
ibevtModuleSw-LSB1SRPA                    OBJECT IDENTIFIER ::= { ibevtModuleSwitchType 30 }
ibevtModuleSw-LSB1FT48A                   OBJECT IDENTIFIER ::= { ibevtModuleSwitchType 31 }
ibevtModuleSw-LSB1FT48B                   OBJECT IDENTIFIER ::= { ibevtModuleSwitchType 32 }
ibevtModuleSw-LSB1F48GA                   OBJECT IDENTIFIER ::= { ibevtModuleSwitchType 33 }
ibevtModuleSw-LSB1F48GB                   OBJECT IDENTIFIER ::= { ibevtModuleSwitchType 34 }
ibevtModuleSw-LSB1FP20A                   OBJECT IDENTIFIER ::= { ibevtModuleSwitchType 35 }
ibevtModuleSw-LSB1FP20B                   OBJECT IDENTIFIER ::= { ibevtModuleSwitchType 36 }
ibevtModuleSw-FT48A                       OBJECT IDENTIFIER ::= { ibevtModuleSwitchType 37 }
ibevtModuleSw-GP4U                        OBJECT IDENTIFIER ::= { ibevtModuleSwitchType 38 }
ibevtModuleSw-GP2U                        OBJECT IDENTIFIER ::= { ibevtModuleSwitchType 39 }
ibevtModuleSw-TGX1A                       OBJECT IDENTIFIER ::= { ibevtModuleSwitchType 40 }
ibevtModuleSw-1000BASE-LX-SM-IR-SC        OBJECT IDENTIFIER ::= { ibevtModuleSwitchType 41 }
ibevtModuleSw-1000BASE-SX-MM-SR-SC        OBJECT IDENTIFIER ::= { ibevtModuleSwitchType 42 }
ibevtModuleSw-1000BASE-T-RJ45             OBJECT IDENTIFIER ::= { ibevtModuleSwitchType 43 }
ibevtModuleSw-100BASE-FX-SM-IR-SC         OBJECT IDENTIFIER ::= { ibevtModuleSwitchType 44 }
ibevtModuleSw-100BASE-FX-MM-SR-SC         OBJECT IDENTIFIER ::= { ibevtModuleSwitchType 45 }
ibevtModuleSw-GIGA-STACK-1M-PC            OBJECT IDENTIFIER ::= { ibevtModuleSwitchType 46 }
ibevtModuleSw-1000BASE-LX-SM-VLR-LC       OBJECT IDENTIFIER ::= { ibevtModuleSwitchType 47 }
ibevtModuleSw-1000BASE-LX-SM-LR-LC        OBJECT IDENTIFIER ::= { ibevtModuleSwitchType 48 }
ibevtModuleSw-100BASE-FX-SM-LR-SC         OBJECT IDENTIFIER ::= { ibevtModuleSwitchType 49 }
ibevtModuleSw-1000BASE-X-GBIC             OBJECT IDENTIFIER ::= { ibevtModuleSwitchType 50 }
ibevtModuleSw-100M-SINGLEMODE-FX-LC       OBJECT IDENTIFIER ::= { ibevtModuleSwitchType 51 }
ibevtModuleSw-100M-MULTIMODE-FX-LC        OBJECT IDENTIFIER ::= { ibevtModuleSwitchType 52 }
ibevtModuleSw-1000BASE-4SFP               OBJECT IDENTIFIER ::= { ibevtModuleSwitchType 53 }
ibevtModuleSw-1000BASE-4GBIC              OBJECT IDENTIFIER ::= { ibevtModuleSwitchType 54 }
ibevtModuleSw-1000BASE-FIXED-4SFP         OBJECT IDENTIFIER ::= { ibevtModuleSwitchType 55 }
ibevtModuleSw-1000BASE-FIXED-4GBIC        OBJECT IDENTIFIER ::= { ibevtModuleSwitchType 56 }
ibevtModuleSw-LSB1GP12A                   OBJECT IDENTIFIER ::= { ibevtModuleSwitchType 57 }
ibevtModuleSw-LSB1GP12B                   OBJECT IDENTIFIER ::= { ibevtModuleSwitchType 58 }
ibevtModuleSw-LSB1TGX1A                   OBJECT IDENTIFIER ::= { ibevtModuleSwitchType 59 }
ibevtModuleSw-LSB1TGX1B                   OBJECT IDENTIFIER ::= { ibevtModuleSwitchType 60 }
ibevtModuleSw-LSB1P4G8A                   OBJECT IDENTIFIER ::= { ibevtModuleSwitchType 61 }
ibevtModuleSw-LSB1P4G8B                   OBJECT IDENTIFIER ::= { ibevtModuleSwitchType 62 }
ibevtModuleSw-LSB1A4G8A                   OBJECT IDENTIFIER ::= { ibevtModuleSwitchType 63 }
ibevtModuleSw-LSB1A4G8B                   OBJECT IDENTIFIER ::= { ibevtModuleSwitchType 64 }
ibevtModuleSw-FT48C                       OBJECT IDENTIFIER ::= { ibevtModuleSwitchType 65 }
ibevtModuleSw-FP20                        OBJECT IDENTIFIER ::= { ibevtModuleSwitchType 66 }
ibevtModuleSw-BOARD-LS81FT48              OBJECT IDENTIFIER ::= { ibevtModuleSwitchType 67 }
ibevtModuleSw-BOARD-LS81GB8U              OBJECT IDENTIFIER ::= { ibevtModuleSwitchType 68 }
ibevtModuleSw-BOARD-LS81GT8U              OBJECT IDENTIFIER ::= { ibevtModuleSwitchType 69 }
ibevtModuleSw-BOARD-LS81FS24              OBJECT IDENTIFIER ::= { ibevtModuleSwitchType 70 }
ibevtModuleSw-BOARD-LS81FM24              OBJECT IDENTIFIER ::= { ibevtModuleSwitchType 71 }
ibevtModuleSw-BOARD-LS82GP20              OBJECT IDENTIFIER ::= { ibevtModuleSwitchType 72 }
ibevtModuleSw-LSB1SRPB                    OBJECT IDENTIFIER ::= { ibevtModuleSwitchType 73 }
ibevtModuleSw-LSB1F32GA                   OBJECT IDENTIFIER ::= { ibevtModuleSwitchType 74 }
ibevtModuleSw-LSB1F32GB                   OBJECT IDENTIFIER ::= { ibevtModuleSwitchType 75 }
ibevtModuleSw-LSB2FT48A                   OBJECT IDENTIFIER ::= { ibevtModuleSwitchType 76 }
ibevtModuleSw-LSB2FT48B                   OBJECT IDENTIFIER ::= { ibevtModuleSwitchType 77 }
ibevtModuleSw-LSB1GT12A                   OBJECT IDENTIFIER ::= { ibevtModuleSwitchType 78 }
ibevtModuleSw-LSB1GT12B                   OBJECT IDENTIFIER ::= { ibevtModuleSwitchType 79 }
ibevtModuleSw-PC4U                        OBJECT IDENTIFIER ::= { ibevtModuleSwitchType 80 }
ibevtModuleSw-FT32A                       OBJECT IDENTIFIER ::= { ibevtModuleSwitchType 81 }
ibevtModuleSw-GT4U                        OBJECT IDENTIFIER ::= { ibevtModuleSwitchType 82 }
ibevtModuleSw-BOARD-LS83FP20A             OBJECT IDENTIFIER ::= { ibevtModuleSwitchType 83 }
ibevtModuleSw-BOARD-LS82HGMU              OBJECT IDENTIFIER ::= { ibevtModuleSwitchType 84 }
ibevtModuleSw-LSB1GP8TB                   OBJECT IDENTIFIER ::= { ibevtModuleSwitchType 85 }
ibevtModuleSw-LSB1GP8TC                   OBJECT IDENTIFIER ::= { ibevtModuleSwitchType 86 }
ibevtModuleSw-LSB1GT8PB                   OBJECT IDENTIFIER ::= { ibevtModuleSwitchType 87 }
ibevtModuleSw-LSB1GT8PC                   OBJECT IDENTIFIER ::= { ibevtModuleSwitchType 88 }
ibevtModuleSw-LSB1FT48C                   OBJECT IDENTIFIER ::= { ibevtModuleSwitchType 89 }
ibevtModuleSw-LSB1FP20C                   OBJECT IDENTIFIER ::= { ibevtModuleSwitchType 90 }
ibevtModuleSw-LSB1F32GC                   OBJECT IDENTIFIER ::= { ibevtModuleSwitchType 91 }
ibevtModuleSw-LSB1GT12C                   OBJECT IDENTIFIER ::= { ibevtModuleSwitchType 92 }
ibevtModuleSw-LSB1GP12C                   OBJECT IDENTIFIER ::= { ibevtModuleSwitchType 93 }
ibevtModuleSw-LSB1P4G8C                   OBJECT IDENTIFIER ::= { ibevtModuleSwitchType 94 }
ibevtModuleSw-LSB1TGX1C                   OBJECT IDENTIFIER ::= { ibevtModuleSwitchType 95 }
ibevtModuleSw-LSB1GT24B                   OBJECT IDENTIFIER ::= { ibevtModuleSwitchType 96 }
ibevtModuleSw-LSB1GT24C                   OBJECT IDENTIFIER ::= { ibevtModuleSwitchType 97 }
ibevtModuleSw-LSB1GP24B                   OBJECT IDENTIFIER ::= { ibevtModuleSwitchType 98 }
ibevtModuleSw-LSB1GP24C                   OBJECT IDENTIFIER ::= { ibevtModuleSwitchType 99 }
ibevtModuleSw-LSB1XP2B                    OBJECT IDENTIFIER ::= { ibevtModuleSwitchType 100 }
ibevtModuleSw-LSB1XP2C                    OBJECT IDENTIFIER ::= { ibevtModuleSwitchType 101 }
ibevtModuleSw-LSB1GV48B                   OBJECT IDENTIFIER ::= { ibevtModuleSwitchType 102 }
ibevtModuleSw-LSB1GV48C                   OBJECT IDENTIFIER ::= { ibevtModuleSwitchType 103 }
ibevtModuleSw-LSB1SRPC                    OBJECT IDENTIFIER ::= { ibevtModuleSwitchType 104 }
ibevtModuleSw-LSB1SRP1N0                  OBJECT IDENTIFIER ::= { ibevtModuleSwitchType 105 }
ibevtModuleSw-LSB1SRP1N1                  OBJECT IDENTIFIER ::= { ibevtModuleSwitchType 106 }
ibevtModuleSw-LSB1SRP1N2                  OBJECT IDENTIFIER ::= { ibevtModuleSwitchType 107 }
ibevtModuleSw-GT24                        OBJECT IDENTIFIER ::= { ibevtModuleSwitchType 108 }
ibevtModuleSw-GP24                        OBJECT IDENTIFIER ::= { ibevtModuleSwitchType 109 }
ibevtModuleSw-XP2                         OBJECT IDENTIFIER ::= { ibevtModuleSwitchType 110 }
ibevtModuleSw-GV48                        OBJECT IDENTIFIER ::= { ibevtModuleSwitchType 111 }
ibevtModuleSw-LSG1GP8U                    OBJECT IDENTIFIER ::= { ibevtModuleSwitchType 112 }
ibevtModuleSw-LSG1GT8U                    OBJECT IDENTIFIER ::= { ibevtModuleSwitchType 113 }
ibevtModuleSw-LSG1TG1U                    OBJECT IDENTIFIER ::= { ibevtModuleSwitchType 114 }
ibevtModuleSw-LSG1TD1U                    OBJECT IDENTIFIER ::= { ibevtModuleSwitchType 115 }
ibevtModuleSw-LSB2FT48C                   OBJECT IDENTIFIER ::= { ibevtModuleSwitchType 116 } -- 48-Ports 100Base-TX Ethernet Interface module C
ibevtModuleSw-LSB1GT48B                   OBJECT IDENTIFIER ::= { ibevtModuleSwitchType 117 } -- 48-Ports 10/100/1000Base-T Ethernet Interface Module B
ibevtModuleSw-LSB1GT48C                   OBJECT IDENTIFIER ::= { ibevtModuleSwitchType 118 } -- 48-Ports 10/100/1000Base-T Ethernet Interface Module C
ibevtModuleSw-LS81GT48                    OBJECT IDENTIFIER ::= { ibevtModuleSwitchType 119 } -- 48 Port Gigabit Ethernet Electric Interface Unit
ibevtModuleSw-LS81SRPG0                   OBJECT IDENTIFIER ::= { ibevtModuleSwitchType 120 } -- Salience III, Switch and Route Processing Board
ibevtModuleSw-LS81SRPG1                   OBJECT IDENTIFIER ::= { ibevtModuleSwitchType 121 } -- Salience III Plus
ibevtModuleSw-LS81SRPG2                   OBJECT IDENTIFIER ::= { ibevtModuleSwitchType 122 } -- Salience III Lite
ibevtModuleSw-LS81SRPG3                   OBJECT IDENTIFIER ::= { ibevtModuleSwitchType 123 } -- Salience III Edge

ibevtModuleSw-SR01SRPUB                   OBJECT IDENTIFIER ::= { ibevtModuleSwitchType 125 } -- Switching and Route Processing Unit
ibevtModuleSw-SR01SRPUA                   OBJECT IDENTIFIER ::= { ibevtModuleSwitchType 126 } -- Switching and Route Processing Unit
ibevtModuleSw-SR01GP12L                   OBJECT IDENTIFIER ::= { ibevtModuleSwitchType 127 } -- 12-Port 1000Base-X Ethernet SFP Optical Interface Line Card(L)
ibevtModuleSw-SR01GP12W                   OBJECT IDENTIFIER ::= { ibevtModuleSwitchType 128 } -- 12-Port 1000Base-X Ethernet SFP Optical Interface Line Card(W)
ibevtModuleSw-SR01FT48L                   OBJECT IDENTIFIER ::= { ibevtModuleSwitchType 129 } -- 48-Port 10/100Base-TX Ethernet RJ45 Electrical Interface Line Card (L)
ibevtModuleSw-SR01FT48W                   OBJECT IDENTIFIER ::= { ibevtModuleSwitchType 130 } -- 48-Port 10/100Base-TX Ethernet RJ45 Electrical Interface Line Card (W)
ibevtModuleSw-SR01XK1W                    OBJECT IDENTIFIER ::= { ibevtModuleSwitchType 131 } -- 1-Port 10GBase-R Ethernet XENPAK Optical Interface Line Card (W)
ibevtModuleSw-SR01FP20W                   OBJECT IDENTIFIER ::= { ibevtModuleSwitchType 132 } -- 20-Port 100Base-FX Ethernet SFP Optical Interface Line Card (W)
ibevtModuleSw-SR01GT12W                   OBJECT IDENTIFIER ::= { ibevtModuleSwitchType 133 } -- 12-Port 10/100/1000Base-T Ethernet RJ45 Electrical Interface Line Card (W)
ibevtModuleSw-SR01F32GL                   OBJECT IDENTIFIER ::= { ibevtModuleSwitchType 134 } -- 32-Port 10/100Base-TX Ethernet RJ45 Electrical Interface + 4-Port 1000Base-X Ethernet SFP Optical interface Line Card (L)
ibevtModuleSw-SR01F32GW                   OBJECT IDENTIFIER ::= { ibevtModuleSwitchType 135 } -- 32-Port 10/100Base-TX Ethernet RJ45 Electrical Interface  + 4-Port 1000Base-X  Ethernet SFP Optical interface Line Card (W)
ibevtModuleSw-SR01GT8PL                   OBJECT IDENTIFIER ::= { ibevtModuleSwitchType 136 } -- 8-Port 10/100/1000Base-T Ethernet RJ45 Electrical Interface + 4-Port 1000Base-X Ethernet SFP Optical Line Card (L)
ibevtModuleSw-SR01GT8PW                   OBJECT IDENTIFIER ::= { ibevtModuleSwitchType 137 } -- 8-Port 10/100/1000Base-T Ethernet RJ45 Electrical Interface + 4-Port 1000Base-X Ethernet SFP Optical Line Card (W)
ibevtModuleSw-SR01P4G8W                   OBJECT IDENTIFIER ::= { ibevtModuleSwitchType 138 } -- 4-Port 155M POS Optical Interface + 8-Port 1000Base-X Ethernet SFP Optical Interface Line Card (W)
ibevtModuleSw-LSA1FP8U                    OBJECT IDENTIFIER ::= { ibevtModuleSwitchType 139 } -- 8 Ports 100Base-FX Ethernet SFP Card
ibevtModuleSw-LSB1SP4B                    OBJECT IDENTIFIER ::= { ibevtModuleSwitchType 140 } -- 4-Port OC-48 POS SFP Optical Interface Board B
ibevtModuleSw-LSB1SP4C                    OBJECT IDENTIFIER ::= { ibevtModuleSwitchType 141 } -- 4-Port OC-48 POS SFP Optical Interface Board C
ibevtModuleSw-LSB1UP1B                    OBJECT IDENTIFIER ::= { ibevtModuleSwitchType 142 } -- 1-Port OC-192 POS XFP Optical Interface Board B
ibevtModuleSw-LSB1UP1C                    OBJECT IDENTIFIER ::= { ibevtModuleSwitchType 143 } -- 1-Port OC-192 POS XFP Optical Interface Board C
ibevtModuleSw-LSB1XP4B                    OBJECT IDENTIFIER ::= { ibevtModuleSwitchType 144 } -- 4-Port 10GBase Ethernet XFP Optical Interface Board B
ibevtModuleSw-LSB1XP4C                    OBJECT IDENTIFIER ::= { ibevtModuleSwitchType 145 } -- 4-Port 10GBase Ethernet XFP Optical Interface Board C
ibevtModuleSw-SP4                         OBJECT IDENTIFIER ::= { ibevtModuleSwitchType 146 } -- 4-Port OC-48 POS SFP Optical Interface Module
ibevtModuleSw-UP1                         OBJECT IDENTIFIER ::= { ibevtModuleSwitchType 147 } -- 1-Port OC-192 POS XFP Optical Interface Module
ibevtModuleSw-XP4                         OBJECT IDENTIFIER ::= { ibevtModuleSwitchType 148 } -- 4-Port 10GBase Ethernet XFP Optical Interface Module
ibevtModuleSw-LS81VSNP                    OBJECT IDENTIFIER ::= { ibevtModuleSwitchType 149 } -- VerSatile Network Processing Board
ibevtModuleSw-LS81T12P                    OBJECT IDENTIFIER ::= { ibevtModuleSwitchType 150 } -- 12-Port 1000Base-T Gigabit Ethernet Interface(RJ45)+4-Port 1000BASE-X  Gigabit Ethernet Optical Interface Board(SFP,LC)
ibevtModuleSw-LS81P12T                    OBJECT IDENTIFIER ::= { ibevtModuleSwitchType 151 } -- 12-Port 1000BASE-X Gigabit Ethernet Optical Interface(SFP,LC)+4-Port 1000BASE-T Gigabit Ethernet Interface Board(RJ45)
ibevtModuleSw-LS81GP8UB                   OBJECT IDENTIFIER ::= { ibevtModuleSwitchType 152 } -- 8-Port 1000M Ethernet Optical Interface Board(SFP,LC),LC Connector
ibevtModuleSw-LS81FT48E                   OBJECT IDENTIFIER ::= { ibevtModuleSwitchType 153 } -- 48-Port 100M Ethernet Electrical Interface Switch Unit(RJ45)
ibevtModuleSw-LS81GP4UB                   OBJECT IDENTIFIER ::= { ibevtModuleSwitchType 154 } -- 4-Port 1000M Ethernet Optical Interface Board(SFP,LC)
ibevtModuleSw-LS81GT8UE                   OBJECT IDENTIFIER ::= { ibevtModuleSwitchType 155 } -- 8-Port 1000M Ethernet Electrical Interface Switch Unit (RJ45)
ibevtModuleSw-LS81GT48A                   OBJECT IDENTIFIER ::= { ibevtModuleSwitchType 156 } -- 48 Port Gigabit Ethernet Electric Interface Unit
ibevtModuleSw-LS81FP48                    OBJECT IDENTIFIER ::= { ibevtModuleSwitchType 157 } -- 48 Port 100M Ethernet Optical Interface Board(SFP,LC)
ibevtModuleSw-LSB1XK1B                    OBJECT IDENTIFIER ::= { ibevtModuleSwitchType 158 } -- 1-Port 10GBase-R Ethernet XENPAK Optical Interface Board B
ibevtModuleSw-LSB1XK1C                    OBJECT IDENTIFIER ::= { ibevtModuleSwitchType 159 } -- 1-Port 10GBase-R Ethernet XENPAK Optical Interface Board C
ibevtModuleSw-SR01SRPUC                   OBJECT IDENTIFIER ::= { ibevtModuleSwitchType 160 } -- Switching and Route Processing Unit C
ibevtModuleSw-SR01SRPUD                   OBJECT IDENTIFIER ::= { ibevtModuleSwitchType 161 } -- Switching and Route Processing Unit D
ibevtModuleSw-SR01SRPUE                   OBJECT IDENTIFIER ::= { ibevtModuleSwitchType 162 } -- Switching and Route Processing Unit E
ibevtModuleSw-LSB1SRP1N3                  OBJECT IDENTIFIER ::= { ibevtModuleSwitchType 163 } -- Switching and Route Process Unit, Clock Module
ibevtModuleSw-LSB1VP2B                    OBJECT IDENTIFIER ::= { ibevtModuleSwitchType 164 } -- 2*10G Resilient Packet Ring Interface Line Card
ibevtModuleSw-LSB1NATB                    OBJECT IDENTIFIER ::= { ibevtModuleSwitchType 165 } -- NAT Service Processing Card (B)
ibevtModuleSw-LSB1VPNB                    OBJECT IDENTIFIER ::= { ibevtModuleSwitchType 166 } -- VPN Service Processing Card (B)
ibevtModuleSw-LSGP8P                      OBJECT IDENTIFIER ::= { ibevtModuleSwitchType 167 } -- 8-Port 1000M SFP Module
ibevtModuleSw-LSXK1P                      OBJECT IDENTIFIER ::= { ibevtModuleSwitchType 168 } -- 1-Port 10G Xenpak Module
ibevtModuleSw-LSXP2P                      OBJECT IDENTIFIER ::= { ibevtModuleSwitchType 169 } -- 2-Port 10G XFP Module
ibevtModuleSw-LS81FT48F                   OBJECT IDENTIFIER ::= { ibevtModuleSwitchType 170 } -- 48-Port 100M Ethernet Electrical Interface Switch Unit(RJ45)
ibevtModuleSw-LS81PT8G                    OBJECT IDENTIFIER ::= { ibevtModuleSwitchType 171 } -- 8 Port 1000BASE-X Gigabit Passive Optical Line Interface Board
ibevtModuleSw-LS81PT4G                    OBJECT IDENTIFIER ::= { ibevtModuleSwitchType 172 } -- 4 Port 1000BASE-X Gigabit Passive Optical Line Interface Board
ibevtModuleSw-LSSTK24G                    OBJECT IDENTIFIER ::= { ibevtModuleSwitchType 173 } -- 24G Stacking Ports Module
ibevtModuleSw-LS82GT20A                   OBJECT IDENTIFIER ::= { ibevtModuleSwitchType 174 } -- 20-Port 1000Base-T Gigabit Ethernet Electrical Interface Board(RJ45), BCM5697
ibevtModuleSw-LS82GP20A                   OBJECT IDENTIFIER ::= { ibevtModuleSwitchType 175 } -- 20-Port 1000BASE-X Gigabit Ethernet Optical Interface Board(SFP,LC), BCM5697
ibevtModuleSw-LS81TGX1C                   OBJECT IDENTIFIER ::= { ibevtModuleSwitchType 176 } -- 1-Port 10G Base-R Ethernet Board
ibevtModuleSw-VP2                         OBJECT IDENTIFIER ::= { ibevtModuleSwitchType 177 } -- 2*10G Resilient Packet Ring Interface Module
ibevtModuleSw-LSA1FB8U                    OBJECT IDENTIFIER ::= { ibevtModuleSwitchType 178 } -- 8-Port 100Base-Fx BIDI Ethernet Board
ibevtModuleSw-LS81T12PE                   OBJECT IDENTIFIER ::= { ibevtModuleSwitchType 179 } -- 12-Port 1000Base-T GE Interface+4-Port 1000BASE-X GE Optical Interface Board(SFP,LC)
ibevtModuleSw-LS81P12TE                   OBJECT IDENTIFIER ::= { ibevtModuleSwitchType 180 } -- 12-Port 1000BASE-X GE Optical Interface(SFP,LC)+4-Port 1000 BASE-T GE Interface Board(RJ45)
ibevtModuleSw-LSB1SRP2N0                  OBJECT IDENTIFIER ::= { ibevtModuleSwitchType 181 } -- Switching and Route Process Unit,12*LPU
ibevtModuleSw-LSB1SRP2N3                  OBJECT IDENTIFIER ::= { ibevtModuleSwitchType 182 } -- Switching and Route Process Unit, Clock Module
ibevtModuleSw-LSB1GV48DB                  OBJECT IDENTIFIER ::= { ibevtModuleSwitchType 183 } -- 48 Ports 1000Base-T Ethernet Interface Line Card with POE(DB)
ibevtModuleSw-LSB1FW8B                    OBJECT IDENTIFIER ::= { ibevtModuleSwitchType 184 } -- Firewall Service Processing Board with 8GE (B)
ibevtModuleSw-LSB1IPSEC8B                 OBJECT IDENTIFIER ::= { ibevtModuleSwitchType 185 } -- VPN Service Processing Board with 8GE (B)
ibevtModuleSw-LSB1IDSB                    OBJECT IDENTIFIER ::= { ibevtModuleSwitchType 186 } -- IDS Service Processing Board (B)
ibevtModuleSw-LSB1IPSB                    OBJECT IDENTIFIER ::= { ibevtModuleSwitchType 187 } -- IPS Service Processing Board (B)
ibevtModuleSw-LSB2FT48CA                  OBJECT IDENTIFIER ::= { ibevtModuleSwitchType 188 } -- 48 Ports 100Base-TX Ethernet Line Card (CA)
ibevtModuleSw-LSB1FP20CA                  OBJECT IDENTIFIER ::= { ibevtModuleSwitchType 189 } -- 20 Ports 100Base-FX Ethernet Interface Service Card (CA)
ibevtModuleSw-LSB1F32GCA                  OBJECT IDENTIFIER ::= { ibevtModuleSwitchType 190 } -- 32 Ports FE and 4 Ports GE Line Card(CA)
ibevtModuleSw-LSB1P4G8CA                  OBJECT IDENTIFIER ::= { ibevtModuleSwitchType 191 } -- 4 Ports OC-3c POS and 8 Ports GE Line Card(CA)
ibevtModuleSw-LSB1GT12CA                  OBJECT IDENTIFIER ::= { ibevtModuleSwitchType 192 } -- 12 Ports 1000Base-T Ethernet Interface Line Card(CA)
ibevtModuleSw-LSB1GT24CA                  OBJECT IDENTIFIER ::= { ibevtModuleSwitchType 193 } -- 24 Ports 1000Base-T Ethernet Interface Line Card(CA)
ibevtModuleSw-LSB1GP12CA                  OBJECT IDENTIFIER ::= { ibevtModuleSwitchType 194 } -- 12 Ports 1000Base Ethernet Optical Interface Service Card(CA)
ibevtModuleSw-LSB1GP24CA                  OBJECT IDENTIFIER ::= { ibevtModuleSwitchType 195 } -- 24 Ports 1000Base-X Ethernet Interface Line Card (CA)
ibevtModuleSw-LSB1GT8PCA                  OBJECT IDENTIFIER ::= { ibevtModuleSwitchType 196 } -- 8 Ports 1000Base-T Ethernet Interface & 4 Ports 1000Base-X Ethernet SFP Interface Line Card(CA)
ibevtModuleSw-LSB1XP2CA                   OBJECT IDENTIFIER ::= { ibevtModuleSwitchType 197 } -- 2-Port 10GBase-R/W Ethernet XFP Optical Interface Card(CA)
ibevtModuleSw-LSB1XK1CA                   OBJECT IDENTIFIER ::= { ibevtModuleSwitchType 198 } -- 10GBase-R Ethernet XENPAK Optical Interface Line Card(CA)
ibevtModuleSw-LSB1XP4CA                   OBJECT IDENTIFIER ::= { ibevtModuleSwitchType 199 } -- 4-Port 10GBase-R/X Ethernet Optical Interface Line Card(CA)
ibevtModuleSw-LSB1UP1CA                   OBJECT IDENTIFIER ::= { ibevtModuleSwitchType 200 } -- Single Port OC-192c POS XFP Optical Interface Card(CA)
ibevtModuleSw-LSB1SP4CA                   OBJECT IDENTIFIER ::= { ibevtModuleSwitchType 201 } -- 4-Port OC-48c POS SFP Optical Interface Card(CA)
ibevtModuleSw-LSB1VP2CA                   OBJECT IDENTIFIER ::= { ibevtModuleSwitchType 202 } -- 2*10G RPR Process Unit(CA)
ibevtModuleSw-SR01FT48WA                  OBJECT IDENTIFIER ::= { ibevtModuleSwitchType 203 } -- 48 Ports 100Base-TX Ethernet Line Card (WA)
ibevtModuleSw-SR01FP20WA                  OBJECT IDENTIFIER ::= { ibevtModuleSwitchType 204 } -- 20 Ports 100Base-FX Ethernet Interface Service Card (WA)
ibevtModuleSw-SR01F32GWA                  OBJECT IDENTIFIER ::= { ibevtModuleSwitchType 205 } -- 32 Ports FE and 4 Ports GE Line Card(WA)
ibevtModuleSw-SR01P4G8WA                  OBJECT IDENTIFIER ::= { ibevtModuleSwitchType 206 } -- 4 Ports OC-3c POS and 8 Ports GE Line Card(WA)
ibevtModuleSw-SR01GT12WA                  OBJECT IDENTIFIER ::= { ibevtModuleSwitchType 207 } -- 12 Ports 1000Base-T Ethernet Interface Line Card(WA)
ibevtModuleSw-SR01GT24WA                  OBJECT IDENTIFIER ::= { ibevtModuleSwitchType 208 } -- 24 Ports 1000Base-T Ethernet Interface Line Card(WA)
ibevtModuleSw-SR01GP12WA                  OBJECT IDENTIFIER ::= { ibevtModuleSwitchType 209 } -- 12 Ports 1000Base Ethernet Optical Interface Service Card(WA)
ibevtModuleSw-SR01GP24WA                  OBJECT IDENTIFIER ::= { ibevtModuleSwitchType 210 } -- 24 Ports 1000Base-X Ethernet Interface Line Card (WA)
ibevtModuleSw-SR01GT8PWA                  OBJECT IDENTIFIER ::= { ibevtModuleSwitchType 211 } -- 8 Ports 1000Base-T Ethernet Interface & 4 Ports 1000Base-X Ethernet SFP Interface Line Card(WA)
ibevtModuleSw-SR01XP2WA                   OBJECT IDENTIFIER ::= { ibevtModuleSwitchType 212 } -- 2-Port 10GBase-R/W Ethernet XFP Optical Interface Card(WA)
ibevtModuleSw-SR01XK1WA                   OBJECT IDENTIFIER ::= { ibevtModuleSwitchType 213 } -- 10GBase-R Ethernet XENPAK Optical Interface Line Card(WA)
ibevtModuleSw-SR01UP1WA                   OBJECT IDENTIFIER ::= { ibevtModuleSwitchType 214 } -- Single Port OC-192c POS XFP Optical Interface Card(WA)
ibevtModuleSw-SR01SP4WA                   OBJECT IDENTIFIER ::= { ibevtModuleSwitchType 215 } -- 4-Port OC-48c POS SFP Optical Interface Card(WA)
ibevtModuleSw-GP8U                        OBJECT IDENTIFIER ::= { ibevtModuleSwitchType 216 } -- 8-Port 1000Base-X SFP Optical Interface Module
ibevtModuleSw-LSEXP1P                     OBJECT IDENTIFIER ::= { ibevtModuleSwitchType 217 } -- Single 10G SFP Optical Interface Module
ibevtModuleSw-LSEXK1P                     OBJECT IDENTIFIER ::= { ibevtModuleSwitchType 218 } -- Single 10G XENPAK Interface Module
ibevtModuleSw-LSEXS1P                     OBJECT IDENTIFIER ::= { ibevtModuleSwitchType 219 } -- Single 10G STACK Interface Module
ibevtModuleSw-LS81GP48                    OBJECT IDENTIFIER ::= { ibevtModuleSwitchType 220 } -- 48-Port 1000M Ethernet Optical Interface Board(SFP,LC),LC Connector
ibevtModuleSw-LS81GT48B                   OBJECT IDENTIFIER ::= { ibevtModuleSwitchType 221 } -- 48-Port 1000Base-T Gigabit Ethernet Interface Board(RJ45)
ibevtModuleSw-LS81T16P                    OBJECT IDENTIFIER ::= { ibevtModuleSwitchType 222 } -- 16-Port 1000Base-T Gigabit Ethernet Interface(RJ45) + 8-Port 1000BASE-X Gigabit Ethernet Optical Interface Board(SFP,LC)
ibevtModuleSw-LS81T32P                    OBJECT IDENTIFIER ::= { ibevtModuleSwitchType 223 } -- 32-Port 1000Base-T Gigabit Ethernet Interface(RJ45) + 16-Port 1000BASE-X Gigabit Ethernet Optical Interface Board(SFP,LC)
ibevtModuleSw-LS81TGX2                    OBJECT IDENTIFIER ::= { ibevtModuleSwitchType 224 } -- 2-Port 10GBASE Ethernet Interface Board(XFP,LC)
ibevtModuleSw-LS81TGX4                    OBJECT IDENTIFIER ::= { ibevtModuleSwitchType 225 } -- 4-Port 10GBASE Ethernet Interface Module(XFP,LC),XG
ibevtModuleSw-LSB1GV48DA                  OBJECT IDENTIFIER ::= { ibevtModuleSwitchType 226 } -- 48 Ports 1000Base-T Ethernet Interface Line Card with POE(DA)
ibevtModuleSw-SR01GV48VB                  OBJECT IDENTIFIER ::= { ibevtModuleSwitchType 227 } -- 48 Ports 1000Base-T Ethernet Interface Line Card with POE(VB)
ibevtModuleSw-LSB1GT24DB                  OBJECT IDENTIFIER ::= { ibevtModuleSwitchType 228 } -- 24 Ports 1000Base-T Ethernet Interface Line Card(DB)
ibevtModuleSw-LSB1GP24DB                  OBJECT IDENTIFIER ::= { ibevtModuleSwitchType 229 } -- 24 Ports 1000Base-X Ethernet Interface Line Card(DB)
ibevtModuleSw-LSB1GP24DC                  OBJECT IDENTIFIER ::= { ibevtModuleSwitchType 230 } -- 24 Ports 1000Base-X Ethernet Interface Line Card(DC)
ibevtModuleSw-LSB1FW8DB                   OBJECT IDENTIFIER ::= { ibevtModuleSwitchType 231 } -- 8-port 1000BASE-X (SFP) Firewall Service Card(DB)
ibevtModuleSw-LSB1IPSEC8DB                OBJECT IDENTIFIER ::= { ibevtModuleSwitchType 232 } -- 8-port 1000BASE-X (SFP) IPSEC Service Card(DB)
ibevtModuleSw-SR01GT24VB                  OBJECT IDENTIFIER ::= { ibevtModuleSwitchType 233 } -- 24 Ports 1000Base-T Ethernet Interface Line Card(VB)
ibevtModuleSw-SR01GP24VC                  OBJECT IDENTIFIER ::= { ibevtModuleSwitchType 234 } -- 24 Ports 1000Base-X Ethernet Interface Line Card(VC)
ibevtModuleSw-SR01VP2WA                   OBJECT IDENTIFIER ::= { ibevtModuleSwitchType 235 } -- 2*10G RPR Process Unit(WA)
ibevtModuleSw-SR01FW8VB                   OBJECT IDENTIFIER ::= { ibevtModuleSwitchType 236 } -- 8-port 1000BASE-X (SFP) Firewall Service Card(VB)
ibevtModuleSw-SR01IPSEC8VB                OBJECT IDENTIFIER ::= { ibevtModuleSwitchType 237 } -- 8-port 1000BASE-X (SFP) IPSEC Service Card(VB)
ibevtModuleSw-SR01NATL                    OBJECT IDENTIFIER ::= { ibevtModuleSwitchType 238 } -- NAT Service Processing Card (L)
ibevtModuleSw-SR01VPNL                    OBJECT IDENTIFIER ::= { ibevtModuleSwitchType 239 } -- VPN Service Processing Card (L)
ibevtModuleSw-LSB1GP24CB                  OBJECT IDENTIFIER ::= { ibevtModuleSwitchType 240 } -- 24 Ports 1000Base-X Ethernet Interface Line Card(CB)
ibevtModuleSw-LSB1GP48DB                  OBJECT IDENTIFIER ::= { ibevtModuleSwitchType 241 } -- 48-Port Gigabit Ethernet Optical Interface Line Card(DB)
ibevtModuleSw-LSB1XP2CB                   OBJECT IDENTIFIER ::= { ibevtModuleSwitchType 242 } -- 2-Port 10Gigabit Ethernet Optical Interface Card(CB)
ibevtModuleSw-XP4L                        OBJECT IDENTIFIER ::= { ibevtModuleSwitchType 243 } -- 4 Port 1000BASE Optic Interface Module (XFP)
ibevtModuleSw-LSB1XP4LDB                  OBJECT IDENTIFIER ::= { ibevtModuleSwitchType 244 } -- 4-Port 10GBase-R/W Ethernet XFP Optical Interface Line Speed Card(DB)
ibevtModuleSw-LSB1XP4LDC                  OBJECT IDENTIFIER ::= { ibevtModuleSwitchType 245 } -- 4-Port 10GBase-R/W Ethernet XFP Optical Interface Line Speed Card(DC)
ibevtModuleSw-AHP4                        OBJECT IDENTIFIER ::= { ibevtModuleSwitchType 246 } -- 2-Port OC-3 ATM and 2-Port OC-3/12 ATM Interface Module (SFP)
ibevtModuleSw-LSB1AHP4GCA                 OBJECT IDENTIFIER ::= { ibevtModuleSwitchType 247 } -- 2-Port OC-3 ATM and 2-Port OC-3/12 ATM and 8-Port 1000Base-X Ethernet Optical Interface Line Card(CA)
ibevtModuleSw-CLP4                        OBJECT IDENTIFIER ::= { ibevtModuleSwitchType 248 } -- 4 Ports OC-3/STM-1 CPOS Optical Interface Module (SFP)
ibevtModuleSw-LSB1CLP4GCA                 OBJECT IDENTIFIER ::= { ibevtModuleSwitchType 249 } -- 4 Ports OC-3/STM-1 CPOS Optical Interface and 4-Port 1000Base-X Ethernet Optical Interface Line Card(CA)
ibevtModuleSw-ET32                        OBJECT IDENTIFIER ::= { ibevtModuleSwitchType 250 } -- 32-Port Channelized E1/T1 Interface Module
ibevtModuleSw-LSB1ET32GCA                 OBJECT IDENTIFIER ::= { ibevtModuleSwitchType 251 } -- 32-Port Channelized E1/T1 Interface and 4-Port 1000Base-X Ethernet Optical Interface Line Card(CA)
ibevtModuleSw-LSB1IDSDB                   OBJECT IDENTIFIER ::= { ibevtModuleSwitchType 252 } -- Intrusion Detection Service Card(DB)
ibevtModuleSw-LSB1SRP2N1                  OBJECT IDENTIFIER ::= { ibevtModuleSwitchType 253 } -- Switching and Route Processing Board,8*LPU
ibevtModuleSw-BOARD-LS82SRPB              OBJECT IDENTIFIER ::= { ibevtModuleSwitchType 254 }
ibevtModuleSw-BORAD-LS83SRPC              OBJECT IDENTIFIER ::= { ibevtModuleSwitchType 255 }
ibevtModuleSw-Main                        OBJECT IDENTIFIER ::= { ibevtModuleSwitchType 256 }
ibevtModuleSw-LSB1SRP2N2                  OBJECT IDENTIFIER ::= { ibevtModuleSwitchType 257 } -- Switching and Route Processing Board,5*LPU
ibevtModuleSw-LSB1NAMB                    OBJECT IDENTIFIER ::= { ibevtModuleSwitchType 258 } -- NAM Service Processing Card (B)
ibevtModuleSw-RSP2                        OBJECT IDENTIFIER ::= { ibevtModuleSwitchType 259 } -- 2*2.5G Resilient Packet Ring Interface
ibevtModuleSw-LSB1RSP2CA                  OBJECT IDENTIFIER ::= { ibevtModuleSwitchType 260 } -- 2*2.5G Resilient Packet Ring Interface Line Card(CA)
ibevtModuleSw-SR01XP4LVC                  OBJECT IDENTIFIER ::= { ibevtModuleSwitchType 261 } -- 4-Port 10GBase-R/W Ethernet XFP Optical Interface Line Speed Card(VC)
ibevtModuleSw-SR01AHP4GWA                 OBJECT IDENTIFIER ::= { ibevtModuleSwitchType 262 } -- 2-Port OC-3 ATM and 2-Port OC-3/12 ATM and 8-Port 1000Base-X Ethernet Optical Interface Line Card(WA)
ibevtModuleSw-SR01CLP4GWA                 OBJECT IDENTIFIER ::= { ibevtModuleSwitchType 263 } -- 4 Ports OC-3/STM-1 CPOS Optical Interface and 4-Port 1000Base-X Ethernet Optical Interface Line Card(WA)
ibevtModuleSw-SR01ET32GWA                 OBJECT IDENTIFIER ::= { ibevtModuleSwitchType 264 } -- 32-Port Channelized E1/T1 Interface and 4-Port 1000Base-X Ethernet Optical Interface Line Card(WA)
ibevtModuleSw-SR01IDSVB                   OBJECT IDENTIFIER ::= { ibevtModuleSwitchType 265 } -- Intrusion Detection Service Card(VB)
ibevtModuleSw-SR01SRPUF                   OBJECT IDENTIFIER ::= { ibevtModuleSwitchType 266 } -- Switching and Route Processing Board,12*LPU
ibevtModuleSw-SR01NAML                    OBJECT IDENTIFIER ::= { ibevtModuleSwitchType 267 } -- NAM Service Processing Card (L)
ibevtModuleSw-SR01RSP2WA                  OBJECT IDENTIFIER ::= { ibevtModuleSwitchType 268 } -- 2*2.5G Resilient Packet Ring Interface Line Card(WA)
ibevtModuleSw-LSPM1XP1P                   OBJECT IDENTIFIER ::= { ibevtModuleSwitchType 269 } -- 1-Port 10G XFP Module
ibevtModuleSw-LSPM1XP2P                   OBJECT IDENTIFIER ::= { ibevtModuleSwitchType 270 } -- 2-Port 10G XFP Module
ibevtModuleSw-LSPM1CX2P                   OBJECT IDENTIFIER ::= { ibevtModuleSwitchType 271 } -- 2-Port 10G CX4 Module
ibevtModuleSw-STK-1000BASE-T              OBJECT IDENTIFIER ::= { ibevtModuleSwitchType 272 } -- Single Port 1000BASE-T Stack Ethernet Interface Card

--
-- 273 to 299 reserved for other product
--


--
-- 300 to 499 reserved for advanced switches part I
--
ibevtModuleSw-LSB1SRP1M0                  OBJECT IDENTIFIER ::= { ibevtModuleSwitchType 300 } -- Switching and Route Process Unit,2*LPU or 3*LPU
ibevtModuleSw-LSB1SRP1M1                  OBJECT IDENTIFIER ::= { ibevtModuleSwitchType 301 } -- Switching and Route Process Unit
ibevtModuleSw-LSB1GP12DB                  OBJECT IDENTIFIER ::= { ibevtModuleSwitchType 302 } -- 12 Ports 1000Base Ethernet Optical Interface Service Card(DB)
ibevtModuleSw-LSB1GT12DB                  OBJECT IDENTIFIER ::= { ibevtModuleSwitchType 303 } -- 12 Ports 1000Base-T Ethernet Interface Line Card(DB)
ibevtModuleSw-LSB1XK1DB                   OBJECT IDENTIFIER ::= { ibevtModuleSwitchType 304 } -- 10GBase-R Ethernet XENPAK Optical Interface Line Card(DB)
ibevtModuleSw-LSB1XP2DB                   OBJECT IDENTIFIER ::= { ibevtModuleSwitchType 305 } -- 2-Port 10GBase-R/W Ethernet XFP Optical Interface Card(DB)
ibevtModuleSw-LSB1XP2DC                   OBJECT IDENTIFIER ::= { ibevtModuleSwitchType 306 } -- 2-Port 10GBase-R/W Ethernet XFP Optical Interface Card(DC)
ibevtModuleSw-LSB1GT48LDB                 OBJECT IDENTIFIER ::= { ibevtModuleSwitchType 307 } -- 48-Port Gigabit Ethernet RJ45 Electrical Interface Card (DB)
ibevtModuleSw-LSB1XP4TDB                  OBJECT IDENTIFIER ::= { ibevtModuleSwitchType 308 } -- 4-Port 10GBase-R/W Ethernet XFP Optical Interface Line Speed Test Card(DB)
ibevtModuleSw-LSB1XP4TDC                  OBJECT IDENTIFIER ::= { ibevtModuleSwitchType 309 } -- 4-Port 10GBase-R/W Ethernet XFP Optical Interface Line Speed Test Card(DC)
ibevtModuleSw-LSB1RSP2DC                  OBJECT IDENTIFIER ::= { ibevtModuleSwitchType 310 } -- 2*2.5G Resilient Packet Ring Interface Line Card(DC)
ibevtModuleSw-LSB1VP2DC                   OBJECT IDENTIFIER ::= { ibevtModuleSwitchType 311 } -- 2*10G Resilient Packet Ring Process Unit(DC)
ibevtModuleSw-LSB1XP4DB                   OBJECT IDENTIFIER ::= { ibevtModuleSwitchType 312 } -- 4-Port 10GBase-R/X Ethernet Optical Interface Line Card(DB)
ibevtModuleSw-LSB1SRP2E0                  OBJECT IDENTIFIER ::= { ibevtModuleSwitchType 313 } -- Switching and Route Process Unit,12*LPU
ibevtModuleSw-LSB1SRP2E1                  OBJECT IDENTIFIER ::= { ibevtModuleSwitchType 314 } -- Switching and Route Process Unit,8*LPU
ibevtModuleSw-LSB1SRP2E2                  OBJECT IDENTIFIER ::= { ibevtModuleSwitchType 315 } -- Switching and Route Process Unit,5*LPU
ibevtModuleSw-LSB1SRP2E3                  OBJECT IDENTIFIER ::= { ibevtModuleSwitchType 316 } -- Switching and Route Process Unit, Clock module
ibevtModuleSw-SR01SRPUQ                   OBJECT IDENTIFIER ::= { ibevtModuleSwitchType 317 } -- Switching and Route Processing Unit Q
ibevtModuleSw-AHP1                        OBJECT IDENTIFIER ::= { ibevtModuleSwitchType 318 } -- 1-Port OC-12c(3c)/STM-4(1) ATM Optical Interface Module(SFP)
ibevtModuleSw-AHP2                        OBJECT IDENTIFIER ::= { ibevtModuleSwitchType 319 } -- 2-Port OC-12c(3c)/STM-4(1) ATM Optical Interface Module(SFP)
ibevtModuleSw-CLP1                        OBJECT IDENTIFIER ::= { ibevtModuleSwitchType 320 } -- 1-Port OC-3/STM-1 CPOS Optical Interface Module(SFP)
ibevtModuleSw-CLP2                        OBJECT IDENTIFIER ::= { ibevtModuleSwitchType 321 } -- 2-Port OC-3/STM-1 CPOS Optical Interface Module(SFP)
ibevtModuleSw-ET16                        OBJECT IDENTIFIER ::= { ibevtModuleSwitchType 322 } -- 16-Port Channelized E1/T1 Interface Module
ibevtModuleSw-LSB1SRP1NA0                 OBJECT IDENTIFIER ::= { ibevtModuleSwitchType 323 } -- Switching and Route Process Unit,12*LPU
ibevtModuleSw-LSB1SRP1NA1                 OBJECT IDENTIFIER ::= { ibevtModuleSwitchType 324 } -- Switching and Route Process Unit,8*LPU
ibevtModuleSw-LSB1SRP1NA2                 OBJECT IDENTIFIER ::= { ibevtModuleSwitchType 325 } -- Switching and Route Process Unit,5*LPU
ibevtModuleSw-LSB1SRP1NA3                 OBJECT IDENTIFIER ::= { ibevtModuleSwitchType 326 } -- Switching and Route Process Unit, Clock module
ibevtModuleSw-SR01AHP1GWA                 OBJECT IDENTIFIER ::= { ibevtModuleSwitchType 327 } -- 1-Port OC-12c(3c)/STM-4(1) ATM Optical Interface and 4-Port 1000Base-X Ethernet Optical Interface Line Card(WA)
ibevtModuleSw-SR01AHP2GWA                 OBJECT IDENTIFIER ::= { ibevtModuleSwitchType 328 } -- 2-Port OC-12c(3c)/STM-4(1) ATM Optical Interface and 4-Port 1000Base-X Ethernet Optical Interface Line Card(WA)
ibevtModuleSw-SR01CLP1GWA                 OBJECT IDENTIFIER ::= { ibevtModuleSwitchType 329 } -- 1-Port OC-3/STM-1 CPOS Optical Interface and 4-Port 1000Base-X Ethernet Optical Interface Line Card(WA)
ibevtModuleSw-SR01CLP2GWA                 OBJECT IDENTIFIER ::= { ibevtModuleSwitchType 330 } -- 2-Port OC-3/STM-1 CPOS Optical Interface and 4-Port 1000Base-X Ethernet Optical Interface Line Card(WA)
ibevtModuleSw-SR01ET16GWA                 OBJECT IDENTIFIER ::= { ibevtModuleSwitchType 331 } -- 16-Port Channelized E1/T1 Interface and  4-Port 1000Base-X Ethernet Optical Interface Line Card(WA)
ibevtModuleSw-SR01GP12VB                  OBJECT IDENTIFIER ::= { ibevtModuleSwitchType 332 } -- 12-Port Gigabit Ethernet Optical Interface Card(VB)
ibevtModuleSw-SR01XK1VB                   OBJECT IDENTIFIER ::= { ibevtModuleSwitchType 333 } -- 1-Port 10Gigabit Ethernet Optical Interface Card(VB)
ibevtModuleSw-SR01XP2VC                   OBJECT IDENTIFIER ::= { ibevtModuleSwitchType 334 } -- 2-Port 10GBase-RW Ethernet XFP Optical Interface Line Card(VC)
ibevtModuleSw-SR01XP4LVB                  OBJECT IDENTIFIER ::= { ibevtModuleSwitchType 335 } -- 4-Port 10GBase-R/W Ethernet XFP Optical Interface Line Speed Card(VB)
ibevtModuleSw-SR01SRPUEA                  OBJECT IDENTIFIER ::= { ibevtModuleSwitchType 336 } -- Switching and Route Process Unit, Clock Module
ibevtModuleSw-LSB1SRP1N4                  OBJECT IDENTIFIER ::= { ibevtModuleSwitchType 337 } -- Switching and Route Process Unit, 12*LPU
ibevtModuleSw-LSB1SRP1N5                  OBJECT IDENTIFIER ::= { ibevtModuleSwitchType 338 } -- Switching and Route Process Unit, 8*LPU
ibevtModuleSw-LSB1SRP1N6                  OBJECT IDENTIFIER ::= { ibevtModuleSwitchType 339 } -- Switching and Route Process Unit, 5*LPU
ibevtModuleSw-LSB1SRP1N7                  OBJECT IDENTIFIER ::= { ibevtModuleSwitchType 340 } -- Switching and Route Process Unit, Clock Module
ibevtModuleSw-LSB1SRP2N4                  OBJECT IDENTIFIER ::= { ibevtModuleSwitchType 341 } -- Switching and Route Process Unit, 12*LPU
ibevtModuleSw-LSB1SRP2N5                  OBJECT IDENTIFIER ::= { ibevtModuleSwitchType 342 } -- Switching and Route Process Unit, 8*LPU
ibevtModuleSw-LSB1SRP2N6                  OBJECT IDENTIFIER ::= { ibevtModuleSwitchType 343 } -- Switching and Route Process Unit, 5*LPU
ibevtModuleSw-LSB1SRP2N7                  OBJECT IDENTIFIER ::= { ibevtModuleSwitchType 344 } -- Switching and Route Process Unit, Clock Module
ibevtModuleSw-LSB1SRP1NA4                 OBJECT IDENTIFIER ::= { ibevtModuleSwitchType 345 } -- Switching and Route Process Unit, 12*LPU
ibevtModuleSw-LSB1SRP1NA5                 OBJECT IDENTIFIER ::= { ibevtModuleSwitchType 346 } -- Switching and Route Process Unit, 8*LPU
ibevtModuleSw-LSB1SRP1NA6                 OBJECT IDENTIFIER ::= { ibevtModuleSwitchType 347 } -- Switching and Route Process Unit, 5*LPU
ibevtModuleSw-LSB1SRP1NA7                 OBJECT IDENTIFIER ::= { ibevtModuleSwitchType 348 } -- Switching and Route Process Unit, Clock Module
ibevtModuleSw-LSB2GV48DA                  OBJECT IDENTIFIER ::= { ibevtModuleSwitchType 349 } -- 48-Ports 1000Base-T Ethernet Interface Line Card with POE(DA)
ibevtModuleSw-LSB1RGP2GDB                 OBJECT IDENTIFIER ::= { ibevtModuleSwitchType 350 } -- 2-Port GE RPR and 8-Port GE Optical Interface Service Card(DB)
ibevtModuleSw-LSB1RGP4GDB                 OBJECT IDENTIFIER ::= { ibevtModuleSwitchType 351 } -- 4-Port GE RPR and 8-Port GE Optical Interface Service Card(DB)
ibevtModuleSw-LSB2GP24DB                  OBJECT IDENTIFIER ::= { ibevtModuleSwitchType 352 } -- 24-Port 1000BASE-X  Interface Module(DB),(SFP,LC)
ibevtModuleSw-LSB2GP24DC                  OBJECT IDENTIFIER ::= { ibevtModuleSwitchType 353 } -- 24-Port 1000BASE-X  Interface Module(DC),(SFP,LC)
ibevtModuleSw-LSB2GT24DB                  OBJECT IDENTIFIER ::= { ibevtModuleSwitchType 354 } -- 24-Port 10/100/1000BASE-T Interface Module(DB),(RJ45)
ibevtModuleSw-LSB2FW8DB                   OBJECT IDENTIFIER ::= { ibevtModuleSwitchType 355 } -- 8-Port 1000BASE-X Interface Firewall Service Module(DB),(SFP,LC)
ibevtModuleSw-LSB2IPSEC8DB                OBJECT IDENTIFIER ::= { ibevtModuleSwitchType 356 } -- 8-Port 1000BASE-X Interface IPSEC Service Module(DB),(SFP,LC)
ibevtModuleSw-LSB2GV48DB                  OBJECT IDENTIFIER ::= { ibevtModuleSwitchType 357 } -- 48-Port 10/100/1000BASE-T Interface Module(DB),(PoE,RJ45)
ibevtModuleSw-RGP2                        OBJECT IDENTIFIER ::= { ibevtModuleSwitchType 358 } -- 2-Port GE Resilient Packet Ring Interface Module
ibevtModuleSw-RGP4                        OBJECT IDENTIFIER ::= { ibevtModuleSwitchType 359 } -- 4-Port GE Resilient Packet Ring Interface Module
ibevtModuleSw-SR02FW8VB                   OBJECT IDENTIFIER ::= { ibevtModuleSwitchType 360 } -- 8-Port 1000BASE-X Interface Firewall Service Module(VB),(SFP,LC)
ibevtModuleSw-SR02IPSEC8VB                OBJECT IDENTIFIER ::= { ibevtModuleSwitchType 361 } -- 8-Port 1000BASE-X Interface IPSEC Service Module(VB),(SFP,LC)
ibevtModuleSw-LSB2SRP1N0                  OBJECT IDENTIFIER ::= { ibevtModuleSwitchType 362 } -- Switching and Route Process Unit, 12*LPU
ibevtModuleSw-LSB2SRP1N1                  OBJECT IDENTIFIER ::= { ibevtModuleSwitchType 363 } -- Switching and Route Process Unit, 8*LPU
ibevtModuleSw-LSB2SRP1N2                  OBJECT IDENTIFIER ::= { ibevtModuleSwitchType 364 } -- Switching and Route Process Unit, 5*LPU
ibevtModuleSw-LSB2SRP1N3                  OBJECT IDENTIFIER ::= { ibevtModuleSwitchType 365 } -- Switching and Route Process Unit, Clock module
ibevtModuleSw-LSB2SRP1N4                  OBJECT IDENTIFIER ::= { ibevtModuleSwitchType 366 } -- Switching and Route Process Unit, 12*LPU
ibevtModuleSw-LSB2SRP1N5                  OBJECT IDENTIFIER ::= { ibevtModuleSwitchType 367 } -- Switching and Route Process Unit, 8*LPU
ibevtModuleSw-LSB2SRP1N6                  OBJECT IDENTIFIER ::= { ibevtModuleSwitchType 368 } -- Switching and Route Process Unit, 5*LPU
ibevtModuleSw-LSB2SRP1N7                  OBJECT IDENTIFIER ::= { ibevtModuleSwitchType 369 } -- Switching and Route Process Unit, Clock module
ibevtModuleSw-SR02SRPUE                   OBJECT IDENTIFIER ::= { ibevtModuleSwitchType 370 } -- Switching and Route Process Unit, Clock module
ibevtModuleSw-SR01LN1BQH0                 OBJECT IDENTIFIER ::= { ibevtModuleSwitchType 371 } -- Single XG Service Board(BQH)
ibevtModuleSw-SR01DXP1L                   OBJECT IDENTIFIER ::= { ibevtModuleSwitchType 372 } -- 1-Port 10GBASE-R/W Ethernet Optical Interface Card,(XFP,LC)
ibevtModuleSw-SR01DGP10L                  OBJECT IDENTIFIER ::= { ibevtModuleSwitchType 373 } -- 10-Port 1000BASE-X Optical Interface Card,(SFP,LC)
ibevtModuleSw-SR01DRSP2L                  OBJECT IDENTIFIER ::= { ibevtModuleSwitchType 374 } -- 2-Port 2.5G RPR Optical Interface Card,(SFP,LC)
ibevtModuleSw-SR01DRUP1L                  OBJECT IDENTIFIER ::= { ibevtModuleSwitchType 375 } -- 1-Port 10G RPR Optical Interface Card,(XFP,LC)
ibevtModuleSw-SR01DGP20R                  OBJECT IDENTIFIER ::= { ibevtModuleSwitchType 376 } -- 20-Port 1000BASE-X Optical Interface Card,(SFP,LC)
ibevtModuleSw-SR01DPLP8L                  OBJECT IDENTIFIER ::= { ibevtModuleSwitchType 377 } -- 8-Port 155M POS Optical Interface Card,(SFP,LC)
ibevtModuleSw-SR01DXP2R                   OBJECT IDENTIFIER ::= { ibevtModuleSwitchType 378 } -- 2-Port 10GBASE-R/W Ethernet Optical Interface Card,(XFP,LC)
ibevtModuleSw-LSB1FW2A0                   OBJECT IDENTIFIER ::= { ibevtModuleSwitchType 379 } -- Gigabit Firewall Card, 4 Gigabit Port for Management
ibevtModuleSw-LSB1GP48LDB                 OBJECT IDENTIFIER ::= { ibevtModuleSwitchType 380 } -- 48-Port Line Rate Gigabit Ethernet Optical Interface Card(DB)
ibevtModuleSw-SR01LN1BNA0                 OBJECT IDENTIFIER ::= { ibevtModuleSwitchType 381 } -- Single XG Service Board(BNA)
ibevtModuleSw-SR01LN2BQH0                 OBJECT IDENTIFIER ::= { ibevtModuleSwitchType 382 } -- Dual XG Service Board(BQH)
ibevtModuleSw-SR01LN2BNA0                 OBJECT IDENTIFIER ::= { ibevtModuleSwitchType 383 } -- Dual XG Service Board(BNA)
ibevtModuleSw-SR01DGT20R                  OBJECT IDENTIFIER ::= { ibevtModuleSwitchType 384 } -- 20-Port 10/100/1000BASE-T Electrical Interface Card,(RJ45)
ibevtModuleSw-SR01DPSP4L                  OBJECT IDENTIFIER ::= { ibevtModuleSwitchType 385 } -- 4-Port 2.5G POS Optical Interface Card(SFP,LC)
ibevtModuleSw-SR01DPUP1L                  OBJECT IDENTIFIER ::= { ibevtModuleSwitchType 386 } -- 1-Port 10G POS Optical Interface Card,(XFP,LC)
ibevtModuleSw-SR01DPL2G6L                 OBJECT IDENTIFIER ::= { ibevtModuleSwitchType 387 } -- 2-Port 155M POS Optical Interface(SFP,LC)+6-Port 1000BASE-X Optical Interface Card(SFP,LC)
ibevtModuleSw-SR01DPH2G6L                 OBJECT IDENTIFIER ::= { ibevtModuleSwitchType 388 } -- 2-Port 622M POS Optical Interface(SFP,LC)+6-Port 1000BASE-X Optical Interface Card(SFP,LC)
ibevtModuleSw-SR01DPS2G4L                 OBJECT IDENTIFIER ::= { ibevtModuleSwitchType 389 } -- 2-Port 2.5G POS Optical Interface(SFP,LC)+4-Port 1000BASE-X Optical Interface Card(SFP,LC)
ibevtModuleSw-SR01DCL1G8L                 OBJECT IDENTIFIER ::= { ibevtModuleSwitchType 390 } -- 1-Port 155M CPOS Optical Interface(SFP,LC)+8-Port 1000BASE-X Optical Interface Card(SFP,LC)
ibevtModuleSw-SR01DCL2G8L                 OBJECT IDENTIFIER ::= { ibevtModuleSwitchType 391 } -- 2-Port 155M CPOS Optical Interface(SFP,LC)+8-Port 1000BASE-X Optical Interface Card(SFP,LC)
ibevtModuleSw-SR01DET8G8L                 OBJECT IDENTIFIER ::= { ibevtModuleSwitchType 392 } -- 8-Port E1/T1 Electrical Interface(RJ45)+8-Port 1000BASE-X Optical Interface Card(SFP,LC)
ibevtModuleSw-SR02SRP2E3                  OBJECT IDENTIFIER ::= { ibevtModuleSwitchType 393 } -- Switching and Route Process Unit, Clock module
ibevtModuleSw-SR02SRP1E3                  OBJECT IDENTIFIER ::= { ibevtModuleSwitchType 394 } -- Switching and Route Process Unit, Clock module
ibevtModuleSw-SR02SRP1M3                  OBJECT IDENTIFIER ::= { ibevtModuleSwitchType 395 } -- Switching and Route Process Unit, Clock module
ibevtModuleSw-SR01DQCP4L                  OBJECT IDENTIFIER ::= { ibevtModuleSwitchType 396 } -- 4-Port OC-3c/OC-12c/OC-48c POS/GE Optical Interface Card,(SFP,LC)
ibevtModuleSw-SR01DTCP8L                  OBJECT IDENTIFIER ::= { ibevtModuleSwitchType 397 } -- 8-Port OC-3c/OC-12c POS/GE Optical Interface Card,(SFP,LC)
ibevtModuleSw-LSB1AFC1A0                  OBJECT IDENTIFIER ::= { ibevtModuleSwitchType 398 } -- Anomaly Flow Cleaner Board
ibevtModuleSw-LSB1SSL1A0                  OBJECT IDENTIFIER ::= { ibevtModuleSwitchType 399 } -- SSL VPN High-end Board
ibevtModuleSw-IMNAM                       OBJECT IDENTIFIER ::= { ibevtModuleSwitchType 400 } -- Net Analysis Service Processing Board
ibevtModuleSw-IMNAT                       OBJECT IDENTIFIER ::= { ibevtModuleSwitchType 401 } -- Network Address Translation Service Processing Board
ibevtModuleSw-PICAHP1L                    OBJECT IDENTIFIER ::= { ibevtModuleSwitchType 402 } -- 1-Port OC-12c/STM-4c ATM Optical Interface Card,(SFP,LC)
ibevtModuleSw-PICALP4L                    OBJECT IDENTIFIER ::= { ibevtModuleSwitchType 403 } -- 4-Port OC-3c/STM-1c ATM Optical Interface Card,(SFP,LC)
ibevtModuleSw-PICCHP4L                    OBJECT IDENTIFIER ::= { ibevtModuleSwitchType 404 } -- 4-Port 622M CPOS Optical Interface Card(SFP,LC)
ibevtModuleSw-PICCHS1G4L                  OBJECT IDENTIFIER ::= { ibevtModuleSwitchType 405 } -- 1-Port 622M CPOS Optical Interface(Channelized to E3/T3)+4-Port 1000BASE-X Optical Interface Card(SFP,LC)
ibevtModuleSw-PICCLS4G4L                  OBJECT IDENTIFIER ::= { ibevtModuleSwitchType 406 } -- 4-Port 155M CPOS Optical Interface(Channelized to E3/T3)+4-Port 1000BASE-X Optical Interface Card(SFP,LC)
ibevtModuleSw-PICCSP1L                    OBJECT IDENTIFIER ::= { ibevtModuleSwitchType 407 } -- 1-Port 2.5G CPOS Optical Interface Card(SFP,LC)
ibevtModuleSw-LSB1ACG1A0                  OBJECT IDENTIFIER ::= { ibevtModuleSwitchType 408 } -- Application Control Gateway Board
ibevtModuleSw-LST1MRPNC1                  OBJECT IDENTIFIER ::= { ibevtModuleSwitchType 409 } -- Management and Route Process Unit
ibevtModuleSw-LST1SF18B1                  OBJECT IDENTIFIER ::= { ibevtModuleSwitchType 410 } -- S12518 Switch Fabric Card
ibevtModuleSw-LST1SF08B1                  OBJECT IDENTIFIER ::= { ibevtModuleSwitchType 411 } -- S12508 Switch Fabric Card
ibevtModuleSw-LST1GT48LEC1                OBJECT IDENTIFIER ::= { ibevtModuleSwitchType 412 } -- 48-Port 10/100/1000BASE-T Interface Module(LEC),(RJ45)
ibevtModuleSw-LST1GP48LEC1                OBJECT IDENTIFIER ::= { ibevtModuleSwitchType 413 } -- 48-Port 1000BASE-X Interface Module (LEC),(SFP,LC)
ibevtModuleSw-LST1XP4LEC1                 OBJECT IDENTIFIER ::= { ibevtModuleSwitchType 414 } -- 4-Port 10GBASE-R/W Interface Module (LEC),(XFP,LC)
ibevtModuleSw-LST1XP8LEC1                 OBJECT IDENTIFIER ::= { ibevtModuleSwitchType 415 } -- 8-Port 10GBASE-R/W Interface Module (LEC),(XFP,LC)
ibevtModuleSw-LSR1SRP2B1                  OBJECT IDENTIFIER ::= { ibevtModuleSwitchType 416 } -- Switching and Route Process Unit
ibevtModuleSw-LSR1SRP2C1                  OBJECT IDENTIFIER ::= { ibevtModuleSwitchType 417 } -- Switching and Route Process Unit
ibevtModuleSw-LSR1SRP2B2                  OBJECT IDENTIFIER ::= { ibevtModuleSwitchType 418 } -- Switching and Route Process Unit
ibevtModuleSw-LSR1SRP2C2                  OBJECT IDENTIFIER ::= { ibevtModuleSwitchType 419 } -- Switching and Route Process Unit
ibevtModuleSw-LSR1GT24LEC1                OBJECT IDENTIFIER ::= { ibevtModuleSwitchType 420 } -- 16-Port 10/100/1000BASE-T Interface and 8-port 1000BASE-T/1000BASE-X Combo Interface Service Card(LEC)
ibevtModuleSw-LSR1GP24LEB1                OBJECT IDENTIFIER ::= { ibevtModuleSwitchType 421 } -- 16-Port 1000BASE-X Interface and 8-port 1000BASE-T/1000BASE-X Combo Interface Service Card(LEB)
ibevtModuleSw-LSR1GP24LEC1                OBJECT IDENTIFIER ::= { ibevtModuleSwitchType 422 } -- 16-Port 1000BASE-X Interface and 8-port 1000BASE-T/1000BASE-X Combo Interface Service Card(LEC)
ibevtModuleSw-LSR1GT48LEB1                OBJECT IDENTIFIER ::= { ibevtModuleSwitchType 423 } -- 48-Port 10/100/1000BASE-T Interface Module(LEB),(RJ45)
ibevtModuleSw-LSR1GT48LEC1                OBJECT IDENTIFIER ::= { ibevtModuleSwitchType 424 } -- 48-Port 10/100/1000BASE-T Interface Module(LEC),(RJ45)
ibevtModuleSw-LSR1GP48LEB1                OBJECT IDENTIFIER ::= { ibevtModuleSwitchType 425 } -- 48-Port 1000BASE-X Interface Module(LEB),(SFP,LC)
ibevtModuleSw-LSR1GP48LEC1                OBJECT IDENTIFIER ::= { ibevtModuleSwitchType 426 } -- 48-Port 1000BASE-X Interface Module(LEC),(SFP,LC)
ibevtModuleSw-LSR2GV48REB1                OBJECT IDENTIFIER ::= { ibevtModuleSwitchType 427 } -- 48-Port 10/100/1000BASE-T Interface Module(REB),(PoE,RJ45)
ibevtModuleSw-LSR1XP2LEB1                 OBJECT IDENTIFIER ::= { ibevtModuleSwitchType 428 } -- 2-Port 10GBase-R/W Interface Module (LEB),(XFP,LC)
ibevtModuleSw-LSR1XP2LEC1                 OBJECT IDENTIFIER ::= { ibevtModuleSwitchType 429 } -- 2-Port 10GBase-R/W Interface Module (LEC),(XFP,LC)
ibevtModuleSw-LSR1XP4LEB1                 OBJECT IDENTIFIER ::= { ibevtModuleSwitchType 430 } -- 4-Port 10GBase-R/W Interface Module (LEB),(XFP,LC)
ibevtModuleSw-LSR1XP4LEC1                 OBJECT IDENTIFIER ::= { ibevtModuleSwitchType 431 } -- 4-Port 10GBase-R/W Interface Module (LEC),(XFP,LC)
ibevtModuleSw-IMFW                        OBJECT IDENTIFIER ::= { ibevtModuleSwitchType 432 } -- Firewall Service Processing Board
ibevtModuleSw-LSB1LB1A0                   OBJECT IDENTIFIER ::= { ibevtModuleSwitchType 433 } -- Load Balance Board
ibevtModuleSw-LSB1IPS1A0                  OBJECT IDENTIFIER ::= { ibevtModuleSwitchType 434 } -- Gigabit IPS Card
ibevtModuleSw-LST1GT48LEB1                OBJECT IDENTIFIER ::= { ibevtModuleSwitchType 435 } -- 48-Port 10/100/1000BASE-T Interface Module(LEB),(RJ45)
ibevtModuleSw-LST1GP48LEB1                OBJECT IDENTIFIER ::= { ibevtModuleSwitchType 436 } -- 48-Port 1000BASE-X Interface Module (LEB),(SFP,LC)
ibevtModuleSw-LST1XP4LEB1                 OBJECT IDENTIFIER ::= { ibevtModuleSwitchType 437 } -- 4-Port 10GBASE-R/W Interface Module (LEB),(XFP,LC)
ibevtModuleSw-LST1XP8LEB1                 OBJECT IDENTIFIER ::= { ibevtModuleSwitchType 438 } -- 8-Port 10GBASE-R/W Interface Module (LEB),(XFP,LC)
ibevtModuleSw-LST1XP32REB1                OBJECT IDENTIFIER ::= { ibevtModuleSwitchType 439 } -- 32-Port 10GBASE-R Interface Module (REB),(SFP+,LC)
ibevtModuleSw-LST1XP32REC1                OBJECT IDENTIFIER ::= { ibevtModuleSwitchType 440 } -- 32-Port 10GBASE-R Interface Module (REC),(SFP+,LC)
ibevtModuleSw-LSR1FW2A1                   OBJECT IDENTIFIER ::= { ibevtModuleSwitchType 441 } -- Firewall Service Module
ibevtModuleSw-LSR1SSL1A1                  OBJECT IDENTIFIER ::= { ibevtModuleSwitchType 442 } -- SSL VPN Service Module
ibevtModuleSw-SR01DET32G2L                OBJECT IDENTIFIER ::= { ibevtModuleSwitchType 443 } -- 32-Port E1/T1 75ohm Electrical Interface(DB56 Female Socket)+2-Port 1000BASE-X Optical Interface Card(SFP,LC)
ibevtModuleSw-LSR1GP24LEF1                OBJECT IDENTIFIER ::= { ibevtModuleSwitchType 444 } -- 16-Port 1000BASE-X Interface and 8-port 1000BASE-T/1000BASE-X Combo Interface Service Card(LEF)
ibevtModuleSw-LSR1XP4LEF1                 OBJECT IDENTIFIER ::= { ibevtModuleSwitchType 445 } -- 4-Port 10GBASE-R/W Interface Module (LEF),(XFP,LC)
ibevtModuleSw-LSR1LB1A1                   OBJECT IDENTIFIER ::= { ibevtModuleSwitchType 446 } -- Load Balance Module
ibevtModuleSw-LSR1NSM1A1                  OBJECT IDENTIFIER ::= { ibevtModuleSwitchType 447 } -- NetStream Module
ibevtModuleSw-LSR1ACG1A1                  OBJECT IDENTIFIER ::= { ibevtModuleSwitchType 448 } -- Application Control Gateway Service Module
ibevtModuleSw-LSR1IPS1A1                  OBJECT IDENTIFIER ::= { ibevtModuleSwitchType 449 } -- Intrusion Protection System Service Module
ibevtModuleSw-LSR2GP24LEB1                OBJECT IDENTIFIER ::= { ibevtModuleSwitchType 450 } -- 16-Port 1000BASE-X Interface and 8-port 1000BASE-T/1000BASE-X Combo Interface Service Card(LEB)
ibevtModuleSw-LSR2GT24LEB1                OBJECT IDENTIFIER ::= { ibevtModuleSwitchType 451 } -- 16-Port 10/100/1000BASE-T Interface and 8-port 1000BASE-T/1000BASE-X Combo Interface Service Card(LEB)
ibevtModuleSw-LSR2GT48LEB1                OBJECT IDENTIFIER ::= { ibevtModuleSwitchType 452 } -- 48-Port 10/100/1000BASE-T Interface Module(LEB),(RJ45)
ibevtModuleSw-SPC-GP24L                   OBJECT IDENTIFIER ::= { ibevtModuleSwitchType 453 } -- 24-Port 1000BASE-X Interface Service Card,(SFP,LC)
ibevtModuleSw-SPC-GT48L                   OBJECT IDENTIFIER ::= { ibevtModuleSwitchType 454 } -- 48-Port 10/100/1000BASE-T Interface Module,(RJ45)
ibevtModuleSw-SPC-GP48L                   OBJECT IDENTIFIER ::= { ibevtModuleSwitchType 455 } -- 48-Port 1000BASE-X Interface Module,(SFP,LC)
ibevtModuleSw-SPC-XP2L                    OBJECT IDENTIFIER ::= { ibevtModuleSwitchType 456 } -- 2-Port 10GBASE-R/W Interface Service Card,(XFP,LC)
ibevtModuleSw-SPC-XP4L                    OBJECT IDENTIFIER ::= { ibevtModuleSwitchType 457 } -- 4-Port 10GBase-R/W Interface Module,(XFP,LC)
ibevtModuleSw-SR06SRP2E3                  OBJECT IDENTIFIER ::= { ibevtModuleSwitchType 458 } -- SDI,Routing Switch Processing Board
ibevtModuleSw-SPE-2010-E                  OBJECT IDENTIFIER ::= { ibevtModuleSwitchType 459 } -- SDI,Single XG Service Board
ibevtModuleSw-SPE-2020-E                  OBJECT IDENTIFIER ::= { ibevtModuleSwitchType 460 } -- SDI,Dual XG Service Board
ibevtModuleSw-SPC-XP4L-S-SDI              OBJECT IDENTIFIER ::= { ibevtModuleSwitchType 461 } -- SDI 4-Port 10GBase-R/W Interface Module,(XFP,LC)
ibevtModuleSw-SPC-GT48L-SDI               OBJECT IDENTIFIER ::= { ibevtModuleSwitchType 462 } -- SDI 48-Port 10/100/1000BASE-T Interface Module,(RJ45)
ibevtModuleSw-SPC-GP48L-S-SDI             OBJECT IDENTIFIER ::= { ibevtModuleSwitchType 463 } -- SDI 48-Port 1000BASE-X Interface Module,(SFP,LC)
ibevtModuleSw-SPC-SR02OPMA0               OBJECT IDENTIFIER ::= { ibevtModuleSwitchType 464 } -- Single Mode 1310&1550nm Optical Protect Board(LC)
ibevtModuleSw-LSR1XP16REB1                OBJECT IDENTIFIER ::= { ibevtModuleSwitchType 465 } -- 16-Port 10GBASE-R Interface Module (REB),(SFP+,LC)
ibevtModuleSw-LSR1GP48LEF1                OBJECT IDENTIFIER ::= { ibevtModuleSwitchType 466 } -- 48-Port 1000BASE-X Interface Module (LEF),(SFP,LC)
ibevtModuleSw-LST1GP48LEF1                OBJECT IDENTIFIER ::= { ibevtModuleSwitchType 467 } -- 48-Port 1000BASE-X Interface Module (LEF),(SFP,LC)
ibevtModuleSw-LST1XP8LEF1                 OBJECT IDENTIFIER ::= { ibevtModuleSwitchType 468 } -- 8-Port 10GBASE-R/W Interface Module (LEF),(XFP,LC)
ibevtModuleSw-SPE-1010-II                 OBJECT IDENTIFIER ::= { ibevtModuleSwitchType 469 } -- Single XG Service Board-II
ibevtModuleSw-SPE-1010-E-II               OBJECT IDENTIFIER ::= { ibevtModuleSwitchType 470 } -- Enhanced Single XG Service Board-II
ibevtModuleSw-SPE-1020-II                 OBJECT IDENTIFIER ::= { ibevtModuleSwitchType 471 } -- Double XG Service Board-II
ibevtModuleSw-SPE-1020-E-II               OBJECT IDENTIFIER ::= { ibevtModuleSwitchType 472 } -- Enhanced Double XG Service Board-II
ibevtModuleSw-LST1FW2A1                   OBJECT IDENTIFIER ::= { ibevtModuleSwitchType 473 } -- Firewall Board (LEC)
ibevtModuleSw-LST1NSM1A1                  OBJECT IDENTIFIER ::= { ibevtModuleSwitchType 474 } -- NetStream Service Board (LEC)
ibevtModuleSw-LST1LB1A1                   OBJECT IDENTIFIER ::= { ibevtModuleSwitchType 475 } -- Load Balancing Board (LEC)
ibevtModuleSw-LST1ACG1A1                  OBJECT IDENTIFIER ::= { ibevtModuleSwitchType 476 } -- Application Control Gateway Board Module (LEC)
ibevtModuleSw-LST1IPS1A1                  OBJECT IDENTIFIER ::= { ibevtModuleSwitchType 477 } -- Gigabit Intrusion Prevention System Module (LEC)
ibevtModuleSw-LSR1DRUP1L1                 OBJECT IDENTIFIER ::= { ibevtModuleSwitchType 478 } -- 1-Port OC-192c/STM-64c RPR Optical Interface Card,(XFP,LC)
ibevtModuleSw-LSR1DPUP1L1                 OBJECT IDENTIFIER ::= { ibevtModuleSwitchType 479 } -- 1-Port OC-192c/STM-64c POS Optical Interface Card,(XFP,LC)
ibevtModuleSw-LSR1DPSP4L1                 OBJECT IDENTIFIER ::= { ibevtModuleSwitchType 480 } -- 4-Port OC-48c/STM-16c POS Optical Interface Card,(SFP,LC)
ibevtModuleSw-LSR1DTCP8L1                 OBJECT IDENTIFIER ::= { ibevtModuleSwitchType 481 } -- 8-Port OC-3c/OC-12c POS/GE Optical Interface Card,(SFP,LC)
ibevtModuleSw-LSR1DXP1L1                  OBJECT IDENTIFIER ::= { ibevtModuleSwitchType 482 } -- 1-Port 10GBASE-R/W Ethernet Optical Interface Card,(XPF,LC)
ibevtModuleSw-LSR1DGP10L1                 OBJECT IDENTIFIER ::= { ibevtModuleSwitchType 483 } -- 10-Port 1000BASE-X Optical Interface Card,(SFP,LC)
ibevtModuleSw-LSR1LN1BNL1                 OBJECT IDENTIFIER ::= { ibevtModuleSwitchType 484 } -- Single Service Processing Board
ibevtModuleSw-LSR1LN2BL1                  OBJECT IDENTIFIER ::= { ibevtModuleSwitchType 485 } -- Dual Serivice Processing Board
ibevtModuleSw-LSR1SRP2D1                  OBJECT IDENTIFIER ::= { ibevtModuleSwitchType 486 } -- Switching and Route Process Unit With Clock
ibevtModuleSw-IM-NAT-II                   OBJECT IDENTIFIER ::= { ibevtModuleSwitchType 487 } -- Network Address Translation Service Processing Board,II
ibevtModuleSw-IM-NAM-II                   OBJECT IDENTIFIER ::= { ibevtModuleSwitchType 488 } -- Net Analysis Service Processing Board,II
ibevtModuleSw-CR-MRP-I                    OBJECT IDENTIFIER ::= { ibevtModuleSwitchType 489 } -- Management and Route Unit With OAM Module and Clock Module
ibevtModuleSw-CR-SF18C                    OBJECT IDENTIFIER ::= { ibevtModuleSwitchType 490 } -- Switch Fabric Card
ibevtModuleSw-CR-SF08C                    OBJECT IDENTIFIER ::= { ibevtModuleSwitchType 491 } -- Switch Fabric Card
ibevtModuleSw-CR-SPC-XP8LEF               OBJECT IDENTIFIER ::= { ibevtModuleSwitchType 492 } -- 8-Port 10GBASE-R/W Interface Module,(XFP,LC)
ibevtModuleSw-CR-SPC-XP4LEF               OBJECT IDENTIFIER ::= { ibevtModuleSwitchType 493 } -- 4-Port 10GBASE-R/W Interface Module,(XFP,LC)
ibevtModuleSw-CR-SPC-GP48LEF              OBJECT IDENTIFIER ::= { ibevtModuleSwitchType 494 } -- 48-Port 1000BASE-X Interface Module,(SFP,LC)
ibevtModuleSw-CR-SPC-GT48LEF              OBJECT IDENTIFIER ::= { ibevtModuleSwitchType 495 } -- 48-Port 10/100/1000BASE-T Interface Module
ibevtModuleSw-CR-SPE-3020-E               OBJECT IDENTIFIER ::= { ibevtModuleSwitchType 496 } -- Double XG Service Board (Enhanced)
ibevtModuleSw-CR-SPC-PUP4L-E              OBJECT IDENTIFIER ::= { ibevtModuleSwitchType 497 } -- 4-Port 10G POS Optical Interface Module,(XFP,LC)
ibevtModuleSw-LST1SF08C1                  OBJECT IDENTIFIER ::= { ibevtModuleSwitchType 498 } -- Switch Fabric Card
ibevtModuleSw-LST1SF18C1                  OBJECT IDENTIFIER ::= { ibevtModuleSwitchType 499 } -- Switch Fabric Card

--
-- 500 to 699 reserved for secondary switches part I
--
ibevtModuleSw-LS81GP16TM                  OBJECT IDENTIFIER ::= { ibevtModuleSwitchType 500 } -- 12-port 1000BASE-X SFP Interface and 4-port 1000BASE-T/1000BASE-X Combo Interface Metro Switch and Route Processing Board
ibevtModuleSw-LS81VP4C                    OBJECT IDENTIFIER ::= { ibevtModuleSwitchType 501 } -- 4-port 1000BASE-X SFP Interface Virtual Daughter Card
ibevtModuleSw-LS8M1PT8P0                  OBJECT IDENTIFIER ::= { ibevtModuleSwitchType 502 } -- 8-Port 1000BASE-PX Optical Line Interface Board, SFP Req
ibevtModuleSw-LS8M1PT8GB0                 OBJECT IDENTIFIER ::= { ibevtModuleSwitchType 503 } -- 8-Port 1000BASE-PX20 Gigabit Passive Optical Line Interface Board B(20km, SFF), SC Connector
ibevtModuleSw-LS8M1PT4GB0                 OBJECT IDENTIFIER ::= { ibevtModuleSwitchType 504 } -- 4-Port 1000BASE-PX20 Gigabit Passive Optical Line Interface Board B(20km, SFF), SC Connector
ibevtModuleSw-LS81GP2R                    OBJECT IDENTIFIER ::= { ibevtModuleSwitchType 505 } -- 2-port 1000M Ethernet Optical Interface RPR Board
ibevtModuleSw-LS81GP4R                    OBJECT IDENTIFIER ::= { ibevtModuleSwitchType 506 } -- 4-port 1000M Ethernet Optical Interface RPR Board
ibevtModuleSw-LS81IPSECA                  OBJECT IDENTIFIER ::= { ibevtModuleSwitchType 507 } -- IPSec Service Board
ibevtModuleSw-LS81FWA                     OBJECT IDENTIFIER ::= { ibevtModuleSwitchType 508 } -- Firewall Service Board
ibevtModuleSw-LS82VSNP                    OBJECT IDENTIFIER ::= { ibevtModuleSwitchType 509 } -- Versatile Network Processing Service Module (PBR/NAT/NetStream) with 12-port 1000BASE-X SFP, XGBUS Uplink
ibevtModuleSw-LSQ1GV48SA                  OBJECT IDENTIFIER ::= { ibevtModuleSwitchType 510 } -- 48-Port 1000Base-T Gigabit Ethernet Interface Board(RJ45)
ibevtModuleSw-LSQ1SRPB                    OBJECT IDENTIFIER ::= { ibevtModuleSwitchType 511 } -- Salience VI
ibevtModuleSw-LSQ1SRP2XB                  OBJECT IDENTIFIER ::= { ibevtModuleSwitchType 512 } -- Salience VI-10GE
ibevtModuleSw-LSQ1SRP1CB                  OBJECT IDENTIFIER ::= { ibevtModuleSwitchType 513 } -- Salience VI-Turbo
ibevtModuleSw-LSQ1FV48SA                  OBJECT IDENTIFIER ::= { ibevtModuleSwitchType 514 } -- 48-Port 100M Ethernet Electrical Interface Switch Unit(RJ45)
ibevtModuleSw-LSD1MPUA                    OBJECT IDENTIFIER ::= { ibevtModuleSwitchType 515 } -- Main Control Unit
ibevtModuleSw-LSD1GP20A0                  OBJECT IDENTIFIER ::= { ibevtModuleSwitchType 516 } -- 16-port 1000BASE-X SFP Interface and 4-port 1000BASE-T/1000BASE-X Combo Interface Line Card
ibevtModuleSw-LSD1GP20TA0                 OBJECT IDENTIFIER ::= { ibevtModuleSwitchType 517 } -- 16-port 1000BASE-X SFP Interface and 4-port 1000BASE-T/1000BASE-X Combo Interface and 16 1000BASE-T Interface Line Card
ibevtModuleSw-LSD1GP36A0                  OBJECT IDENTIFIER ::= { ibevtModuleSwitchType 518 } -- 32-port 1000BASE-X SFP Interface and 4-port 1000BASE-T/1000BASE-X Combo Interface Line Card
ibevtModuleSw-LSD1GP20XA0                 OBJECT IDENTIFIER ::= { ibevtModuleSwitchType 519 } -- 16-port 1000BASE-X SFP Interface and 4-port 1000BASE-T/1000BASE-X Combo Interface and 2-port 10GBASE-X XFP Interface Line Card
ibevtModuleSw-LSD1GP20EA0                 OBJECT IDENTIFIER ::= { ibevtModuleSwitchType 520 } -- 16-port 1000BASE-X SFP Interface and 4-port 1000BASE-T/1000BASE-X Combo Interface and 2-port GE RPR Interface Line Card
ibevtModuleSw-LSD1GP20RA0                 OBJECT IDENTIFIER ::= { ibevtModuleSwitchType 521 } -- 16-port 1000BASE-X SFP Interface and 4-port 1000BASE-T/1000BASE-X Combo Interface and 2-port OC48 RPR Interface Line Card
ibevtModuleSw-LSD1GP16A0                  OBJECT IDENTIFIER ::= { ibevtModuleSwitchType 522 } -- 16-port 1000BASE-X SFP Ethernet Interface SubCard
ibevtModuleSw-LSD1GT16A0                  OBJECT IDENTIFIER ::= { ibevtModuleSwitchType 523 } -- 16-port 1000BASE-T Ethernet Interface SubCard
ibevtModuleSw-LSD1XP2A0                   OBJECT IDENTIFIER ::= { ibevtModuleSwitchType 524 } -- 2-port 10GBASE-X XFP Ethernet Interface SubCard
ibevtModuleSw-LSD1EP2A0                   OBJECT IDENTIFIER ::= { ibevtModuleSwitchType 525 } -- 2-port 1000BASE-T Ethernet RPR Interface SubCard
ibevtModuleSw-LSD1RP2A0                   OBJECT IDENTIFIER ::= { ibevtModuleSwitchType 526 } -- 2-port OC48 RPR Interface SubCard
ibevtModuleSw-LSQ1GV48SC                  OBJECT IDENTIFIER ::= { ibevtModuleSwitchType 527 } -- 48-Port 1000Base-T Gigabit Ethernet Interface Board(RJ45)-POE
ibevtModuleSw-LSQ1FP48SA                  OBJECT IDENTIFIER ::= { ibevtModuleSwitchType 528 } -- 48 Port 100M Ethernet Optical Interface Board(SFP,LC)
ibevtModuleSw-LSQ1GP24SC                  OBJECT IDENTIFIER ::= { ibevtModuleSwitchType 529 } -- 24 Port 1000BASE-X Ethernet Optical Interface Board(SFP,LC)
ibevtModuleSw-LSQ1GT24SC                  OBJECT IDENTIFIER ::= { ibevtModuleSwitchType 530 } -- 24-Port 1000BASE-T Ethernet Interface Board (RJ45)
ibevtModuleSw-LSQ1TGX2SC                  OBJECT IDENTIFIER ::= { ibevtModuleSwitchType 531 } -- 2-Port 10GBASE Ethernet Optical Interface Board(XFP,LC)
ibevtModuleSw-LSQ1GP12EA                  OBJECT IDENTIFIER ::= { ibevtModuleSwitchType 532 } -- 12-Port 1000BASE-X Ethernet Optical Interface Board(SFP,LC)
ibevtModuleSw-LSQ1TGX1EA                  OBJECT IDENTIFIER ::= { ibevtModuleSwitchType 533 } -- 1-Port 10GBASE Ethernet Optical Interface Module(XFP,LC)
ibevtModuleSw-LSQ1P24XGSC                 OBJECT IDENTIFIER ::= { ibevtModuleSwitchType 534 } -- 24-Port 1000BASE-X Gigabit Ethernet Optical Interface(SFP,LC)+2-Port 10GBASE Ethernet Optical Interface Board(XFP,LC)
ibevtModuleSw-LSQ1T24XGSC                 OBJECT IDENTIFIER ::= { ibevtModuleSwitchType 535 } -- 24-Port 1000BASE-T Gigabit Ethernet Interface(RJ45)+2-Port 10GBASE Ethernet Optical Interface Board(XFP,LC)
ibevtModuleSw-LS81TGX1B                   OBJECT IDENTIFIER ::= { ibevtModuleSwitchType 536 } -- 1 Port 10GBase-R Ethernet Interface Board(XENPAK,SC)
ibevtModuleSw-LSQ1PT4PSC0                 OBJECT IDENTIFIER ::= { ibevtModuleSwitchType 537 } -- 4-Port 1000Base-PX Optical Line Terminal(EPON OLT SFP,SC)+8-Port 1000BASE-X Optical Interface Board(SFP,LC)
ibevtModuleSw-LS81SRPG13                  OBJECT IDENTIFIER ::= { ibevtModuleSwitchType 538 } -- Salience V, Switch and Route Processing Board
ibevtModuleSw-LS81SRPG14                  OBJECT IDENTIFIER ::= { ibevtModuleSwitchType 539 } -- Salience V Edge
ibevtModuleSw-LS81SRPG15                  OBJECT IDENTIFIER ::= { ibevtModuleSwitchType 540 } -- Salience V Plus
ibevtModuleSw-LSQ1GP48SC0                 OBJECT IDENTIFIER ::= { ibevtModuleSwitchType 541 } -- 48-Port 1000BASE Ethernet Optical Interface Board(SFP,LC)
ibevtModuleSw-LSQ1GP12SC0                 OBJECT IDENTIFIER ::= { ibevtModuleSwitchType 542 } -- 12-Port 1000BASE-X Ethernet Optical Interface Board(SFP,LC)
ibevtModuleSw-LSD1SRPA                    OBJECT IDENTIFIER ::= { ibevtModuleSwitchType 543 } -- Salience VIII 160
ibevtModuleSw-LSD1SRPB                    OBJECT IDENTIFIER ::= { ibevtModuleSwitchType 544 } -- Salience VIII 480
ibevtModuleSw-LSD1SRPC                    OBJECT IDENTIFIER ::= { ibevtModuleSwitchType 545 } -- Salience VIII 800
ibevtModuleSw-LSD1GT16PES0                OBJECT IDENTIFIER ::= { ibevtModuleSwitchType 546 } -- 16-Port 10/100/1000BASE-T and 8-Port 100/1000BASE-X SFP Interface Card
ibevtModuleSw-LSD1GP24ES0                 OBJECT IDENTIFIER ::= { ibevtModuleSwitchType 547 } -- 24-Port 1000BASE-X Ethernet SFP Interface Card
ibevtModuleSw-LSD1GT24XES0                OBJECT IDENTIFIER ::= { ibevtModuleSwitchType 548 } -- 24-Port 10/100/1000BASE-T and 2-port 10GBASE-X Ethernet XFP Optical Interface Card
ibevtModuleSw-LSD1GP24XES0                OBJECT IDENTIFIER ::= { ibevtModuleSwitchType 549 } -- 24-Port 1000BASE-X Ethernet SFP interface and 2-port 10GBASE-X Ethernet XFP Optical Interface Card
ibevtModuleSw-LSD1XP2ES0                  OBJECT IDENTIFIER ::= { ibevtModuleSwitchType 550 } -- 2-Port 10GBASE-X Ethernet XFP Optical Interface Card
ibevtModuleSw-LSD1GP48ES0                 OBJECT IDENTIFIER ::= { ibevtModuleSwitchType 551 } -- 48-Port 1000BASE-X Ethernet SFP Interface Card
ibevtModuleSw-LSQ1MPUA0                   OBJECT IDENTIFIER ::= { ibevtModuleSwitchType 552 } -- Master Process Board
ibevtModuleSw-LSQ1MPUA1                   OBJECT IDENTIFIER ::= { ibevtModuleSwitchType 553 } -- Master Process Unit
ibevtModuleSw-LSQ1FWBSC0                  OBJECT IDENTIFIER ::= { ibevtModuleSwitchType 554 } -- Gigabit Firewall Card, 4 Gigabit Port for Management
ibevtModuleSw-LSQ1PT8PSC0                 OBJECT IDENTIFIER ::= { ibevtModuleSwitchType 555 } -- 8-Port 1000Base-PX Optical Line Terminal(EPON OLT SFP,SC)+8-Port 1000BASE-X Optical Interface Board(SFP,LC)
ibevtModuleSw-LSQ1PT16PSC0                OBJECT IDENTIFIER ::= { ibevtModuleSwitchType 556 } -- 16-Port 1000Base-PX Optical Line Terminal(EPON OLT SFP,SC)+8-Port 1000BASE-X Optical Interface Board(SFP,LC)
ibevtModuleSw-SA11MPUA0                   OBJECT IDENTIFIER ::= { ibevtModuleSwitchType 557 } -- SmartEngine I-Lite
ibevtModuleSw-SA11MPUB0                   OBJECT IDENTIFIER ::= { ibevtModuleSwitchType 558 } -- SmartEngine I
ibevtModuleSw-LSQ1AFCBSC0                 OBJECT IDENTIFIER ::= { ibevtModuleSwitchType 559 } -- Anomaly Flow Cleaner Board Interface Board(SFP,LC)
ibevtModuleSw-LSQ1MPUB0                   OBJECT IDENTIFIER ::= { ibevtModuleSwitchType 560 } -- Salience VI-Lite
ibevtModuleSw-LSQ1MPUB1                   OBJECT IDENTIFIER ::= { ibevtModuleSwitchType 561 } -- Salience VI-Lite
ibevtModuleSw-LSQ1PT4PSC1                 OBJECT IDENTIFIER ::= { ibevtModuleSwitchType 562 } -- 4-Port 1000Base-PX Optical Line Terminal(EPON OLT SFP,SC)+8-Port 1000BASE-X Optical Interface Board(SFP,LC)
ibevtModuleSw-LSQ1PT8PSC1                 OBJECT IDENTIFIER ::= { ibevtModuleSwitchType 563 } -- 8-Port 1000Base-PX Optical Line Terminal(EPON OLT SFP,SC)+8-Port 1000BASE-X Optical Interface Board(SFP,LC)
ibevtModuleSw-LSQ1PT16PSC1                OBJECT IDENTIFIER ::= { ibevtModuleSwitchType 564 } -- 16-Port 1000Base-PX Optical Line Terminal(EPON OLT SFP,SC)+8-Port 1000BASE-X Optical Interface Board(SFP,LC)
ibevtModuleSw-LSQ1FP48USA0                OBJECT IDENTIFIER ::= { ibevtModuleSwitchType 565 } -- 48-Port 100M Ethernet Optical Interface Switch Unit(SFP,LC)
ibevtModuleSw-LSQ1FP48USA1                OBJECT IDENTIFIER ::= { ibevtModuleSwitchType 566 } -- 48-Port 100M Ethernet Optical Interface Switch Unit(SFP,LC)
ibevtModuleSw-LSQ1FV48USA0                OBJECT IDENTIFIER ::= { ibevtModuleSwitchType 567 } -- 48-Port 100M Ethernet Electrical Interface Switch Unit(RJ45),PoE
ibevtModuleSw-LSQ1FV48USA1                OBJECT IDENTIFIER ::= { ibevtModuleSwitchType 568 } -- 48-Port 100M Ethernet Electrical Interface Switch Unit(RJ45),PoE
ibevtModuleSw-LSQ1SRPD0                   OBJECT IDENTIFIER ::= { ibevtModuleSwitchType 569 } -- Switch and Route Processing Unit, Salience VI-Plus
ibevtModuleSw-LSQ1CGP24TSC0               OBJECT IDENTIFIER ::= { ibevtModuleSwitchType 570 } -- Switching and Routing Processing Unit with 24 1000BASE-X Gigabit Ethernet Optical Ports,including 8 Combo Ports,SFP Req.
ibevtModuleSw-LSQ1GP24TSC0                OBJECT IDENTIFIER ::= { ibevtModuleSwitchType 571 } -- 16-Port 1000BASE-X Gigabit Ethernet Optical(SFP,LC) And 8-Port 10/100/1000BASE-T RJ45/1000BASE-X SFP Combo Interface Board
ibevtModuleSw-LSQ1ACGASC0                 OBJECT IDENTIFIER ::= { ibevtModuleSwitchType 572 } -- Application Control Gateway Board
ibevtModuleSw-LSD1XP1ES0                  OBJECT IDENTIFIER ::= { ibevtModuleSwitchType 573 } -- 1-Port 10GBASE-X Ethernet XFP Optical Interface Card
ibevtModuleSw-LSD1GP12ES0                 OBJECT IDENTIFIER ::= { ibevtModuleSwitchType 574 } -- 12-Port 1000BASE-X Ethernet SFP Interface Card
ibevtModuleSw-LSQ1SRP12GB0                OBJECT IDENTIFIER ::= { ibevtModuleSwitchType 575 } -- Switch And Route Processing Unit with 12 1000BASE Ethernet Optical Interfaces(SFP,LC),Salience VI-GE
ibevtModuleSw-LSQ1GV40PSC0                OBJECT IDENTIFIER ::= { ibevtModuleSwitchType 576 } -- 40-Port 10/100/1000BASE-T Electrical(RJ45) And 8-Port 1000BASE-X Optical Ethernet Interface Board(SFP,LC),PoE
ibevtModuleSw-LSQ1FWBSC1                  OBJECT IDENTIFIER ::= { ibevtModuleSwitchType 577 } -- Firewall Board
ibevtModuleSw-LSQ1NSMSC0                  OBJECT IDENTIFIER ::= { ibevtModuleSwitchType 578 } -- NetStream Board
ibevtModuleSw-LSQ1NSMSC1                  OBJECT IDENTIFIER ::= { ibevtModuleSwitchType 579 } -- NetStream Board
ibevtModuleSw-LSQ1AFDBSC0                 OBJECT IDENTIFIER ::= { ibevtModuleSwitchType 580 } -- Anomaly Flow Detector Board
ibevtModuleSw-LS81MPUB                    OBJECT IDENTIFIER ::= { ibevtModuleSwitchType 581 } -- Salience IV
ibevtModuleSw-LS81FP48XL                  OBJECT IDENTIFIER ::= { ibevtModuleSwitchType 582 } -- 48-Port 100M Ethernet Optical Interface Module,(SFP,LC)
ibevtModuleSw-LS81FT48XL                  OBJECT IDENTIFIER ::= { ibevtModuleSwitchType 583 } -- 48-Port 10/100M Ethernet Electrical Interface Module(RJ45)
ibevtModuleSw-LS81GP12XL                  OBJECT IDENTIFIER ::= { ibevtModuleSwitchType 584 } -- 12-Port 1000/100M Ethernet Optical Interface Module(SFP,LC)
ibevtModuleSw-LS81GP24XL                  OBJECT IDENTIFIER ::= { ibevtModuleSwitchType 585 } -- 24-Port 1000/100M Ethernet Optical Interface Module(SFP,LC)
ibevtModuleSw-LS81GP48XL                  OBJECT IDENTIFIER ::= { ibevtModuleSwitchType 586 } -- 48-Port 1000/100M Ethernet Optical Interface Module(SFP,LC)
ibevtModuleSw-LS81GT24XL                  OBJECT IDENTIFIER ::= { ibevtModuleSwitchType 587 } -- 24-Port 10/100/1000M Ethernet Electrical Interface Module(RJ45)
ibevtModuleSw-LS81GT48XL                  OBJECT IDENTIFIER ::= { ibevtModuleSwitchType 588 } -- 48-Port 10/100/1000M Ethernet Electrical Interface Module(RJ45)
ibevtModuleSw-LS81TGX2XL                  OBJECT IDENTIFIER ::= { ibevtModuleSwitchType 589 } -- 2-Port 10GBASE Ethernet Optical Interface Module(XFP,LC)
ibevtModuleSw-LSQ1GV48SD0                 OBJECT IDENTIFIER ::= { ibevtModuleSwitchType 590 } -- 48-Port 1000Base-T Gigabit Ethernet Interface Board(RJ45),PoE
ibevtModuleSw-LSQ1GP48EB0                 OBJECT IDENTIFIER ::= { ibevtModuleSwitchType 591 } -- 48-Port Enhanced 1000BASE-X Ethernet Optical Interface Board(SFP,LC)
ibevtModuleSw-LSQ1IPSSC0                  OBJECT IDENTIFIER ::= { ibevtModuleSwitchType 592 } -- Gigabit IPS Card
ibevtModuleSw-LSQ1GV48SD1                 OBJECT IDENTIFIER ::= { ibevtModuleSwitchType 593 } -- 48-Port 1000Base-T Gigabit Ethernet Interface Board(RJ45),PoE
ibevtModuleSw-LSQ1GP48SD0                 OBJECT IDENTIFIER ::= { ibevtModuleSwitchType 594 } -- 48-Port 1000BASE-X Gigabit Ethernet Optical Interface(SFP,LC) Interface Board
ibevtModuleSw-LSQ1GP48SD1                 OBJECT IDENTIFIER ::= { ibevtModuleSwitchType 595 } -- 48-Port 1000BASE-X Gigabit Ethernet Optical Interface(SFP,LC) Interface Board
ibevtModuleSw-LSQ1SRPA0                   OBJECT IDENTIFIER ::= { ibevtModuleSwitchType 596 } -- Salience VI-Smart
ibevtModuleSw-LSQ1SRPA1                   OBJECT IDENTIFIER ::= { ibevtModuleSwitchType 597 } -- Salience VI-Smart
ibevtModuleSw-LSQ2FP48SA0                 OBJECT IDENTIFIER ::= { ibevtModuleSwitchType 598 } -- 48 Port 100M Ethernet Optical Interface Board(SFP,LC)
ibevtModuleSw-LSQ2FP48SA1                 OBJECT IDENTIFIER ::= { ibevtModuleSwitchType 599 } -- 48 Port 100M Ethernet Optical Interface Board(SFP,LC)
ibevtModuleSw-LSQ2FT48SA0                 OBJECT IDENTIFIER ::= { ibevtModuleSwitchType 600 } -- 48-Port 100M Ethernet Electrical Interface Switch Unit(RJ45)
ibevtModuleSw-LSQ2FT48SA1                 OBJECT IDENTIFIER ::= { ibevtModuleSwitchType 601 } -- 48-Port 100M Ethernet Electrical Interface Switch Unit(RJ45)
ibevtModuleSw-LSQ1GV24PSC0                OBJECT IDENTIFIER ::= { ibevtModuleSwitchType 602 } -- 24-Port 10/100/1000BASE-T Electrical(RJ45) Interface Board,including 4 Combo Ports,SFP Req,PoE,No Spell
ibevtModuleSw-LSQ1GV24PSC1                OBJECT IDENTIFIER ::= { ibevtModuleSwitchType 603 } -- 24-Port 10/100/1000BASE-T Electrical(RJ45) Interface Board,including 4 Combo Ports,SFP Req,PoE,No Spell
ibevtModuleSw-LSQ1CGV24PSC0               OBJECT IDENTIFIER ::= { ibevtModuleSwitchType 604 } -- Switching and Routing Processing Unit with 24 10/100/1000BASE-T Electrical Ports(RJ45),including 4 Combo Ports,SFP Req,PoE,No Spell
ibevtModuleSw-LSQ1CGV24PSC1               OBJECT IDENTIFIER ::= { ibevtModuleSwitchType 605 } -- Switching and Routing Processing Unit with 24 10/100/1000BASE-T Electrical Ports(RJ45),including 4 Combo Ports,SFP Req,PoE,No Spell
ibevtModuleSw-LSQ1GP24TEB0                OBJECT IDENTIFIER ::= { ibevtModuleSwitchType 606 } -- 16-Port 1000BASE-X Gigabit Ethernet Optical Interface(SFP,LC)+8-Port Combo Interface Board
ibevtModuleSw-LSQ1GP24TEB1                OBJECT IDENTIFIER ::= { ibevtModuleSwitchType 607 } -- 16-Port 1000BASE-X Gigabit Ethernet Optical Interface(SFP,LC)+8-Port Combo Interface Board
ibevtModuleSw-LSQ1GP24TSD0                OBJECT IDENTIFIER ::= { ibevtModuleSwitchType 608 } -- 16-Port 1000BASE-X Gigabit Ethernet Optical Interface(SFP,LC)+8-Port Combo Interface Board
ibevtModuleSw-LSQ1GP24TSD1                OBJECT IDENTIFIER ::= { ibevtModuleSwitchType 609 } -- 16-Port 1000BASE-X Gigabit Ethernet Optical Interface(SFP,LC)+8-Port Combo Interface Board
ibevtModuleSw-LSQ1GP24TXSD0               OBJECT IDENTIFIER ::= { ibevtModuleSwitchType 610 } -- 16-Port GE Optical Interface(SFP,LC)+8-Port Combo Interface+2-Port 10GE Optical Interface Board(XFP,LC)
ibevtModuleSw-LSQ1GP24TXSD1               OBJECT IDENTIFIER ::= { ibevtModuleSwitchType 611 } -- 16-Port GE Optical Interface(SFP,LC)+8-Port Combo Interface+2-Port 10GE Optical Interface Board(XFP,LC)
ibevtModuleSw-LSQ1TGX2EB0                 OBJECT IDENTIFIER ::= { ibevtModuleSwitchType 612 } -- 2-Port 10GBASE Ethernet Optical Interface Board(XFP,LC)
ibevtModuleSw-LSQ1TGX2EB1                 OBJECT IDENTIFIER ::= { ibevtModuleSwitchType 613 } -- 2-Port 10GBASE Ethernet Optical Interface Board(XFP,LC)
ibevtModuleSw-LSQ1TGX2SD0                 OBJECT IDENTIFIER ::= { ibevtModuleSwitchType 614 } -- 2-Port 10GBASE Ethernet Optical Interface Board(XFP,LC)
ibevtModuleSw-LSQ1TGX2SD1                 OBJECT IDENTIFIER ::= { ibevtModuleSwitchType 615 } -- 2-Port 10GBASE Ethernet Optical Interface Board(XFP,LC)
ibevtModuleSw-LSQ1TGX4SD0                 OBJECT IDENTIFIER ::= { ibevtModuleSwitchType 616 } -- 4-Port 10GBASE Ethernet Optical Interface Board(XFP,LC)
ibevtModuleSw-LSQ1TGX4SD1                 OBJECT IDENTIFIER ::= { ibevtModuleSwitchType 617 } -- 4-Port 10GBASE Ethernet Optical Interface Board(XFP,LC)
ibevtModuleSw-LSQ1TGX8SD0                 OBJECT IDENTIFIER ::= { ibevtModuleSwitchType 618 } -- 8-Port 10GBASE Ethernet Optical Interface Board(XFP,LC)
ibevtModuleSw-LSQ1TGX8SD1                 OBJECT IDENTIFIER ::= { ibevtModuleSwitchType 619 } -- 8-Port 10GBASE Ethernet Optical Interface Board(XFP,LC)
ibevtModuleSw-LSQ1GP48EB1                 OBJECT IDENTIFIER ::= { ibevtModuleSwitchType 620 } -- 48-Port Enhanced 1000BASE-X Ethernet Optical Interface Board(SFP,LC)
ibevtModuleSw-LSQ1TGX4EB0                 OBJECT IDENTIFIER ::= { ibevtModuleSwitchType 621 } -- 4-Port 10GBASE Ethernet Optical Interface Board(XFP,LC)
ibevtModuleSw-LSQ1TGX4EB1                 OBJECT IDENTIFIER ::= { ibevtModuleSwitchType 622 } -- 4-Port 10GBASE Ethernet Optical Interface Board(XFP,LC)
ibevtModuleSw-LSQ1GP12SC3                 OBJECT IDENTIFIER ::= { ibevtModuleSwitchType 623 } -- 12-Port 1000BASE-X Ethernet Optical Interface Board(SFP,LC)
ibevtModuleSw-LSQ1GP24TSC3                OBJECT IDENTIFIER ::= { ibevtModuleSwitchType 624 } -- 16-Port 1000BASE-X Gigabit Ethernet Optical(SFP,LC) And 8-Port 10/100/1000BASE-T RJ45/1000BASE-X SFP Combo Interface Board
ibevtModuleSw-LSQ1GP48SC3                 OBJECT IDENTIFIER ::= { ibevtModuleSwitchType 625 } -- 48-Port 1000BASE Ethernet Optical Interface Board(SFP,LC)
ibevtModuleSw-LSQ1GV48SC3                 OBJECT IDENTIFIER ::= { ibevtModuleSwitchType 626 } -- 48-Port 1000Base-T Gigabit Ethernet Interface Board(RJ45),PoE
ibevtModuleSw-LSQ1MPUA3                   OBJECT IDENTIFIER ::= { ibevtModuleSwitchType 627 } -- Master Process Board
ibevtModuleSw-LSQ1SRP1CB3                 OBJECT IDENTIFIER ::= { ibevtModuleSwitchType 628 } -- Salience VI-Turbo
ibevtModuleSw-LSQ1SRPA3                   OBJECT IDENTIFIER ::= { ibevtModuleSwitchType 629 } -- Salience VI-Smart
ibevtModuleSw-LSQ2FP48SA3                 OBJECT IDENTIFIER ::= { ibevtModuleSwitchType 630 } -- 48 Port 100M Ethernet Optical Interface Board(SFP,LC)
ibevtModuleSw-LSQ2FT48SA3                 OBJECT IDENTIFIER ::= { ibevtModuleSwitchType 631 } -- 48-Port 100M Ethernet Electrical Interface Switch Unit(RJ45)
ibevtModuleSw-LSQ1MPUB3                   OBJECT IDENTIFIER ::= { ibevtModuleSwitchType 632 } -- Salience VI-Lite
ibevtModuleSw-LSQ1CGP24TSC3               OBJECT IDENTIFIER ::= { ibevtModuleSwitchType 633 } -- Switching and Routing Processing Unit with 24 1000BASE-X Gigabit Ethernet Optical Ports,including 8 Combo Ports,SFP Req.
ibevtModuleSw-LSQ1MPUB4                   OBJECT IDENTIFIER ::= { ibevtModuleSwitchType 634 } -- Salience VI-Lite
ibevtModuleSw-LSQ1SRPD4                   OBJECT IDENTIFIER ::= { ibevtModuleSwitchType 635 } -- Salience VI-Plus
ibevtModuleSw-LSQ1SSLSC0                  OBJECT IDENTIFIER ::= { ibevtModuleSwitchType 636 } -- SSL VPN Service Board(B)
ibevtModuleSw-LSQ1LBSC0                   OBJECT IDENTIFIER ::= { ibevtModuleSwitchType 637 } -- Gigabit Load Balancing Card
ibevtModuleSw-LSQ1NAT24SC0                OBJECT IDENTIFIER ::= { ibevtModuleSwitchType 638 } -- NAT/NetStream-Supported Line Processing Unit with 24 10/100/1000BASE-T Electrical Ports(RJ45),including Combo Ports,Upgradeable to PoE
ibevtModuleSw-LSQ1SRP12GB4                OBJECT IDENTIFIER ::= { ibevtModuleSwitchType 639 } -- Salience VI-GE
ibevtModuleSw-LSQ1TGS8SC0                 OBJECT IDENTIFIER ::= { ibevtModuleSwitchType 640 } -- 8-Port 10GBASE Ethernet SFP+ Optical Interface Board
ibevtModuleSw-LSQ3PT4PSC0                 OBJECT IDENTIFIER ::= { ibevtModuleSwitchType 641 } -- 4-Port 1000Base-PX Optical Line Terminal(EPON OLT SFP,SC)+8-Port 1000BASE-X Optical Interface Board(SFP,LC)
ibevtModuleSw-EWPXM2MPUB0                 OBJECT IDENTIFIER ::= { ibevtModuleSwitchType 642 } -- Salience VI-Lite
ibevtModuleSw-EWPXM2SRP12GB0              OBJECT IDENTIFIER ::= { ibevtModuleSwitchType 643 } -- Salience VI-GE
ibevtModuleSw-EWPXM2SRPD0                 OBJECT IDENTIFIER ::= { ibevtModuleSwitchType 644 } -- Salience VI-Plus
ibevtModuleSw-EWPXM2GP24TSD0              OBJECT IDENTIFIER ::= { ibevtModuleSwitchType 645 } -- 16-Port 1000BASE-X Ethernet Optical Interface(SFP Req.)+8-Port Combo Interface Module
ibevtModuleSw-EWPXM2GP24TXSD0             OBJECT IDENTIFIER ::= { ibevtModuleSwitchType 646 } -- 16-Port 1000BASE-X Ethernet Optical Interface(SFP Req.)+8-Port Combo Interface+2-Port 10GE Optical Interface(XFP Req.) Module
ibevtModuleSw-EWPXM2TGX4SD0               OBJECT IDENTIFIER ::= { ibevtModuleSwitchType 647 } -- 4-Port 10GBASE Ethernet Optical Interface Module,XFP Req
ibevtModuleSw-EWPXM2GP48SD0               OBJECT IDENTIFIER ::= { ibevtModuleSwitchType 648 } -- 48-Port 1000BASE-X Gigabit Ethernet Optical Interface Module,SFP Req
ibevtModuleSw-EWPXM2GP24TSC0              OBJECT IDENTIFIER ::= { ibevtModuleSwitchType 649 } -- 24-Port 1000BASE-X/100BASE-FX Optical  Interface Module,including 8 Combo Ports,SFP Req
ibevtModuleSw-EWPXM2TGX2SC0               OBJECT IDENTIFIER ::= { ibevtModuleSwitchType 650 } -- 2-Port 10GBASE Ethernet Optical Interface Module,XFP Req
ibevtModuleSw-EWPXM2GP48SC0               OBJECT IDENTIFIER ::= { ibevtModuleSwitchType 651 } -- 48-Port 1000BASE-X/100BASE-FX Ethernet Optical Interface Module,SFP Req
ibevtModuleSw-LS7500-GP48-SC              OBJECT IDENTIFIER ::= { ibevtModuleSwitchType 652 } -- 48-Port 1000BASE-X/100BASE-FX Ethernet Optical Interface Module(SFP,LC)
ibevtModuleSw-LS7500-GP48-SD              OBJECT IDENTIFIER ::= { ibevtModuleSwitchType 653 } -- 48-Port 1000BASE-X Gigabit Ethernet Optical Interface Module(SFP,LC)
ibevtModuleSw-LS7500-GT48-SC              OBJECT IDENTIFIER ::= { ibevtModuleSwitchType 654 } -- 48-Port 10/100/1000BASE-TX Ethernet Interface Module(RJ45)
ibevtModuleSw-LS7500-GT48-SD              OBJECT IDENTIFIER ::= { ibevtModuleSwitchType 655 } -- 48-Port 10/100/1000BASE-T Ethernet Interface Module(RJ45)
ibevtModuleSw-LS7500-SRPG1                OBJECT IDENTIFIER ::= { ibevtModuleSwitchType 656 } -- Main Control Unit
ibevtModuleSw-LS7500-SRPG2                OBJECT IDENTIFIER ::= { ibevtModuleSwitchType 657 } -- Salience VI-Lite
ibevtModuleSw-LS7500-XP4-SD               OBJECT IDENTIFIER ::= { ibevtModuleSwitchType 658 } -- 4-Port 10GBASE Ethernet Optical Interface Module(XFP,LC)
ibevtModuleSw-LS7500-XP8-SD               OBJECT IDENTIFIER ::= { ibevtModuleSwitchType 659 } -- 8-Port 10GBASE Ethernet Optical Interface Module(XFP,LC)
ibevtModuleSw-LSQ4PT4PSC0                 OBJECT IDENTIFIER ::= { ibevtModuleSwitchType 660 } -- 4-Port 1000Base-PX Optical Line Terminal(EPON OLT SFP,SC)+8-Port 1000BASE-X Optical Interface Board(SFP,LC)
ibevtModuleSw-LSQ4PT8PSC0                 OBJECT IDENTIFIER ::= { ibevtModuleSwitchType 661 } -- 8-Port 1000Base-PX Optical Line Terminal(EPON OLT SFP,SC)+8-Port 1000BASE-X Optical Interface Board(SFP,LC)
ibevtModuleSw-LSQ4PT16PSC0                OBJECT IDENTIFIER ::= { ibevtModuleSwitchType 662 } -- 16-Port 1000Base-PX Optical Line Terminal(EPON OLT SFP,SC)+8-Port 1000BASE-X Optical Interface Board(SFP,LC)
ibevtModuleSw-LSQ1GP24TSA0                OBJECT IDENTIFIER ::= { ibevtModuleSwitchType 663 } -- 16-Port 1000BASE-X Gigabit Ethernet Optical(SFP,LC) And 8-Port 10/100/1000BASE-T RJ45/1000BASE-X SFP Combo Interface Board
ibevtModuleSw-LSQ1GV24PSA0                OBJECT IDENTIFIER ::= { ibevtModuleSwitchType 664 } -- 24-Port 10/100/1000BASE-T Electrical(RJ45) Interface Board,including 4 Combo Ports,SFP Req,Upgradeable to PoE
ibevtModuleSw-LSQ1SRPD3                   OBJECT IDENTIFIER ::= { ibevtModuleSwitchType 665 } -- Salience VI-Plus
ibevtModuleSw-LSQ1SUPA0                   OBJECT IDENTIFIER ::= { ibevtModuleSwitchType 666 } -- Supervisor Engine Board
ibevtModuleSw-LSU1FAB04A0                 OBJECT IDENTIFIER ::= { ibevtModuleSwitchType 667 } -- Switch Fabric Board
ibevtModuleSw-LSU1FAB08A0                 OBJECT IDENTIFIER ::= { ibevtModuleSwitchType 668 } -- Switch Fabric Board
ibevtModuleSw-LSU1TGS8EA0                 OBJECT IDENTIFIER ::= { ibevtModuleSwitchType 669 } -- 8-Port 10GBASE Ethernet SFP+ Optical Interface Board(EA)
ibevtModuleSw-LSU1TGS8EB0                 OBJECT IDENTIFIER ::= { ibevtModuleSwitchType 670 } -- 8-Port 10GBASE Ethernet SFP+ Optical Interface Board
ibevtModuleSw-LSU1TGS8SE0                 OBJECT IDENTIFIER ::= { ibevtModuleSwitchType 671 } -- 8-Port 10GBASE Ethernet SFP+ Optical Interface Board(SE)
ibevtModuleSw-LSUTGS16SC0                 OBJECT IDENTIFIER ::= { ibevtModuleSwitchType 672 } -- 16-Port 10GBASE Ethernet SFP+ Optical Interface Board
ibevtModuleSw-LSU1SUPA0                   OBJECT IDENTIFIER ::= { ibevtModuleSwitchType 673 } -- Supervisor Engine Board
ibevtModuleSw-LSU1GP24TXEA0               OBJECT IDENTIFIER ::= { ibevtModuleSwitchType 674 } -- 16-Port 1000BASE-X Optical Interface(SFP,LC)+8-Port Combo Interface+2-Port 10GE Optical Interface Board(XFP,LC)(EA)
ibevtModuleSw-LSU1GP24TXEB0               OBJECT IDENTIFIER ::= { ibevtModuleSwitchType 675 } -- 16-Port 1000BASE-X Optical Interface(SFP,LC)+8-Port Combo Interface+2-Port 10GE Optical Interface Board(XFP,LC)(EB)
ibevtModuleSw-LSU1GP24TXSE0               OBJECT IDENTIFIER ::= { ibevtModuleSwitchType 676 } -- 16-Port 1000BASE-X Optical Interface(SFP,LC)+8-Port Combo Interface+2-Port 10GE Optical Interface Board(XFP,LC)(SE)
ibevtModuleSw-LSU1GP48EA0                 OBJECT IDENTIFIER ::= { ibevtModuleSwitchType 677 } -- 48-Port 1000BASE-X Gigabit Ethernet Optical Interface(SFP,LC) Interface Board(EA)
ibevtModuleSw-LSU1GP48EB0                 OBJECT IDENTIFIER ::= { ibevtModuleSwitchType 678 } -- 48-Port Enhanced 1000BASE-X Ethernet Optical Interface Board(SFP,LC)(EB)
ibevtModuleSw-LSU1GP48SE0                 OBJECT IDENTIFIER ::= { ibevtModuleSwitchType 679 } -- 48-Port 1000BASE Ethernet Optical Interface Board(SFP,LC)(SE)
ibevtModuleSw-LSU1GT48EA0                 OBJECT IDENTIFIER ::= { ibevtModuleSwitchType 680 } -- 48-Port 1000Base-T Gigabit Ethernet Interface Board(RJ45)(EA)
ibevtModuleSw-LSU1GT48SE0                 OBJECT IDENTIFIER ::= { ibevtModuleSwitchType 681 } -- 48-Port 1000Base-T Gigabit Ethernet Interface Board(RJ45)(SE)
ibevtModuleSw-LSU1TGX4EA0                 OBJECT IDENTIFIER ::= { ibevtModuleSwitchType 682 } -- 4-Port 10GBASE Ethernet Optical Interface Board(XFP,LC)(EA)
ibevtModuleSw-LSU1TGX4EB0                 OBJECT IDENTIFIER ::= { ibevtModuleSwitchType 683 } -- 4-Port 10GBASE Ethernet Optical Interface Board(XFP,LC)(EB)
ibevtModuleSw-LSU1TGX4SE0                 OBJECT IDENTIFIER ::= { ibevtModuleSwitchType 684 } -- 4-Port 10GBASE Ethernet Optical Interface Board(XFP,LC)(SE)
ibevtModuleSw-LSQ1FAB08A0                 OBJECT IDENTIFIER ::= { ibevtModuleSwitchType 685 } -- Switching Fabric Board
ibevtModuleSw-EWPX2WCMD0                  OBJECT IDENTIFIER ::= { ibevtModuleSwitchType 686 } -- Access Controller Card
ibevtModuleSw-LSQ1WCMD0                   OBJECT IDENTIFIER ::= { ibevtModuleSwitchType 687 } -- Access Controller Card
ibevtModuleSw-LSQ1IAGSC0                  OBJECT IDENTIFIER ::= { ibevtModuleSwitchType 688 } -- Wireless&IAG Service Card
ibevtModuleSw-LSU1GP24TSE0                OBJECT IDENTIFIER ::= { ibevtModuleSwitchType 689 } -- 16-Port 1000BASE-X Optical Interface(SFP,LC)+8-Port Combo Interface Board(SE)
ibevtModuleSw-LSQ1TGS16SC0                OBJECT IDENTIFIER ::= { ibevtModuleSwitchType 690 } -- 16-Port 10GBASE Ethernet SFP+ Optical Interface Board
ibevtModuleSw-EWPX2TGS16SC0               OBJECT IDENTIFIER ::= { ibevtModuleSwitchType 691 } -- 16-Port 10GBASE Ethernet SFP+ Optical Interface Board
ibevtModuleSw-LSQ1SUPA3                   OBJECT IDENTIFIER ::= { ibevtModuleSwitchType 692 } -- Supervisor Engine Board
ibevtModuleSw-LSQ1FAB04A3                 OBJECT IDENTIFIER ::= { ibevtModuleSwitchType 693 } -- 320G Switch Fabric Board
ibevtModuleSw-LSQ1FAB08A3                 OBJECT IDENTIFIER ::= { ibevtModuleSwitchType 694 } -- 640G Switch Fabric Board
ibevtModuleSw-LSQ1GT48SC0                 OBJECT IDENTIFIER ::= { ibevtModuleSwitchType 695 } -- 48-Port 1000Base-T Gigabit Ethernet Interface Board(RJ45)
ibevtModuleSw-LSR2SRP2C1                  OBJECT IDENTIFIER ::= { ibevtModuleSwitchType 696 } -- Management and Route Process Unit
ibevtModuleSw-LSR2SRP2C2                  OBJECT IDENTIFIER ::= { ibevtModuleSwitchType 697 } -- Management and Route Process Unit

--
-- 700 to 799 reserved for primary switches
--
ibevtModuleSw-1000BASE-X-COMBO            OBJECT IDENTIFIER ::= { ibevtModuleSwitchType 701 } -- Single port 10/100/1000BASE-T/1000BASE-X Combo Interface Board
ibevtModuleSw-EPON-1000M                  OBJECT IDENTIFIER ::= { ibevtModuleSwitchType 702 } -- Optical Network Unit Interface Board
ibevtModuleSw-1000BASE-FIXED-2SFP-T-2RJ45         OBJECT IDENTIFIER ::= { ibevtModuleSwitchType 703 } -- 2 port 10/100/1000BASE-T and 2 port 1000BASE-X Interface Board
ibevtModuleSw-100M-1550-BIDI              OBJECT IDENTIFIER ::= { ibevtModuleSwitchType 704 }  -- 100BASE-X BIDI Interface Board, Tx 1550nm, Rx 1310nm
ibevtModuleSw-100M-1310-BIDI              OBJECT IDENTIFIER ::= { ibevtModuleSwitchType 705 }  -- 100BASE-X reverse Interface Board, Tx 1310nm, Rx 1550nm
ibevtModuleSw-1000BASE-FIXED-4RJ45-4SFP-COMBO     OBJECT IDENTIFIER ::= { ibevtModuleSwitchType 706 } -- 4 port 10/100/1000BASE-T and 4 port 1000BASE-X COMBO Interface Board
ibevtModuleSw-LSH1PK2T                    OBJECT IDENTIFIER ::= { ibevtModuleSwitchType 707 } -- OSM Interface Board
ibevtModuleSw-LSPM2GP2P                   OBJECT IDENTIFIER ::= { ibevtModuleSwitchType 708 } -- 2-Port 1000BASE-X SFP Module
ibevtModuleSw-LSWM1GT16P                  OBJECT IDENTIFIER ::= { ibevtModuleSwitchType 709 } -- 16-Port 10/100/1000BASE-T Ethernet Electrical Interface Module
ibevtModuleSw-LSWM1GP16P                  OBJECT IDENTIFIER ::= { ibevtModuleSwitchType 710 } -- 16-Port 100/1000BASE-X Ethernet Optical Interface Module
ibevtModuleSw-LSWM1XP2P                   OBJECT IDENTIFIER ::= { ibevtModuleSwitchType 711 } -- 2-Port 10G Ethernet XFP Optical Interface Module
ibevtModuleSw-LSWM1XP4P                   OBJECT IDENTIFIER ::= { ibevtModuleSwitchType 712 } -- 4-Port 10G Ethernet XFP Optical Interface Module
ibevtModuleSw-LSWM1SP2P                   OBJECT IDENTIFIER ::= { ibevtModuleSwitchType 713 } -- 2-Port 10G Ethernet SFP PLUS Optical Interface Module
ibevtModuleSw-LSWM1SP4P                   OBJECT IDENTIFIER ::= { ibevtModuleSwitchType 714 } -- 4-Port 10G Ethernet SFP PLUS Optical Interface Module
ibevtModuleSw-LSWM148POEM                 OBJECT IDENTIFIER ::= { ibevtModuleSwitchType 715 } -- 48 Port Mid Power PoE Module
ibevtModuleSw-LSWM1FW10                   OBJECT IDENTIFIER ::= { ibevtModuleSwitchType 716 } -- RMI CPU XLR 732, with Firewall software
ibevtModuleSw-LSWM1WCM10                  OBJECT IDENTIFIER ::= { ibevtModuleSwitchType 717 } -- RMI CPU XLR 732, with Wireless Access Controller software
ibevtModuleSw-LSWM1IPS10                  OBJECT IDENTIFIER ::= { ibevtModuleSwitchType 718 } -- RMI CPU XLR 732, with IPS/AV software
ibevtModuleSw-LSWM1WCM20                  OBJECT IDENTIFIER ::= { ibevtModuleSwitchType 719 } -- RMI CPU XLR 408, with Wireless Access Controller software
ibevtModuleSw-IPS-T1000-M                 OBJECT IDENTIFIER ::= { ibevtModuleSwitchType 720 } -- IPS for T1000-M mainboard module
ibevtModuleSw-IPS-T1000-A                 OBJECT IDENTIFIER ::= { ibevtModuleSwitchType 721 } -- IPS for T1000-A mainboard module
ibevtModuleSw-IPS-T1000-S                 OBJECT IDENTIFIER ::= { ibevtModuleSwitchType 722 } -- IPS for T1000-S mainboard module
ibevtModuleSw-IPS-GX4C                    OBJECT IDENTIFIER ::= { ibevtModuleSwitchType 723 } -- four-port-gigabit-fiber-board－module
ibevtModuleSw-IPS-GT4C                    OBJECT IDENTIFIER ::= { ibevtModuleSwitchType 724 } -- four-port-1000BASET-board－module
ibevtModuleSw-LSPM2SP2P                   OBJECT IDENTIFIER ::= { ibevtModuleSwitchType 725 } -- 2-Port 10G Ethernet SFP PLUS Optical Interface Module
ibevtModuleSw-LSPM2SP2PA                  OBJECT IDENTIFIER ::= { ibevtModuleSwitchType 726 } -- 2-Port Second Version SFP+ Module
ibevtModuleSw-LSP5GP8P                    OBJECT IDENTIFIER ::= { ibevtModuleSwitchType 727 } -- 8-Port 1G Ethernet SFP Optical Interface Module
ibevtModuleSw-LSP5GT8P                    OBJECT IDENTIFIER ::= { ibevtModuleSwitchType 728 } -- 8-Port 10/100/1000BASE-T Ethernet Electrical Interface Module
ibevtModuleSw-LSWM1FC4P                   OBJECT IDENTIFIER ::= { ibevtModuleSwitchType 729 } -- 4-Port 8G Fibre Channel Interface Module
ibevtModuleSw-LSW1XGT4P0                  OBJECT IDENTIFIER ::= { ibevtModuleSwitchType 730 } -- 4-Port 10G Ethernet Copper Interface Module
ibevtModuleSw-LSW1XGT2P0                  OBJECT IDENTIFIER ::= { ibevtModuleSwitchType 731 } -- 2-Port 10G Ethernet Copper Interface Module
ibevtModuleSw-LSP1XGT2P                   OBJECT IDENTIFIER ::= { ibevtModuleSwitchType 732 } -- 2-Port 10G Ethernet Copper Interface Board
ibevtModuleSw-LSPM3XGT2P                  OBJECT IDENTIFIER ::= { ibevtModuleSwitchType 733 } -- 2-Port 1/10G BASE-T Ethernet Copper Interface Module
ibevtModuleSw-LSWM2QP2P                   OBJECT IDENTIFIER ::= { ibevtModuleSwitchType 734 } -- 2-Port QSFP+ Interface Module
ibevtModuleSw-LSWM2XGT2PM                 OBJECT IDENTIFIER ::= { ibevtModuleSwitchType 735 } -- 2-Port 10G Ethernet Copper Interface Module with MACsec
ibevtModuleSw-LSWM2SP2PM                  OBJECT IDENTIFIER ::= { ibevtModuleSwitchType 736 } -- 2-Port SFP+ Interface Module with MACsec
ibevtModuleSw-LSWM2SP8PM                  OBJECT IDENTIFIER ::= { ibevtModuleSwitchType 737 } -- 8-Port SFP+ Interface Module with MACsec
ibevtModuleSw-LSWM2SP8P                   OBJECT IDENTIFIER ::= { ibevtModuleSwitchType 738 } -- 8-Port SFP+ Interface Module
ibevtModuleSw-LSWM2XGT8PM                 OBJECT IDENTIFIER ::= { ibevtModuleSwitchType 739 } -- 8-Port 10G Ethernet Copper Interface Module with MACsec
ibevtModuleSw-LSWM18QC                    OBJECT IDENTIFIER ::= { ibevtModuleSwitchType 740 } -- 8-Port QSFP+ Module
ibevtModuleSw-LSWM124XG2Q                 OBJECT IDENTIFIER ::= { ibevtModuleSwitchType 741 } -- 24-Port SFP+ and 2-Port QSFP+ Module
ibevtModuleSw-LSWM124XGT2Q                OBJECT IDENTIFIER ::= { ibevtModuleSwitchType 742 } -- 24-Port 10G BASE-T and 2-Port QSFP+ Module
ibevtModuleSw-LSWM124XG2QL                OBJECT IDENTIFIER ::= { ibevtModuleSwitchType 743 } -- 24-Port SFP+ and 2-Port QSFP+ Module
ibevtModuleSw-LSWM124XG2QFC               OBJECT IDENTIFIER ::= { ibevtModuleSwitchType 744 } -- 24-Port 8G Fibre Channel Interface and 2-Port QSFP+ Module
ibevtModuleSw-LSWM18QC0                   OBJECT IDENTIFIER ::= { ibevtModuleSwitchType 745 } -- 8-Port QSFP+ Module
ibevtModuleSw-LSWM124XGT2Q0               OBJECT IDENTIFIER ::= { ibevtModuleSwitchType 746 } -- 24-Port 10G BASE-T and 2-Port QSFP+ Module
ibevtModuleSw-LSWM124XG2QL0               OBJECT IDENTIFIER ::= { ibevtModuleSwitchType 747 } -- 24-Port SFP+ and 2-Port QSFP+ Module
ibevtModuleSw-LSP6G4T6P                   OBJECT IDENTIFIER ::= { ibevtModuleSwitchType 748 } -- 6-Port SFP and 2-port 10/100/1000BASE-T COMBO and 2 port 10/100/1000BASE-T Interface Module
ibevtModuleSw-LSPM6QP2PS                  OBJECT IDENTIFIER ::= { ibevtModuleSwitchType 749 } -- 2-Port QSFP+ Stack Interface Module
ibevtModuleSw-LSWM12H2Q                   OBJECT IDENTIFIER ::= { ibevtModuleSwitchType 750 } -- 2-Port QSFP28 and 2-Port QSFP+ Module
ibevtModuleSw-LSWM18CQ                    OBJECT IDENTIFIER ::= { ibevtModuleSwitchType 751 } -- 8-Port QSFP28 Module
ibevtModuleSw-LSWM116Q                    OBJECT IDENTIFIER ::= { ibevtModuleSwitchType 752 } -- 16-Port QSFP+ Module
ibevtModuleSw-LSPM6FWD                    OBJECT IDENTIFIER ::= { ibevtModuleSwitchType 753 } -- Next Generation Firewall Module
ibevtModuleSw-DS-3E-2XT-H                 OBJECT IDENTIFIER ::= { ibevtModuleSwitchType 754 } -- 2-Port 10G Ethernet Copper Interface Module with MACsec
ibevtModuleSw-DS-3E-2XF-H                 OBJECT IDENTIFIER ::= { ibevtModuleSwitchType 755 } -- 2-Port SFP+ Interface Module with MACsec
ibevtModuleSw-DS-3E-2QX-H                 OBJECT IDENTIFIER ::= { ibevtModuleSwitchType 756 } -- 2-Port QSFP+ Stack Interface Module
ibevtModuleSw-LSPM4G4T6P                  OBJECT IDENTIFIER ::= { ibevtModuleSwitchType 757 } -- 6-Port SFP and 2-port 10/100/1000BASE-T COMBO and 2 port 10/100/1000BASE-T Interface Module
ibevtModuleSw-LSWM4SP8PM                  OBJECT IDENTIFIER ::= { ibevtModuleSwitchType 758 } -- 8-Port SFP+ Interface Module with MACsec
ibevtModuleSw-LSWM124TG2H                 OBJECT IDENTIFIER ::= { ibevtModuleSwitchType 759 } -- 24-Port SFP28 and 2-Port QSFP28 Module
ibevtModuleSw-LSWM18CQ0                   OBJECT IDENTIFIER ::= { ibevtModuleSwitchType 760 } -- 8-Port QSFP28 Module
ibevtModuleSw-LSWM116Q0                   OBJECT IDENTIFIER ::= { ibevtModuleSwitchType 761 } -- 16-Port QSFP+ Module
ibevtModuleSw-LSWM124TG2H0                OBJECT IDENTIFIER ::= { ibevtModuleSwitchType 762 } -- 24-Port SFP28 and 2-Port QSFP28 Module
ibevtModuleSw-LSWM2ZQP2P                  OBJECT IDENTIFIER ::= { ibevtModuleSwitchType 763 } -- 2-Port QSFP28 Module
ibevtModuleSw-LSWM2ZSP8P                  OBJECT IDENTIFIER ::= { ibevtModuleSwitchType 764 } -- 8-Port SFP28 Module
ibevtModuleSw-LSWM18CQMSEC                OBJECT IDENTIFIER ::= { ibevtModuleSwitchType 765 } -- 8-Port QSFP28 MACSEC Module
ibevtModuleSw-LSWM2MGT8P                  OBJECT IDENTIFIER ::= { ibevtModuleSwitchType 766 } -- 8-Port SmartGE (5/2.5/1G) Interface Module
ibevtModuleSw-LSWM2XMGT8P                 OBJECT IDENTIFIER ::= { ibevtModuleSwitchType 767 } -- 8-Port SmartGE (10/5/2.5/1G) Interface Module
ibevtModuleSw-LSWM2ZSP2P                  OBJECT IDENTIFIER ::= { ibevtModuleSwitchType 768 } -- 2-Port SFP28 Interface Module
ibevtModuleSw-LSWM116FC                   OBJECT IDENTIFIER ::= { ibevtModuleSwitchType 769 } -- 16-Ports SFP28 Ethernet Optical Interface Module with 16G/32G FC
ibevtModuleSw-LSWM216FC                   OBJECT IDENTIFIER ::= { ibevtModuleSwitchType 770 } -- 16-Ports SFP28 Ethernet Optical Interface Module with 16G/32G FC
ibevtModuleSw-LSWM2SP2PB                  OBJECT IDENTIFIER ::= { ibevtModuleSwitchType 771 } -- 2-Port SFP+ Interface Module
ibevtModuleSw-LSWM2SP4PB                  OBJECT IDENTIFIER ::= { ibevtModuleSwitchType 772 } -- 4-Port SFP+ Interface Module
ibevtModuleSw-LSWM2SP24P                  OBJECT IDENTIFIER ::= { ibevtModuleSwitchType 773 } -- 24-Port SFP+ Interface Module
ibevtModuleSw-LSWM2SP12P2Q                OBJECT IDENTIFIER ::= { ibevtModuleSwitchType 774 } -- 12-Port SFP+ and 2-Port QSFP+ Interface Module
ibevtModuleSw-LSWM2SP12P2QA               OBJECT IDENTIFIER ::= { ibevtModuleSwitchType 775 } -- 12-Port SFP+ and 2-Port QSFP+ Interface Module with wider size
ibevtModuleSw-DS-3E-2QX-HB                OBJECT IDENTIFIER ::= { ibevtModuleSwitchType 776 } -- 2-Port QSFP+ Interface Module
ibevtModuleSw-DS-3E-8XF-H                 OBJECT IDENTIFIER ::= { ibevtModuleSwitchType 777 } -- 8-Port SFP+ Interface Module
ibevtModuleSw-LSWM116HC                   OBJECT IDENTIFIER ::= { ibevtModuleSwitchType 781 } -- 16-Port QSFP28 Ethernet Optical Interface Module
ibevtModuleSw-10GBASE-T-MACSEC-2P-MOD     OBJECT IDENTIFIER ::= { ibevtModuleSwitchType 782 } -- 2*1G/2.5G/5G/10G BASE-T Ethernet Interface Board(RJ45)
--
-- 800 to 899 reserved for WLAN products
--
ibevtModuleSw-WX5002MPU                   OBJECT IDENTIFIER ::= { ibevtModuleSwitchType 800 } -- Wireless Lan Control Board with 2-port 1000BASE-T/1000BASE-X Combo Interface
ibevtModuleSw-LS8M1WCMA                   OBJECT IDENTIFIER ::= { ibevtModuleSwitchType 801 } -- Wireless Lan Service Board
ibevtModuleSw-EWPX1G24XA0                 OBJECT IDENTIFIER ::= { ibevtModuleSwitchType 802 } -- 24-Port 1000BASE-T Gigabit Ethernet Interface(RJ45) and 4-port 1000BASE-T/1000BASE-X Combo Interface and 2-port 10GBASE Interface Line Card
ibevtModuleSw-LSQ1WCMB0                   OBJECT IDENTIFIER ::= { ibevtModuleSwitchType 803 } -- 1 Port 10GBASE Interface Board
ibevtModuleSw-LSB1WCM2A0                  OBJECT IDENTIFIER ::= { ibevtModuleSwitchType 804 } -- Wireless Controller Module Board
ibevtModuleSw-EWPX1WCMB0                  OBJECT IDENTIFIER ::= { ibevtModuleSwitchType 805 } -- 1 Port 10GBASE Interface Board
ibevtModuleSw-EWPX1G24XC0                 OBJECT IDENTIFIER ::= { ibevtModuleSwitchType 806 } -- 24-Port 1000BASE-T Gigabit Ethernet Interface(RJ45) and 4-port 1000BASE-T/1000BASE-X Combo Interface Line Card
ibevtModuleSw-EWPX1WCMC0                  OBJECT IDENTIFIER ::= { ibevtModuleSwitchType 807 } -- 1-Port 1000BASE-T Gigabit Ethernet of wireless Lan Service Board
ibevtModuleSw-EWPX1FWA0                   OBJECT IDENTIFIER ::= { ibevtModuleSwitchType 808 } -- Firewall Service Board
ibevtModuleSw-EWPX1G10XC0                 OBJECT IDENTIFIER ::= { ibevtModuleSwitchType 809 } -- 8-Port 1000BASE-T Gigabit Ethernet Interface(RJ45) and 2-port 1000BASE-X SFP Interface Line Card
ibevtModuleSw-EWPX1WCM10C0                OBJECT IDENTIFIER ::= { ibevtModuleSwitchType 810 } -- 1-Port 1000BASE-T Gigabit Ethernet of wireless Lan Service Board
ibevtModuleSw-LSR1WCM2A1                  OBJECT IDENTIFIER ::= { ibevtModuleSwitchType 811 } -- 1-Port 1000BASE-T Gigabit Ethernet of wireless Lan Service Board
ibevtModuleSw-EWPX1WAP0                   OBJECT IDENTIFIER ::= { ibevtModuleSwitchType 812 } -- Encryption Card
ibevtModuleSw-EWPX1WCMD0                  OBJECT IDENTIFIER ::= { ibevtModuleSwitchType 813 } -- 2 Port 10GBASE Interface Board
ibevtModuleSw-EWPX1G24XCE0                OBJECT IDENTIFIER ::= { ibevtModuleSwitchType 814 } -- 24-Port 1000BASE-T Gigabit Ethernet Interface(RJ45) and 4-port 1000BASE-T/1000BASE-X Combo Interface Line Card
ibevtModuleSw-EWPX1WCMCE0                 OBJECT IDENTIFIER ::= { ibevtModuleSwitchType 815 } -- 2-Port 1000BASE-T Gigabit Ethernet of wireless Lan Service Board
ibevtModuleSw-EWPX1G24XD0                 OBJECT IDENTIFIER ::= { ibevtModuleSwitchType 816 } -- 4-Port 10GBASE-T and 24-Port 1000BASE-T Gigabit Ethernet of wireless Lan Service Board
ibevtModuleSw-EWPXM1XG03                  OBJECT IDENTIFIER ::= { ibevtModuleSwitchType 817 } -- 8GE and 2SFP Plus Interface Board  of wireless Lan Service Board
ibevtModuleSw-EWPXM2X                     OBJECT IDENTIFIER ::= { ibevtModuleSwitchType 818 } -- 2SFP Plus Interface Board  of wireless Lan Service Board
ibevtModuleSw-EWPXM8G                     OBJECT IDENTIFIER ::= { ibevtModuleSwitchType 819 } -- 8GE Interface Board  of wireless Lan Service Board
ibevtModuleSw-IOT-CARD-C1K                OBJECT IDENTIFIER ::= { ibevtModuleSwitchType 820 } -- IoT Service Board for Wireless Controller
ibevtModuleSw-EWPXM1BSTX80                OBJECT IDENTIFIER ::= { ibevtModuleSwitchType 821 } -- 8GE and 8*SFP Plus（or 2*40Ge） Interface Board  of wireless Lan Service Board
ibevtModuleSw-EWPM1WBCD0ENT               OBJECT IDENTIFIER ::= { ibevtModuleSwitchType 822 } -- WBC Service Board for Wireless Controller
ibevtModuleSw-EEWPXM1XG20                 OBJECT IDENTIFIER ::= { ibevtModuleSwitchType 823 } -- 2SFP Plus Interface Board  of wireless Lan Service Board
ibevtModuleSw-EWPM1WBCE0ENT               OBJECT IDENTIFIER ::= { ibevtModuleSwitchType 824 } -- WBC Service Board for Wireless Controller
ibevtModuleSw-LSEM1WBC120G0               OBJECT IDENTIFIER ::= { ibevtModuleSwitchType 825 } -- 4-Port 40GBASE-T of WBC Service Board for Wireless Controller
--
-- 900 to 1199 reserved for advanced switches part II
--
ibevtModuleSw-LSR1DRSP2L1                 OBJECT IDENTIFIER ::= { ibevtModuleSwitchType 900 } -- 2-Port OC-48c/STM-16c RPR Optical Interface Card,(SFP,LC)
ibevtModuleSw-PIC-CLF2G8L                 OBJECT IDENTIFIER ::= { ibevtModuleSwitchType 901 } -- 2-Port 155M CPOS Optical Interface(SFP,LC)+8-Port 1000BASE-X Optical Interface Card(SFP,LC)
ibevtModuleSw-PIC-CLF4G8L                 OBJECT IDENTIFIER ::= { ibevtModuleSwitchType 902 } -- 4-Port 155M CPOS Optical Interface(SFP,LC)+8-Port 1000BASE-X Optical Interface Card(SFP,LC)
ibevtModuleSw-SR02SRP2F3                  OBJECT IDENTIFIER ::= { ibevtModuleSwitchType 903 } -- Routing Switch Processing Board(2F)
ibevtModuleSw-SR02SRP1F3                  OBJECT IDENTIFIER ::= { ibevtModuleSwitchType 904 } -- Routing Switch Processing Board(1F)
ibevtModuleSw-LST1GT48LEA1                OBJECT IDENTIFIER ::= { ibevtModuleSwitchType 905 } -- 48-Port 10/100/1000BASE-T Interface Module(LEA),(RJ45)
ibevtModuleSw-LST1GP48LEA1                OBJECT IDENTIFIER ::= { ibevtModuleSwitchType 906 } -- 48-Port 1000BASE-X Interface Module(LEA),(SFP,LC)
ibevtModuleSw-LST2XP8LEA1                 OBJECT IDENTIFIER ::= { ibevtModuleSwitchType 907 } -- 8-Port 10GBASE-R Interface Module(LEA),(SFP+,LC)
ibevtModuleSw-LST1GT48LEY1                OBJECT IDENTIFIER ::= { ibevtModuleSwitchType 908 } -- 48-Port 10/100/1000BASE-T Interface Module(LEY),(RJ45)
ibevtModuleSw-LST1GP48LEY1                OBJECT IDENTIFIER ::= { ibevtModuleSwitchType 909 } -- 48-Port 1000BASE-X Interface Module(LEY),(SFP,LC)
ibevtModuleSw-LST1XP32REY1                OBJECT IDENTIFIER ::= { ibevtModuleSwitchType 910 } -- 32-Port 10GBASE-R Interface Module(REY),(SFP+,LC)
ibevtModuleSw-LST1XP8LEY1                 OBJECT IDENTIFIER ::= { ibevtModuleSwitchType 911 } -- 8-Port 10GBASE-R/W Interface Module(LEY),(XFP,LC)
ibevtModuleSw-LST1GP48LEZ1                OBJECT IDENTIFIER ::= { ibevtModuleSwitchType 912 } -- 48-Port 1000BASE-X Interface Module(LEZ),(SFP,LC)
ibevtModuleSw-LST1XP8LEZ1                 OBJECT IDENTIFIER ::= { ibevtModuleSwitchType 913 } -- 8-Port 10GBASE-R/W Interface Module(LEZ),(XFP,LC)
ibevtModuleSw-IM-FW-II                    OBJECT IDENTIFIER ::= { ibevtModuleSwitchType 914 } -- Firewall Service Processing Board-II
ibevtModuleSw-IM-IPS                      OBJECT IDENTIFIER ::= { ibevtModuleSwitchType 915 } -- Intrusion Prevention System Service Processing Board
ibevtModuleSw-IM-SSL                      OBJECT IDENTIFIER ::= { ibevtModuleSwitchType 916 } -- SSL VPN Service Processing Board
ibevtModuleSw-IM-LB                       OBJECT IDENTIFIER ::= { ibevtModuleSwitchType 917 } -- Load Balance Service Processing Board
ibevtModuleSw-IM-ACG                      OBJECT IDENTIFIER ::= { ibevtModuleSwitchType 918 } -- Application Control Gateway Service Processing Board
ibevtModuleSw-LSR1XP16REC1                OBJECT IDENTIFIER ::= { ibevtModuleSwitchType 919 } -- 16-Port 10GBASE-R Interface Module(REC),(SFP+,LC)
ibevtModuleSw-LST2XP8LEB1                 OBJECT IDENTIFIER ::= { ibevtModuleSwitchType 920 } -- 8-Port 10GBASE-R/W Interface Module(LEB),(XFP,LC)
ibevtModuleSw-LST2XP8LEC1                 OBJECT IDENTIFIER ::= { ibevtModuleSwitchType 921 } -- 8-Port 10GBASE-R/W Interface Module(LEC),(XFP,LC)
ibevtModuleSw-LST2XP8LEF1                 OBJECT IDENTIFIER ::= { ibevtModuleSwitchType 922 } -- 8-Port 10GBASE-R/W Interface Module(LEF),(XFP,LC)
ibevtModuleSw-LSR2XP4LEB1                 OBJECT IDENTIFIER ::= { ibevtModuleSwitchType 923 } -- 4-Port 10GBase-R/W Interface Module(LEB),(XFP,LC)
ibevtModuleSw-LSR2XP4LEC1                 OBJECT IDENTIFIER ::= { ibevtModuleSwitchType 924 } -- 4-Port 10GBase-R/W Interface Module(LEC),(XFP,LC)
ibevtModuleSw-LST2XP32REB1                OBJECT IDENTIFIER ::= { ibevtModuleSwitchType 925 } -- 32-Port 10GBASE-R Interface Module(REB),(SFP+,LC)
ibevtModuleSw-LST2XP32REC1                OBJECT IDENTIFIER ::= { ibevtModuleSwitchType 926 } -- 32-Port 10GBASE-R Interface Module(REC),(SFP+,LC)
ibevtModuleSw-LSR1WCM3A1                  OBJECT IDENTIFIER ::= { ibevtModuleSwitchType 927 } -- Access Controller Module
ibevtModuleSw-LST1XP16LEB1                OBJECT IDENTIFIER ::= { ibevtModuleSwitchType 928 } -- 16-Port 10GBASE-R Interface Module (LEB),(SFP+,LC)
ibevtModuleSw-LST1XP16LEC1                OBJECT IDENTIFIER ::= { ibevtModuleSwitchType 929 } -- 16-Port 10GBASE-R Interface Module (LEC),(SFP+,LC)
ibevtModuleSw-CR-SPC-XP4L-E-I             OBJECT IDENTIFIER ::= { ibevtModuleSwitchType 930 } -- 4-Port 10GBASE-R/W Optical Interface Module,(XFP,LC)
ibevtModuleSw-LST2MRPNC1                  OBJECT IDENTIFIER ::= { ibevtModuleSwitchType 931 } -- Management and Route Process Unit
ibevtModuleSw-LST2SF08C1                  OBJECT IDENTIFIER ::= { ibevtModuleSwitchType 932 } -- Switch Fabric Card
ibevtModuleSw-LST2SF18C1                  OBJECT IDENTIFIER ::= { ibevtModuleSwitchType 933 } -- Switch Fabric Card
ibevtModuleSw-SR02SRP2G3                  OBJECT IDENTIFIER ::= { ibevtModuleSwitchType 934 } -- Routing Switch Processing Board(2G)
ibevtModuleSw-CR-SPE-3020-E-I             OBJECT IDENTIFIER ::= { ibevtModuleSwitchType 935 } -- CR15LN3CNA1, Dual Service Processing Board
ibevtModuleSw-CR-SPC-PUP4L-E-I            OBJECT IDENTIFIER ::= { ibevtModuleSwitchType 936 } -- 4-Port 10G POS Optical Interface Board(Enhanced),(XFP,LC)
ibevtModuleSw-CR-SPC-XP4LEF-I             OBJECT IDENTIFIER ::= { ibevtModuleSwitchType 937 } -- 4-Port 10GBASE-R/W Interface Module (LEF),(XFP,LC)
ibevtModuleSw-CR-SPC-XP8LEF-I             OBJECT IDENTIFIER ::= { ibevtModuleSwitchType 938 } -- 8-Port 10GBASE-R/W Interface Module (LEF),(XFP,LC)
ibevtModuleSw-LST3XP8LEB1                 OBJECT IDENTIFIER ::= { ibevtModuleSwitchType 939 } -- 8-Port 10GBASE-R Interface Module (LEB),(XFP,LC)
ibevtModuleSw-LST3XP8LEC1                 OBJECT IDENTIFIER ::= { ibevtModuleSwitchType 940 } -- 8-Port 10GBASE-R Interface Module (LEC),(XFP,LC)
ibevtModuleSw-LST1FW3A1                   OBJECT IDENTIFIER ::= { ibevtModuleSwitchType 941 } -- Firewall Board
ibevtModuleSw-CR-IM-NAM1A                 OBJECT IDENTIFIER ::= { ibevtModuleSwitchType 942 } -- CR1M1NAM1A1, Network Analysis Service Module, Domestic&Overseas Version
ibevtModuleSw-LSR2SRP2B1                  OBJECT IDENTIFIER ::= { ibevtModuleSwitchType 943 } -- Management and Route Process Unit
ibevtModuleSw-LSR2SRP2B2                  OBJECT IDENTIFIER ::= { ibevtModuleSwitchType 944 } -- Management and Route Process Unit
ibevtModuleSw-LSR2SRP2D1                  OBJECT IDENTIFIER ::= { ibevtModuleSwitchType 945 } -- Management and Route Process Unit
ibevtModuleSw-LST3XP8LEY1                 OBJECT IDENTIFIER ::= { ibevtModuleSwitchType 946 } -- 8-Port 10GBASE-R/W Interface Module (LEY),(XFP,LC)
ibevtModuleSw-LST2XP32REY1                OBJECT IDENTIFIER ::= { ibevtModuleSwitchType 947 } -- 32-Port 10GBASE-R Interface Module(REY),(SFP+,LC)
ibevtModuleSw-LST1XP16LEY1                OBJECT IDENTIFIER ::= { ibevtModuleSwitchType 948 } -- 16-Port 10GBASE-R Interface Module (LEY),(SFP+,LC)
ibevtModuleSw-SR0M2SRP2G3                 OBJECT IDENTIFIER ::= { ibevtModuleSwitchType 949 } -- Routing Switch Processing Board(2G)
ibevtModuleSw-SR0M2SRP1G3                 OBJECT IDENTIFIER ::= { ibevtModuleSwitchType 950 } -- Routing Switch Processing Board(1G)
ibevtModuleSw-SPC-GP48LA                  OBJECT IDENTIFIER ::= { ibevtModuleSwitchType 951 } -- 48-Port 1000BASE-X Interface Service Module,(SFP,LC)
ibevtModuleSw-SPC-GT48LA                  OBJECT IDENTIFIER ::= { ibevtModuleSwitchType 952 } -- 48-Port 10/100/1000BASE-T Interface Service Module,(RJ45)
ibevtModuleSw-SPC-XP4LA                   OBJECT IDENTIFIER ::= { ibevtModuleSwitchType 953 } -- 4-Port 10GBase-R/W Interface Service Module,(XFP,LC)
ibevtModuleSw-SPC-XP2LA                   OBJECT IDENTIFIER ::= { ibevtModuleSwitchType 954 } -- 2-Port 10GBASE-R/W Interface Service Module,(XFP,LC)
ibevtModuleSw-SPC-GP24LA                  OBJECT IDENTIFIER ::= { ibevtModuleSwitchType 955 } -- 16-Port 1000BASE-X Interface(SFP,LC)+8-Port Combo Interface Service Module
ibevtModuleSw-SPC-XP16RA                  OBJECT IDENTIFIER ::= { ibevtModuleSwitchType 956 } -- 16-Port 10GBASE-R Optical Interface Service Module(RA),(SFP+,LC)
ibevtModuleSw-CR-IM-FW1A                  OBJECT IDENTIFIER ::= { ibevtModuleSwitchType 957 } -- Firewall Service Processing Board
ibevtModuleSw-SPC-XP16R                   OBJECT IDENTIFIER ::= { ibevtModuleSwitchType 958 } -- 16-Port 10GBASE-R Optical Interface Service Module(R),(SFP+,LC)
ibevtModuleSw-CR-IM-LB1A                  OBJECT IDENTIFIER ::= { ibevtModuleSwitchType 959 } -- Load Balancing Service Processing Board
ibevtModuleSw-LST1GT48LEC2                OBJECT IDENTIFIER ::= { ibevtModuleSwitchType 960 } -- 48-Port 10/100/1000BASE-T Interface Module(LEC),(RJ45)
ibevtModuleSw-LST1GP48LEC2                OBJECT IDENTIFIER ::= { ibevtModuleSwitchType 961 } -- 48-Port 1000BASE-X Interface Module (LEC),(SFP,LC)
ibevtModuleSw-LST1XP16LEC2                OBJECT IDENTIFIER ::= { ibevtModuleSwitchType 962 } -- 16-Port 10GBASE-R Interface Module (LEC),(SFP+,LC)
ibevtModuleSw-LST2XP8LEC2                 OBJECT IDENTIFIER ::= { ibevtModuleSwitchType 963 } -- 8-Port 10GBASE-R/W Interface Module(LEC),(XFP,LC)
ibevtModuleSw-LST2XP32REC2                OBJECT IDENTIFIER ::= { ibevtModuleSwitchType 964 } -- 32-Port 10GBASE-R Interface Module(REC),(SFP+,LC)
ibevtModuleSw-CR-IM-MAC1A                 OBJECT IDENTIFIER ::= { ibevtModuleSwitchType 965 } -- Master Access Control Service Module
ibevtModuleSw-LST1XP48LFD1                OBJECT IDENTIFIER ::= { ibevtModuleSwitchType 966 } -- 48-Port 10GBASE-R Interface Module (LFD),(SFP+,LC)
ibevtModuleSw-LST1XP40RFD1                OBJECT IDENTIFIER ::= { ibevtModuleSwitchType 967 } -- 40-Port 10GBASE-R Interface Module (RFD),(SFP+,LC)
ibevtModuleSw-LST1XP40RFG1                OBJECT IDENTIFIER ::= { ibevtModuleSwitchType 968 } -- 40-Port 10GBASE-R/W Interface Module (RFG),(SFP+,LC)
ibevtModuleSw-LST1XLP16RFD1               OBJECT IDENTIFIER ::= { ibevtModuleSwitchType 969 } -- 16-Port 40GBASE-R Interface Module (RFD),(QSFP+,LC)
ibevtModuleSw-LST1CP4RFD1                 OBJECT IDENTIFIER ::= { ibevtModuleSwitchType 970 } -- 4-Port 100GBASE-R Interface Module (RFD),(CFP,LC)
ibevtModuleSw-LST1CP4RFG1                 OBJECT IDENTIFIER ::= { ibevtModuleSwitchType 971 } -- 4-Port 100GBASE-R Interface Module (RFG),(CFP,LC)
ibevtModuleSw-LST1SF08E1                  OBJECT IDENTIFIER ::= { ibevtModuleSwitchType 972 } -- Switch Fabric Card
ibevtModuleSw-LST1SF18E1                  OBJECT IDENTIFIER ::= { ibevtModuleSwitchType 973 } -- Switch Fabric Card
ibevtModuleSw-LST1MRPNE1                  OBJECT IDENTIFIER ::= { ibevtModuleSwitchType 974 } -- Management and Route Process Unit
ibevtModuleSw-LSX1CGX8FC0                 OBJECT IDENTIFIER ::= { ibevtModuleSwitchType 975 } -- 8-Port 100GBASE-R Interface Module (FC),(CXP,MPO)
ibevtModuleSw-LSX1CGX8FC1                 OBJECT IDENTIFIER ::= { ibevtModuleSwitchType 976 } -- 8-Port 100GBASE-R Interface Module (FC),(CXP,MPO)
ibevtModuleSw-LSX1QGS24FC0                OBJECT IDENTIFIER ::= { ibevtModuleSwitchType 977 } -- 24-Port 40GBASE-R Interface Module (FC),(QSFP+)
ibevtModuleSw-LSX1QGS24FC1                OBJECT IDENTIFIER ::= { ibevtModuleSwitchType 978 } -- 24-Port 40GBASE-R Interface Module (FC),(QSFP+)
ibevtModuleSw-LSX1TGS24FC0                OBJECT IDENTIFIER ::= { ibevtModuleSwitchType 979 } -- 24-Port 10GBASE-R Interface Module (FC),(SFP+,LC)
ibevtModuleSw-LSX1TGS24FC1                OBJECT IDENTIFIER ::= { ibevtModuleSwitchType 980 } -- 24-Port 10GBASE-R Interface Module (FC),(SFP+,LC)
ibevtModuleSw-LSX1TGS48FC0                OBJECT IDENTIFIER ::= { ibevtModuleSwitchType 981 } -- 48-Port 10GBASE-R Interface Module (FC),(SFP+,LC)
ibevtModuleSw-LSX1TGS48FC1                OBJECT IDENTIFIER ::= { ibevtModuleSwitchType 982 } -- 48-Port 10GBASE-R Interface Module (FC),(SFP+,LC)
ibevtModuleSw-LST1XP48LFD2                OBJECT IDENTIFIER ::= { ibevtModuleSwitchType 983 } -- 48-Port 10GBASE-R Interface Module (LFD),(SFP+,LC)
ibevtModuleSw-LST1XP40RFD2                OBJECT IDENTIFIER ::= { ibevtModuleSwitchType 984 } -- 40-Port 10GBASE-R Interface Module (RFD),(SFP+,LC)
ibevtModuleSw-LST1XP40RFG2                OBJECT IDENTIFIER ::= { ibevtModuleSwitchType 985 } -- 40-Port 10GBASE-R/W Interface Module (RFG),(SFP+,LC)
ibevtModuleSw-LST1XLP16RFD2               OBJECT IDENTIFIER ::= { ibevtModuleSwitchType 986 } -- 16-Port 40GBASE-R Interface Module (RFD),(QSFP+)
ibevtModuleSw-LST1CP4RFD2                 OBJECT IDENTIFIER ::= { ibevtModuleSwitchType 987 } -- 4-Port 100GBASE-R Interface Module (RFD),(CFP)
ibevtModuleSw-LST1CP4RFG2                 OBJECT IDENTIFIER ::= { ibevtModuleSwitchType 988 } -- 4-Port 100GBASE-R Interface Module (RFG),(CFP)
ibevtModuleSw-MPE-1004                    OBJECT IDENTIFIER ::= { ibevtModuleSwitchType 989 } -- Multi-Service Processing Engine
ibevtModuleSw-MIC-GP4L                    OBJECT IDENTIFIER ::= { ibevtModuleSwitchType 990 } -- 4-Port 1000BASE-X COMBO Interface Card,(SFP,LC)
ibevtModuleSw-MIC-GP8L                    OBJECT IDENTIFIER ::= { ibevtModuleSwitchType 991 } -- 8-Port 1000BASE-X Optical Interface Card,(SFP,LC)
ibevtModuleSw-MIC-SP4L                    OBJECT IDENTIFIER ::= { ibevtModuleSwitchType 992 } -- 4-Port OC-3/STM-1 POS/CPOS/ATM or 1-Port OC-12/STM-4 POS/ATM Optical Interface Card,(SFP,LC)
ibevtModuleSw-MIC-ET16L                   OBJECT IDENTIFIER ::= { ibevtModuleSwitchType 993 } -- 16-Port E1/T1 Electrical Interface Card
ibevtModuleSw-MIC-CLP4L                   OBJECT IDENTIFIER ::= { ibevtModuleSwitchType 994 } -- 4-Port OC-3/STM-1 CPOS/POS Optical Interface Card,(SFP,LC)
ibevtModuleSw-MIC-CLP2L                   OBJECT IDENTIFIER ::= { ibevtModuleSwitchType 995 } -- 2-Port OC-3/STM-1 CPOS/POS Optical Interface Card,(SFP,LC)
ibevtModuleSw-LST1IPS2A1                  OBJECT IDENTIFIER ::= { ibevtModuleSwitchType 996 } -- Intrusion Prevention System Module
ibevtModuleSw-SFC-04B                     OBJECT IDENTIFIER ::= { ibevtModuleSwitchType 997 } -- Switch Fabric Card(B Type)
ibevtModuleSw-SFC-04D                     OBJECT IDENTIFIER ::= { ibevtModuleSwitchType 998 } -- Switch Fabric Card(D Type)
ibevtModuleSw-SFC-08B                     OBJECT IDENTIFIER ::= { ibevtModuleSwitchType 999 } -- Switch Fabric Card(B Type)
ibevtModuleSw-SFC-08D                     OBJECT IDENTIFIER ::= { ibevtModuleSwitchType 1000 } -- Switch Fabric Card(D Type)
ibevtModuleSw-SFC-12B                     OBJECT IDENTIFIER ::= { ibevtModuleSwitchType 1001 } -- Switch Fabric Card(B Type)
ibevtModuleSw-SFC-12D                     OBJECT IDENTIFIER ::= { ibevtModuleSwitchType 1002 } -- Switch Fabric Card(D Type)
ibevtModuleSw-SR05SRP1H1                  OBJECT IDENTIFIER ::= { ibevtModuleSwitchType 1003 } -- Routing Switch Processing Unit(1H)
ibevtModuleSw-SPC-GP24LA1                 OBJECT IDENTIFIER ::= { ibevtModuleSwitchType 1004 } -- 16-Port 1000BASE-X Ethernet Optical Interface(SFP,LC)+8-Port Combo Interface Module(A Type)
ibevtModuleSw-SPC-GP24XP2LA               OBJECT IDENTIFIER ::= { ibevtModuleSwitchType 1005 } -- 16-Port 1000BASE-X Ethernet Optical Interface(SFP,LC)+8-Port Combo Interface+2-Port 10GE Optical Interface Module(XFP,LC)(A Type)
ibevtModuleSw-SPC-GP48LA1                 OBJECT IDENTIFIER ::= { ibevtModuleSwitchType 1006 } -- 48-Port 1000BASE-X Ethernet Optical Interface Module(SFP,LC)(A Type)
ibevtModuleSw-SPC-GP48LB                  OBJECT IDENTIFIER ::= { ibevtModuleSwitchType 1007 } -- 48-Port Enhanced 1000BASE-X Ethernet Optical Interface Module(SFP,LC)(B Type)
ibevtModuleSw-SPC-XP2LA1                  OBJECT IDENTIFIER ::= { ibevtModuleSwitchType 1008 } -- 2-Port 10GBASE Ethernet Optical Interface Module(XFP,LC)(A Type)
ibevtModuleSw-SPC-XP4LA1                  OBJECT IDENTIFIER ::= { ibevtModuleSwitchType 1009 } -- 4-Port 10GBASE Ethernet Optical Interface Module(XFP,LC)(A Type)
ibevtModuleSw-SPC-XP4LB                   OBJECT IDENTIFIER ::= { ibevtModuleSwitchType 1010 } -- 4-Port Enhanced 10GBASE Ethernet Optical Interface Module(XFP,LC)(B Type)
ibevtModuleSw-SPC-XP8LA                   OBJECT IDENTIFIER ::= { ibevtModuleSwitchType 1011 } -- 8-Port 10GBASE Ethernet Optical Interface Module(SFP+,LC)(A Type)
ibevtModuleSw-SPC-XP8LB                   OBJECT IDENTIFIER ::= { ibevtModuleSwitchType 1012 } -- 8-Port Enhanced 10GBASE Ethernet Optical Interface Module(SFP+,LC)(B Type)
ibevtModuleSw-SPC-XP48LA                  OBJECT IDENTIFIER ::= { ibevtModuleSwitchType 1013 } -- 48-Port 10GBASE Ethernet Optical Interface Module(SFP+,LC)(A Type)
ibevtModuleSw-SPC-XLP8LA                  OBJECT IDENTIFIER ::= { ibevtModuleSwitchType 1014 } -- 8-Port 40GBASE Ethernet Optical Interface Module(QSFP+,MPO)(A Type)
ibevtModuleSw-SPC-GP24XP2LB               OBJECT IDENTIFIER ::= { ibevtModuleSwitchType 1015 } -- 16-Port 1000BASE-X Optical Interface(SFP,LC)+8-Port Combo Interface+2-Port 10GE Optical Interface Module(XFP,LC)(B Type)
ibevtModuleSw-LST1MRPNE2                  OBJECT IDENTIFIER ::= { ibevtModuleSwitchType 1016 } -- Management and Route Process Unit
ibevtModuleSw-LST2FW3A1                   OBJECT IDENTIFIER ::= { ibevtModuleSwitchType 1017 } -- Firewall Board
ibevtModuleSw-LST1ADE1A1                  OBJECT IDENTIFIER ::= { ibevtModuleSwitchType 1018 } -- Load Balancing Board
ibevtModuleSw-CR-MRP-II                   OBJECT IDENTIFIER ::= { ibevtModuleSwitchType 1019 } -- Management and Route Unit-II
ibevtModuleSw-CR-SF08E                    OBJECT IDENTIFIER ::= { ibevtModuleSwitchType 1020 } -- Switch Fabric Module(E)
ibevtModuleSw-CR-SF18E                    OBJECT IDENTIFIER ::= { ibevtModuleSwitchType 1021 } -- Switch Fabric Module(E)
ibevtModuleSw-CR-SPC-XP40RC               OBJECT IDENTIFIER ::= { ibevtModuleSwitchType 1022 } -- 40-Port 10GBASE-R/W Optical Interface Module(RC),(SFP+,LC)
ibevtModuleSw-CR-SPC-XP40RB               OBJECT IDENTIFIER ::= { ibevtModuleSwitchType 1023 } -- 40-Port 10GBASE-R Ethernet Optical Interface Module(RB),(SFP+,LC)
ibevtModuleSw-CR-SPC-CP4RC                OBJECT IDENTIFIER ::= { ibevtModuleSwitchType 1024 } -- 4-Port 100GBASE Ethernet Optical Interface Module(RC),(CFP)
ibevtModuleSw-LST1FW3C1                   OBJECT IDENTIFIER ::= { ibevtModuleSwitchType 1025 } -- Firewall Board
ibevtModuleSw-LSU1FWCEA0                  OBJECT IDENTIFIER ::= { ibevtModuleSwitchType 1026 } -- Firewall Board
ibevtModuleSw-SPC-GT48LA1                 OBJECT IDENTIFIER ::= { ibevtModuleSwitchType 1027 } -- 48-Port 10/100/1000BASE-T Ethernet Interface Module(RJ45)(A Type)
ibevtModuleSw-LST1XP20RFD1                OBJECT IDENTIFIER ::= { ibevtModuleSwitchType 1028 } -- 20-Port 10GBASE-R Interface Module (RFD),(SFP+,LC)
ibevtModuleSw-LST1XP20RFD2                OBJECT IDENTIFIER ::= { ibevtModuleSwitchType 1029 } -- 20-Port 10GBASE-R Interface Module (RFD),(SFP+,LC)
ibevtModuleSw-MPE-1104                    OBJECT IDENTIFIER ::= { ibevtModuleSwitchType 1030 } -- 4-Port Multiservice Processing Engine
ibevtModuleSw-SPEX-1204                   OBJECT IDENTIFIER ::= { ibevtModuleSwitchType 1031 } -- 4-Port 10G Processing Engine
ibevtModuleSw-SPC-GP44XP4LCX              OBJECT IDENTIFIER ::= { ibevtModuleSwitchType 1032 } -- 44-Port 100/1000BASE-X Ethernet Optical Interface Module(SFP,LC)+4-Port 10GBASE Ethernet Optical Interface Module(SFP+,LC)(C Type)
ibevtModuleSw-SPC-GP44XP4LAX              OBJECT IDENTIFIER ::= { ibevtModuleSwitchType 1033 } -- 44-Port 100/1000BASE-X Ethernet Optical Interface Module(SFP,LC)+4-Port 10GBASE Ethernet Optical Interface Module(SFP+,LC)(A Type)
ibevtModuleSw-SPC-XP24LCX                 OBJECT IDENTIFIER ::= { ibevtModuleSwitchType 1034 } -- 24-Port 10GBASE Ethernet Optical Interface Module(SFP+,LC)(C Type)
ibevtModuleSw-SPC-XP24LAX                 OBJECT IDENTIFIER ::= { ibevtModuleSwitchType 1035 } -- 24-Port 10GBASE Ethernet Optical Interface Module(SFP+,LC)(A Type)
ibevtModuleSw-SPC-XP12LCX                 OBJECT IDENTIFIER ::= { ibevtModuleSwitchType 1036 } -- 12-Port 10GBASE Ethernet Optical Interface Module(SFP+,LC)(C Type)
ibevtModuleSw-SPC-XP12LAX                 OBJECT IDENTIFIER ::= { ibevtModuleSwitchType 1037 } -- 12-Port 10GBASE Ethernet Optical Interface Module(SFP+,LC)(A Type)
ibevtModuleSw-SPC-XLP6LCX                 OBJECT IDENTIFIER ::= { ibevtModuleSwitchType 1038 } -- 6-Port 40GBASE Ethernet Optical Interface Module(QSFP+,MPO)(C Type)
ibevtModuleSw-SPC-XLP6LAX                 OBJECT IDENTIFIER ::= { ibevtModuleSwitchType 1039 } -- 6-Port 40GBASE Ethernet Optical Interface Module(QSFP+,MPO)(A Type)
ibevtModuleSw-SPC-CP1LCX                  OBJECT IDENTIFIER ::= { ibevtModuleSwitchType 1040 } -- 1-Port 100GBASE Ethernet Optical Interface Module(CFP,LC)(C Type)
ibevtModuleSw-SPC-CP1LAX                  OBJECT IDENTIFIER ::= { ibevtModuleSwitchType 1041 } -- 1-Port 100GBASE Ethernet Optical Interface Module(CFP,LC)(A Type)
ibevtModuleSw-SPC-CP2LB                   OBJECT IDENTIFIER ::= { ibevtModuleSwitchType 1042 } -- 2-Port 100GBASE Ethernet Optical Interface Module(CFP,LC)(B Type)
ibevtModuleSw-SPC-CP2LA                   OBJECT IDENTIFIER ::= { ibevtModuleSwitchType 1043 } -- 2-Port 100GBASE Ethernet Optical Interface Module(CFP,LC)(A Type)
ibevtModuleSw-SR05SRP1L1                  OBJECT IDENTIFIER ::= { ibevtModuleSwitchType 1044 } -- Management and Route Process Unit(1L1)
ibevtModuleSw-SR05SRP1L3                  OBJECT IDENTIFIER ::= { ibevtModuleSwitchType 1045 } -- Management and Route Process Unit(1L3)
ibevtModuleSw-SFC-04-4                    OBJECT IDENTIFIER ::= { ibevtModuleSwitchType 1046 } -- Short-circuit Card Slot 4
ibevtModuleSw-SFC-04-3                    OBJECT IDENTIFIER ::= { ibevtModuleSwitchType 1047 } -- Short-circuit Card Slot 3
ibevtModuleSw-SFC-04-2                    OBJECT IDENTIFIER ::= { ibevtModuleSwitchType 1048 } -- Short-circuit Card Slot 2
ibevtModuleSw-SFC-04-1                    OBJECT IDENTIFIER ::= { ibevtModuleSwitchType 1049 } -- Short-circuit Card Slot 1
ibevtModuleSw-LST1NSM2C1                  OBJECT IDENTIFIER ::= { ibevtModuleSwitchType 1050 } -- NetStream Service Board
ibevtModuleSw-CR-SPC-XP20RB               OBJECT IDENTIFIER ::= { ibevtModuleSwitchType 1051 } -- 20-Port 10GBASE-R Ethernet Optical Interface Module(RB),(SFP+,LC)
ibevtModuleSw-SR07SRPUA1                  OBJECT IDENTIFIER ::= { ibevtModuleSwitchType 1052 } -- Management and Route Process Unit(UA1)
ibevtModuleSw-SR07SRPUB3                  OBJECT IDENTIFIER ::= { ibevtModuleSwitchType 1053 } -- Management and Route Process Unit(UB1)
ibevtModuleSw-SR07SRPUC3                  OBJECT IDENTIFIER ::= { ibevtModuleSwitchType 1054 } -- Management and Route Process Unit
ibevtModuleSw-SR07MPUA1                   OBJECT IDENTIFIER ::= { ibevtModuleSwitchType 1055 } -- Management and Route Process Unit
ibevtModuleSw-SR07SRPUB1                  OBJECT IDENTIFIER ::= { ibevtModuleSwitchType 1056 } -- Management and Route Process Unit(UB1)
ibevtModuleSw-SR07SRPUC1                  OBJECT IDENTIFIER ::= { ibevtModuleSwitchType 1057 } -- Management and Route Process Unit
ibevtModuleSw-MIC-MS4L                    OBJECT IDENTIFIER ::= { ibevtModuleSwitchType 1058 } -- 4-Port Multi-Service Optical Interface Card,Domestic&Overseas Version
ibevtModuleSw-SPC-GP44XP4LC               OBJECT IDENTIFIER ::= { ibevtModuleSwitchType 1059 } -- 44-Port 100/1000BASE-X Ethernet Optical Interface Board(SFP,LC)+4-Port 10GBASE Ethernet Optical Interface Board(SFP+,LC)(C Type)
ibevtModuleSw-SPC-GP44XP4LA               OBJECT IDENTIFIER ::= { ibevtModuleSwitchType 1060 } -- 44-Port 100/1000BASE-X Ethernet Optical Interface Board(SFP,LC)+4-Port 10GBASE Ethernet Optical Interface Board(SFP+,LC)(A Type)
ibevtModuleSw-SPC-XLP2XP4LC               OBJECT IDENTIFIER ::= { ibevtModuleSwitchType 1061 } -- 2-Port 40GBASE Ethernet Optical Interface Board(QSFP+,MPO)+4-Port 10GBASE Ethernet Optical Interface Board(SFP+,LC)(C Type)
ibevtModuleSw-SPC-XP12LC                  OBJECT IDENTIFIER ::= { ibevtModuleSwitchType 1062 } -- 12-Port 10GBASE Ethernet Optical Interface Board(SFP+,LC)(C Type)
ibevtModuleSw-SPC-CP1LC                   OBJECT IDENTIFIER ::= { ibevtModuleSwitchType 1063 } -- 1-Port 100GBASE Ethernet Optical Interface Module(CFP,LC)(C Type)
ibevtModuleSw-SPC-XP24LC                  OBJECT IDENTIFIER ::= { ibevtModuleSwitchType 1064 } -- 24-Port 10GBASE Ethernet Optical Interface Board(SFP+,LC)(C Type)
ibevtModuleSw-SR07SRPUD3                  OBJECT IDENTIFIER ::= { ibevtModuleSwitchType 1065 } -- Management and Route Process Unit(UD1)
ibevtModuleSw-SR07MPUA3                   OBJECT IDENTIFIER ::= { ibevtModuleSwitchType 1066 } -- Management and Route Process Unit(For 02 Chassis)
ibevtModuleSw-MPEX-1304                   OBJECT IDENTIFIER ::= { ibevtModuleSwitchType 1067 } -- 4-Port Multiservice Processing Engine
ibevtModuleSw-MIC-GP10L1                  OBJECT IDENTIFIER ::= { ibevtModuleSwitchType 1068 } -- 6-Port 1000BASE-X Optical Interface Card(SFP,LC)+4-Port 1000BASE-X/10GBASE Optical Interface Card(SFP+,LC)
ibevtModuleSw-SR07SRPUB                   OBJECT IDENTIFIER ::= { ibevtModuleSwitchType 1069 } -- Management and Route Processing Unit(UB3)
ibevtModuleSw-CMPE-1104                   OBJECT IDENTIFIER ::= { ibevtModuleSwitchType 1070 } -- 4-Port Multiservice Processing Engine
ibevtModuleSw-CSFC-04-1                   OBJECT IDENTIFIER ::= { ibevtModuleSwitchType 1071 } -- Fabric Card Slot 1
ibevtModuleSw-CSFC-04-2                   OBJECT IDENTIFIER ::= { ibevtModuleSwitchType 1072 } -- Fabric Card Slot 2
ibevtModuleSw-CSFC-04-3                   OBJECT IDENTIFIER ::= { ibevtModuleSwitchType 1073 } -- Fabric Card Slot 3
ibevtModuleSw-CSFC-04-4                   OBJECT IDENTIFIER ::= { ibevtModuleSwitchType 1074 } -- Fabric Card Slot 4
ibevtModuleSw-CSFC-04B                    OBJECT IDENTIFIER ::= { ibevtModuleSwitchType 1075 } -- Switch Fabric Card(B Type)
ibevtModuleSw-CSFC-04D                    OBJECT IDENTIFIER ::= { ibevtModuleSwitchType 1076 } -- Switch Fabric Card(D Type)
ibevtModuleSw-CSFC-08B                    OBJECT IDENTIFIER ::= { ibevtModuleSwitchType 1077 } -- Switch Fabric Card(B Type)
ibevtModuleSw-CSFC-08D                    OBJECT IDENTIFIER ::= { ibevtModuleSwitchType 1078 } -- Switch Fabric Card(D Type)
ibevtModuleSw-CSFC-12B                    OBJECT IDENTIFIER ::= { ibevtModuleSwitchType 1079 } -- Switch Fabric Card(B Type)
ibevtModuleSw-CSFC-12D                    OBJECT IDENTIFIER ::= { ibevtModuleSwitchType 1080 } -- Switch Fabric Card(D Type)
ibevtModuleSw-CSPC-CP1LCX                 OBJECT IDENTIFIER ::= { ibevtModuleSwitchType 1081 } -- 1-Port 100GBASE Ethernet Optical Interface Module(CFP,LC)(C Type)
ibevtModuleSw-CSPC-CP2LB                  OBJECT IDENTIFIER ::= { ibevtModuleSwitchType 1082 } -- 2-Port 100GBASE Ethernet Optical Interface Module(CFP,LC)(B Type)
ibevtModuleSw-CSPC-GP24LA1                OBJECT IDENTIFIER ::= { ibevtModuleSwitchType 1083 } -- 16-Port 1000BASE-X Ethernet Optical Interface(SFP,LC)+8-Port Combo Interface Module(A Type)
ibevtModuleSw-CSPC-GP24XP2LB              OBJECT IDENTIFIER ::= { ibevtModuleSwitchType 1084 } -- 16-Port 1000BASE-X Optical Interface(SFP,LC)+8-Port Combo Interface+2-Port 10GE Optical Interface Module(XFP,LC)(B Type)
ibevtModuleSw-CSPC-GP44XP4LCX             OBJECT IDENTIFIER ::= { ibevtModuleSwitchType 1085 } -- 44-Port 1000BASE-X Ethernet Optical Interface Module(SFP,LC)+4-Port 10GBASE Ethernet Optical Interface Module(SFP+,LC)(C Type)
ibevtModuleSw-CSPC-GP48LB                 OBJECT IDENTIFIER ::= { ibevtModuleSwitchType 1086 } -- 48-Port Enhanced 1000BASE-X Ethernet Optical Interface Module(SFP,LC)(B Type)
ibevtModuleSw-CSPC-GT48LA1                OBJECT IDENTIFIER ::= { ibevtModuleSwitchType 1087 } -- 48-Port 10/100/1000BASE-T Ethernet Interface Module(RJ45)(A Type)
ibevtModuleSw-CSPC-XLP6LCX                OBJECT IDENTIFIER ::= { ibevtModuleSwitchType 1088 } -- 6-Port 40GBASE Ethernet Optical Interface Module(QSFP+,MPO)(C Type)
ibevtModuleSw-CSPC-XP2LA1                 OBJECT IDENTIFIER ::= { ibevtModuleSwitchType 1089 } -- 2-Port 10GBASE Ethernet Optical Interface Module(XFP,LC)(A Type)
ibevtModuleSw-CSPC-XP4LB                  OBJECT IDENTIFIER ::= { ibevtModuleSwitchType 1090 } -- 4-Port Enhanced 10GBASE Ethernet Optical Interface Module(XFP,LC)(B Type)
ibevtModuleSw-CSPC-XP8LB                  OBJECT IDENTIFIER ::= { ibevtModuleSwitchType 1091 } -- 8-Port Enhanced 10GBASE Ethernet Optical Interface Module(SFP+,LC)(B Type)
ibevtModuleSw-CSPC-XP12LAX                OBJECT IDENTIFIER ::= { ibevtModuleSwitchType 1092 } -- 12-Port 10GBASE Ethernet Optical Interface Module(SFP+,LC)(A Type)
ibevtModuleSw-CSPC-XP12LCX                OBJECT IDENTIFIER ::= { ibevtModuleSwitchType 1093 } -- 12-Port 10GBASE Ethernet Optical Interface Module(SFP+,LC)(C Type)
ibevtModuleSw-CSPC-XP24LAX                OBJECT IDENTIFIER ::= { ibevtModuleSwitchType 1094 } -- 24-Port 10GBASE Ethernet Optical Interface Module(SFP+,LC)(A Type)
ibevtModuleSw-CSPC-XP24LCX                OBJECT IDENTIFIER ::= { ibevtModuleSwitchType 1095 } -- 24-Port 10GBASE Ethernet Optical Interface Module(SFP+,LC)(C Type)
ibevtModuleSw-CSPC-CSPEX-1204             OBJECT IDENTIFIER ::= { ibevtModuleSwitchType 1096 } -- 4-Port 10G Processing Engine
ibevtModuleSw-CSR05SRP1L1                 OBJECT IDENTIFIER ::= { ibevtModuleSwitchType 1097 } -- Management and Route Process Unit(1L1)
ibevtModuleSw-CSR05SRP1L3                 OBJECT IDENTIFIER ::= { ibevtModuleSwitchType 1098 } -- Management and Route Process Unit(1L3)
ibevtModuleSw-CSR07MPUA1                  OBJECT IDENTIFIER ::= { ibevtModuleSwitchType 1099 } -- Management and Route Processing Unit
ibevtModuleSw-CSR07SRPUA1                 OBJECT IDENTIFIER ::= { ibevtModuleSwitchType 1100 } -- Management and Route Processing Unit(UA1)
ibevtModuleSw-CSR07SRPUB1                 OBJECT IDENTIFIER ::= { ibevtModuleSwitchType 1101 } -- Management and Route Processing Unit(UB1)
ibevtModuleSw-CSR07SRPUC1                 OBJECT IDENTIFIER ::= { ibevtModuleSwitchType 1102 } -- Management and Route Processing Unit
ibevtModuleSw-LSXM1CGX8FX1                OBJECT IDENTIFIER ::= { ibevtModuleSwitchType 1103 } -- 8-Port 100GBASE Ethernet Optical Interface Module(CXP)(FX)
ibevtModuleSw-LSXM1QGS24FX1               OBJECT IDENTIFIER ::= { ibevtModuleSwitchType 1104 } -- 24-Port 40GBASE Ethernet Optical Interface Module(QSFP+)(FX)
ibevtModuleSw-LSXM1TGS48FX1               OBJECT IDENTIFIER ::= { ibevtModuleSwitchType 1105 } -- 48-Port 10GBASE Ethernet Optical Interface Module(SFP+,LC)(FX)
ibevtModuleSw-LSXM1QGS12FX1               OBJECT IDENTIFIER ::= { ibevtModuleSwitchType 1106 } -- 12-Port 40GBASE Ethernet Optical Interface Module(QSFP+)(FX)
ibevtModuleSw-LSXM1TGT48FX1               OBJECT IDENTIFIER ::= { ibevtModuleSwitchType 1107 } -- 48-Port 10GBASE-T Ethernet Electrical Interface Module(RJ45)(FX)
ibevtModuleSw-LSU1IPSBEA0                 OBJECT IDENTIFIER ::= { ibevtModuleSwitchType 1108 } -- Intrusion Prevention System Module
ibevtModuleSw-PIC-GP10L                   OBJECT IDENTIFIER ::= { ibevtModuleSwitchType 1109 } -- 10-Port 1000BASE-X Optical Interface Card,(SFP,LC)
ibevtModuleSw-PIC-XP1L                    OBJECT IDENTIFIER ::= { ibevtModuleSwitchType 1110 } -- 1-Port 10GBASE-R/W Ethernet Optical Interface Card,(XFP,LC)
ibevtModuleSw-PIC-PUP1L                   OBJECT IDENTIFIER ::= { ibevtModuleSwitchType 1111 } -- 1-Port 10G POS Optical Interface Card,(XFP,LC)
ibevtModuleSw-PIC-PSP4L                   OBJECT IDENTIFIER ::= { ibevtModuleSwitchType 1112 } -- 4-Port 2.5G POS Optical Interface Card(SFP,LC)
ibevtModuleSw-PIC-PS2G4L                  OBJECT IDENTIFIER ::= { ibevtModuleSwitchType 1113 } -- 2-Port 2.5G POS Optical Interface(SFP,LC)+4-Port 1000BASE-X Optical Interface Card(SFP,LC)
ibevtModuleSw-PIC-PL2G6L                  OBJECT IDENTIFIER ::= { ibevtModuleSwitchType 1114 } -- 2-Port 155M POS Optical Interface(SFP,LC)+6-Port 1000BASE-X Optical Interface Card(SFP,LC)
ibevtModuleSw-PIC-TCP8L                   OBJECT IDENTIFIER ::= { ibevtModuleSwitchType 1115 } -- 8-Port OC-3c/OC-12c POS/GE Optical Interface Card,(SFP,LC)
ibevtModuleSw-PIC-CSP1L                   OBJECT IDENTIFIER ::= { ibevtModuleSwitchType 1116 } -- 1-Port 2.5G CPOS Optical Interface Card(SFP,LC)
ibevtModuleSw-PIC-PH2G6L                  OBJECT IDENTIFIER ::= { ibevtModuleSwitchType 1117 } -- 2-Port 622M POS Optical Interface(SFP,LC)+6-Port 1000BASE-X Optical Interface Card(SFP,LC)
ibevtModuleSw-LSXM1CGP12FX1               OBJECT IDENTIFIER ::= { ibevtModuleSwitchType 1118 } -- 12-Port 100GBASE Ethernet Optical Interface Module(CFP2)(FX)
ibevtModuleSw-LSXM1CGP8FX1                OBJECT IDENTIFIER ::= { ibevtModuleSwitchType 1119 } -- 8-Port 100GBASE Ethernet Optical Interface Module(CFP2)(FX)
ibevtModuleSw-LSXM1GT48FX1                OBJECT IDENTIFIER ::= { ibevtModuleSwitchType 1120 } -- 48-Port 1000Base-T Gigabit Ethernet Interface Board(RJ45)
ibevtModuleSw-LSXM1GT48FX0                OBJECT IDENTIFIER ::= { ibevtModuleSwitchType 1121 } -- 48-Port 1000Base-T Gigabit Ethernet Interface Board(RJ45)
ibevtModuleSw-LSXM1GP48FX1                OBJECT IDENTIFIER ::= { ibevtModuleSwitchType 1122 } -- 48-Port 1000BASE Ethernet SFP Optical Interface Board
ibevtModuleSw-LSXM1GP48FX0                OBJECT IDENTIFIER ::= { ibevtModuleSwitchType 1123 } -- 48-Port 1000BASE Ethernet SFP Optical Interface Board
ibevtModuleSw-LSXM1TGS24FX0               OBJECT IDENTIFIER ::= { ibevtModuleSwitchType 1124 } -- 24-Port 10GBASE Ethernet SFP+ Optical Interface Board
ibevtModuleSw-LSXM1TGS24FX1               OBJECT IDENTIFIER ::= { ibevtModuleSwitchType 1125 } -- 24-Port 10GBASE Ethernet SFP+ Optical Interface Board
ibevtModuleSw-MIC-SP8L                    OBJECT IDENTIFIER ::= { ibevtModuleSwitchType 1126 } -- 8-Port OC-3c/STM-1c POS Optical Interface Card
ibevtModuleSw-LSXM1TGS48FE1               OBJECT IDENTIFIER ::= { ibevtModuleSwitchType 1127 } -- 48-Port 10GBASE Ethernet SFP+ Optical Interface Board(FE)
ibevtModuleSw-LSXM1QGS24FE1               OBJECT IDENTIFIER ::= { ibevtModuleSwitchType 1128 } -- 24-Port 40GBASE Ethernet Optical Interface Board(QSFP+)
ibevtModuleSw-CSPEX-1504S                 OBJECT IDENTIFIER ::= { ibevtModuleSwitchType 1129 } -- Multi-Service Processing Board
ibevtModuleSw-CSPEX-1504X                 OBJECT IDENTIFIER ::= { ibevtModuleSwitchType 1130 } -- Multi-Service Processing Board
ibevtModuleSw-CSPEX-1404S                 OBJECT IDENTIFIER ::= { ibevtModuleSwitchType 1131 } -- Multi-Service Processing Board
ibevtModuleSw-CSPEX-1304S                 OBJECT IDENTIFIER ::= { ibevtModuleSwitchType 1132 } -- Multi-Service Processing Board
ibevtModuleSw-CSPEX-1404X                 OBJECT IDENTIFIER ::= { ibevtModuleSwitchType 1133 } -- Multi-Service Processing Board
ibevtModuleSw-CSPEX-1304X                 OBJECT IDENTIFIER ::= { ibevtModuleSwitchType 1134 } -- Multi-Service Processing Board
ibevtModuleSw-MIC-XP5L                    OBJECT IDENTIFIER ::= { ibevtModuleSwitchType 1135 } -- 5-Port 10GBASE-R/W Ethernet Optical Interface Card,(SFP+,LC)
ibevtModuleSw-MIC-XP2L                    OBJECT IDENTIFIER ::= { ibevtModuleSwitchType 1136 } -- 2-Port 10GBASE-R/W Ethernet Optical Interface Card,(SFP+,LC)
ibevtModuleSw-MIC-CP1L                    OBJECT IDENTIFIER ::= { ibevtModuleSwitchType 1137 } -- 1-Port 100G Optical Interface Card,(CFP,LC)
ibevtModuleSw-MIC-GP20L                   OBJECT IDENTIFIER ::= { ibevtModuleSwitchType 1138 } -- 20-Port 1000BASE-X Ethernet Optical Interface Card,(SFP,LC),Monolithic
ibevtModuleSw-MIC-GT20L                   OBJECT IDENTIFIER ::= { ibevtModuleSwitchType 1139 } -- 20-Port 1000BASE-X Ethernet Electrical Interface Card,(RJ45,LC),Monolithic
ibevtModuleSw-CEPC-XP48RX                 OBJECT IDENTIFIER ::= { ibevtModuleSwitchType 1140 } -- 48-Port 10GBASE-R/W Interface Module,(SFP+,LC)
ibevtModuleSw-CEPC-CP4RX                  OBJECT IDENTIFIER ::= { ibevtModuleSwitchType 1141 } -- 4-Port 100GBASE Ethernet Optical Interface Board(CFP2)
ibevtModuleSw-MIC-GP10L-V2                OBJECT IDENTIFIER ::= { ibevtModuleSwitchType 1142 } -- 10-Port 1000BASE-X Optical Interface Card,(SFP,LC)
ibevtModuleSw-CSR07SRPUD3                 OBJECT IDENTIFIER ::= { ibevtModuleSwitchType 1143 } -- Management and Route Process Board(UD3)
ibevtModuleSw-MIC-XP1L                    OBJECT IDENTIFIER ::= { ibevtModuleSwitchType 1144 } -- 1-Port 10GBASE-R/W Ethernet Optical Interface Card,(SFP+,LC)
ibevtModuleSw-CSFC-12E                    OBJECT IDENTIFIER ::= { ibevtModuleSwitchType 1145 } -- Switch Fabric Board
ibevtModuleSw-CEPC-XP24LX                 OBJECT IDENTIFIER ::= { ibevtModuleSwitchType 1146 } -- 24-Port 10GBASE-R/W Interface Module,(SFP+,LC)
ibevtModuleSw-IM-MSUX                     OBJECT IDENTIFIER ::= { ibevtModuleSwitchType 1147 } -- Multi-Service Processing Board,Monolithic
ibevtModuleSw-CSFC-12F                    OBJECT IDENTIFIER ::= { ibevtModuleSwitchType 1148 } -- Switch Fabric Board, Monolithic
ibevtModuleSw-CSR05SRP1N3                 OBJECT IDENTIFIER ::= { ibevtModuleSwitchType 1149 } -- Main Processing Unit(1N3)
ibevtModuleSw-CSPEX-1602X                 OBJECT IDENTIFIER ::= { ibevtModuleSwitchType 1150 } -- Service Processing Unit(1602X)
ibevtModuleSw-MIC-XP20L                   OBJECT IDENTIFIER ::= { ibevtModuleSwitchType 1151 } -- 20-port 10GBASE-R/W Ethernet Optical Interface Card(SFP+,LC)
ibevtModuleSw-MIC-CP2L                    OBJECT IDENTIFIER ::= { ibevtModuleSwitchType 1152 } -- 2-port 100G Ethernet Optical Interface Card(CFP2,LC)
ibevtModuleSw-IM-NGFWX-IV                 OBJECT IDENTIFIER ::= { ibevtModuleSwitchType 1153 } -- Next Generation Firewall Module
ibevtModuleSw-SFC-12E                     OBJECT IDENTIFIER ::= { ibevtModuleSwitchType 1154 } -- Switch Fabric Board

ibevtModuleSw-SPEX-1602X-E                OBJECT IDENTIFIER ::= { ibevtModuleSwitchType 1155 } -- Service Processing Unit(1602X)-E
ibevtModuleSw-SPEX-1602X-L                OBJECT IDENTIFIER ::= { ibevtModuleSwitchType 1156 } -- Service Processing Unit(1602X)-L
ibevtModuleSw-EPC-XP24LX-E                OBJECT IDENTIFIER ::= { ibevtModuleSwitchType 1157 } -- 24-Port 10GBASE-R/W Ethernet Optical Interface Line Processing Unit (SFP+,LC)-E
ibevtModuleSw-EPC-XP24LX-L                OBJECT IDENTIFIER ::= { ibevtModuleSwitchType 1158 } -- 24-Port 10GBASE-R/W Ethernet Optical Interface Line Processing Unit (SFP+,LC)-L
ibevtModuleSw-EPC-CP4RX-L                 OBJECT IDENTIFIER ::= { ibevtModuleSwitchType 1159 } -- 4-Port 100GBASE Ethernet Optical Interface Line Processing Unit (CFP2)-L
ibevtModuleSw-SPEX-1504X-E                OBJECT IDENTIFIER ::= { ibevtModuleSwitchType 1160 } -- Service Processing Unit(1504X)-E
ibevtModuleSw-SPEX-1504X-L                OBJECT IDENTIFIER ::= { ibevtModuleSwitchType 1161 } -- Service Processing Unit(1504X)-L
ibevtModuleSw-CSPEX-1602X-L               OBJECT IDENTIFIER ::= { ibevtModuleSwitchType 1162 } -- Service Processing Unit(1602X)-L
ibevtModuleSw-CEPC-XP24LX-L               OBJECT IDENTIFIER ::= { ibevtModuleSwitchType 1163 } -- 24-Port 10GBASE-R/W Ethernet Optical Interface Line Processing Unit (SFP+,LC)-L
ibevtModuleSw-CEPC-CP4RX-L                OBJECT IDENTIFIER ::= { ibevtModuleSwitchType 1164 } -- 4-port 100G Ethernet Optical Interface Line Processing Unit(QSFP28)
ibevtModuleSw-MIC-CP1L-E                  OBJECT IDENTIFIER ::= { ibevtModuleSwitchType 1165 } -- 1-port 100G Ethernet Optical Interface Card(CFP,LC)-E
ibevtModuleSw-MIC-XP4L-E                  OBJECT IDENTIFIER ::= { ibevtModuleSwitchType 1166 } -- 4-Port 10GBASE-R/W Ethernet Optical Interface Card,(SFP+,LC)-E
ibevtModuleSw-MIC-XP16L-E                 OBJECT IDENTIFIER ::= { ibevtModuleSwitchType 1167 } -- 16-port 10GBASE-R/W Ethernet Optical Interface Card(SFP+,LC)-E
ibevtModuleSw-MIC-GP20L-E                 OBJECT IDENTIFIER ::= { ibevtModuleSwitchType 1168 } -- 20-Port 1000BASE-X Ethernet Optical Interface Card,(SFP,LC)-E
ibevtModuleSw-MIC-GP10L-V2-E              OBJECT IDENTIFIER ::= { ibevtModuleSwitchType 1169 } -- 10-Port 1000BASE-X Ethernet Optical Interface Card(SFP,LC)-E
ibevtModuleSw-MIC-GT20L-E                 OBJECT IDENTIFIER ::= { ibevtModuleSwitchType 1170 } -- 20-Port 1000BASE-X Ethernet Electrical Interface Card,(RJ45,LC)-E
ibevtModuleSw-CSR05SRP1P3                 OBJECT IDENTIFIER ::= { ibevtModuleSwitchType 1171 } -- CR16018-F Main Processing Unit(1P3)
ibevtModuleSw-SR05SRP1P3                  OBJECT IDENTIFIER ::= { ibevtModuleSwitchType 1172 } -- SR8816-X Main Processing Unit(1P3)
ibevtModuleSw-CSFC-16E                    OBJECT IDENTIFIER ::= { ibevtModuleSwitchType 1173 } -- CR16018-F Fabric Module(E Type)
ibevtModuleSw-SFC-16E                     OBJECT IDENTIFIER ::= { ibevtModuleSwitchType 1174 } -- SR8816-X Fabric Module(E Type)
ibevtModuleSw-CSFC-08E                    OBJECT IDENTIFIER ::= { ibevtModuleSwitchType 1175 } -- CR16010-F Fabric Module(E Type)
ibevtModuleSw-SFC-08E                     OBJECT IDENTIFIER ::= { ibevtModuleSwitchType 1176 } -- SR8808-X Fabric Module(E Type)
ibevtModuleSw-IM-SMUX                     OBJECT IDENTIFIER ::= { ibevtModuleSwitchType 1177 } -- Security Monitor Unit (IM-SMUX)
ibevtModuleSw-IM-IPSX-IV                  OBJECT IDENTIFIER ::= { ibevtModuleSwitchType 1178 } -- Intrusion Prevention System Module
ibevtModuleSw-IM-ACGX-IV                  OBJECT IDENTIFIER ::= { ibevtModuleSwitchType 1179 } -- Application Control Gateway Module
ibevtModuleSw-SFC-08E1                    OBJECT IDENTIFIER ::= { ibevtModuleSwitchType 1180 } -- SR8808H-X Fabric Module(E Type)
ibevtModuleSw-CSFC-08E1                   OBJECT IDENTIFIER ::= { ibevtModuleSwitchType 1181 } -- CR16010H-F Fabric Module(E Type)
ibevtModuleSw-IM-ACG1000X-IV              OBJECT IDENTIFIER ::= { ibevtModuleSwitchType 1182 } -- SecPath ACG1000-Blade-X Application Control Module(SR88-X SecBladeIV)
ibevtModuleSw-MIC-QP1L                    OBJECT IDENTIFIER ::= { ibevtModuleSwitchType 1183 } -- 1-port 40G Ethernet Optical Interface Card(QSFP+,LC)
ibevtModuleSw-CSPEX-1804X                 OBJECT IDENTIFIER ::= { ibevtModuleSwitchType 1184 } -- Service Processing Unit(1804X)
ibevtModuleSw-MIC-CP2L-V2                 OBJECT IDENTIFIER ::= { ibevtModuleSwitchType 1185 } -- 2-port 100G Ethernet Optical Interface Card(QSFP28)
ibevtModuleSw-MIC-XP4L1                   OBJECT IDENTIFIER ::= { ibevtModuleSwitchType 1186 } -- 4-port 10GBASE-R/W Ethernet Optical Interface Card 1(SFP+,LC)
ibevtModuleSw-SFC-16T                     OBJECT IDENTIFIER ::= { ibevtModuleSwitchType 1187 } -- SR8816-X Fabric Module(T Type)
ibevtModuleSw-CSFC-16T                    OBJECT IDENTIFIER ::= { ibevtModuleSwitchType 1188 } -- CR16018-F Fabric Module(T Type)
ibevtModuleSw-SFC-08T                     OBJECT IDENTIFIER ::= { ibevtModuleSwitchType 1189 } -- SR8808H-X Fabric Module(T Type)
ibevtModuleSw-CSFC-08T                    OBJECT IDENTIFIER ::= { ibevtModuleSwitchType 1190 } -- CR16010H-F Fabric Module(T Type)
ibevtModuleSw-MIC-XP2L-LAN                OBJECT IDENTIFIER ::= { ibevtModuleSwitchType 1191 } -- 2-port 10GBASE-R Ethernet Optical Interface Card(SFP+,LC)-LAN
ibevtModuleSw-MIC-XP5L1                   OBJECT IDENTIFIER ::= { ibevtModuleSwitchType 1192 } -- 5-port 10GBASE-R/W Ethernet Optical Interface Card(SFP+,LC)
ibevtModuleSw-MIC-CP1L-V2                 OBJECT IDENTIFIER ::= { ibevtModuleSwitchType 1193 } -- 1-port 100G Ethernet Optical Interface Card(CFP2,LC)
ibevtModuleSw-CEPC-XP40LX                 OBJECT IDENTIFIER ::= { ibevtModuleSwitchType 1194 } -- 40-port 10GBASE-R/W Ethernet Optical Interface Line Processing Unit Module(SFP+,LC)
ibevtModuleSw-CEPC-CQ4LX                  OBJECT IDENTIFIER ::= { ibevtModuleSwitchType 1195 } -- 4-port 100G Ethernet Optical Interface Line Processing Unit Module(QSFP28,LC)


--
-- 1200 to 1399 reserved for secondary switches part II
--
ibevtModuleSw-LSU1QGC4SF0                 OBJECT IDENTIFIER ::= { ibevtModuleSwitchType 1201 } -- 4 Port 40G BASE Ethernet Optical Interface Board(CFP,SC)(SF)
ibevtModuleSw-LSU1QGS8SF0                 OBJECT IDENTIFIER ::= { ibevtModuleSwitchType 1202 } -- 8-Port 40G BASE Ethernet Optical Interface Board(QSFP,MPO)(SF)
ibevtModuleSw-LSU1TGS48SF0                OBJECT IDENTIFIER ::= { ibevtModuleSwitchType 1203 } -- 48-Port 10GBASE Ethernet SFP+ Optical Interface Board
ibevtModuleSw-LSU1QGS4SF0                 OBJECT IDENTIFIER ::= { ibevtModuleSwitchType 1204 } -- 4-Port 40G BASE Ethernet Optical Interface Board(QSFP,MPO)(SF)
ibevtModuleSw-LSU1TGS32SF0                OBJECT IDENTIFIER ::= { ibevtModuleSwitchType 1205 } -- 32-Port 10GBASE Ethernet SFP+ Optical Interface Board
ibevtModuleSw-LSU1FAB08D0                 OBJECT IDENTIFIER ::= { ibevtModuleSwitchType 1206 } -- Switching Fabric Module
ibevtModuleSw-LSU1FAB04B0                 OBJECT IDENTIFIER ::= { ibevtModuleSwitchType 1207 } -- Switching Fabric Module
ibevtModuleSw-LSU1FAB08B0                 OBJECT IDENTIFIER ::= { ibevtModuleSwitchType 1208 } -- Switching Fabric Module
ibevtModuleSw-LSU1FAB12D0                 OBJECT IDENTIFIER ::= { ibevtModuleSwitchType 1209 } -- Switching Fabric Module
ibevtModuleSw-LSU1FAB12B0                 OBJECT IDENTIFIER ::= { ibevtModuleSwitchType 1210 } -- Switching Fabric Module
ibevtModuleSw-LSU1FAB04D0                 OBJECT IDENTIFIER ::= { ibevtModuleSwitchType 1211 } -- Switching Fabric Module
ibevtModuleSw-LSQ1CTGS16SC0               OBJECT IDENTIFIER ::= { ibevtModuleSwitchType 1212 } -- Supervisor Engine Board With 16-Port 10GBASE Ethernet SFP+ Optical Interfaces
ibevtModuleSw-EWPX2CTGS16SC0              OBJECT IDENTIFIER ::= { ibevtModuleSwitchType 1213 } -- Supervisor Engine Board With 16-Port 10GBASE Ethernet SFP+ Optical Interfaces
ibevtModuleSw-LSU3WCMD0                   OBJECT IDENTIFIER ::= { ibevtModuleSwitchType 1214 } -- Access Controller Card
ibevtModuleSw-EWPX3WCMD0                  OBJECT IDENTIFIER ::= { ibevtModuleSwitchType 1215 } -- Access Controller Card
ibevtModuleSw-LSQ1QGS4SC0                 OBJECT IDENTIFIER ::= { ibevtModuleSwitchType 1216 } -- 4-Port 40G BASE Ethernet Optical Interface Board(QSFP+,MPO)(SC)
ibevtModuleSw-LSQ1QGC4SC0                 OBJECT IDENTIFIER ::= { ibevtModuleSwitchType 1217 } -- 4 Port 40GBASE Ethernet Optical Interface Board(CFP)(SC)
ibevtModuleSw-LSU1TGT24SF0                OBJECT IDENTIFIER ::= { ibevtModuleSwitchType 1218 } -- 24-Port 10GBASE-T Ethernet Electrical Interface Board(RJ45)(SF)
ibevtModuleSw-LSQ1QGS8SC3                 OBJECT IDENTIFIER ::= { ibevtModuleSwitchType 1219 } -- 8-Port 40G BASE Ethernet Optical Interface Board(QSFP+,MPO)
ibevtModuleSw-LSQ1TGS32SC3                OBJECT IDENTIFIER ::= { ibevtModuleSwitchType 1220 } -- 32-Port 10GBASE Ethernet SFP+ Optical Interface Board
ibevtModuleSw-LSQ1QGS4SC3                 OBJECT IDENTIFIER ::= { ibevtModuleSwitchType 1221 } -- 4-Port 40GBASE Ethernet Optical Interface Board(QSFP+,MPO)(SC)
ibevtModuleSw-LSQ1TGS48SC3                OBJECT IDENTIFIER ::= { ibevtModuleSwitchType 1222 } -- 48-Port 10GBASE Ethernet SFP+ Optical Interface Board
ibevtModuleSw-LSQ1QGC4SC3                 OBJECT IDENTIFIER ::= { ibevtModuleSwitchType 1223 } -- 4-Port 40GBASE Ethernet Optical Interface Board(CFP)(SC)
ibevtModuleSw-LSQ1FAB12D3                 OBJECT IDENTIFIER ::= { ibevtModuleSwitchType 1224 } -- Switch Fabric Board
ibevtModuleSw-LSQ1FAB08D3                 OBJECT IDENTIFIER ::= { ibevtModuleSwitchType 1225 } -- Switching Fabric Module
ibevtModuleSw-LSQ1FAB04D3                 OBJECT IDENTIFIER ::= { ibevtModuleSwitchType 1226 } -- Switching Fabric Module
ibevtModuleSw-LSQ1TGS8EB3                 OBJECT IDENTIFIER ::= { ibevtModuleSwitchType 1227 } -- 8-Port 10GBASE Ethernet SFP+ Optical Interface Board
ibevtModuleSw-LSQ1TGT24SC3                OBJECT IDENTIFIER ::= { ibevtModuleSwitchType 1228 } -- 24-Port 10GBASE-T Ethernet Electrical Interface Board(RJ45)(SC)
ibevtModuleSw-LSQ1FAB08B0                 OBJECT IDENTIFIER ::= { ibevtModuleSwitchType 1229 } -- Switching Fabric Module
ibevtModuleSw-EWPX2CTGS16SC               OBJECT IDENTIFIER ::= { ibevtModuleSwitchType 1230 } -- Supervisor Engine Board With 16-Port 10GBASE Ethernet SFP+ Optical Interfaces
ibevtModuleSw-LSU1SUPB0                   OBJECT IDENTIFIER ::= { ibevtModuleSwitchType 1231 } -- Supervisor Engine Board
ibevtModuleSw-LSQ1GP48SA0                 OBJECT IDENTIFIER ::= { ibevtModuleSwitchType 1232 } -- 48-Port 1000BASE-X Ethernet Optical Interface Board(SFP,LC)
ibevtModuleSw-LSQ1TGX2SA0                 OBJECT IDENTIFIER ::= { ibevtModuleSwitchType 1233 } -- 2-Port 10GBASE Ethernet Optical Interface Board(XFP,LC)
ibevtModuleSw-LSV1SRPUA1                  OBJECT IDENTIFIER ::= { ibevtModuleSwitchType 1234 } -- Supervisor Engine Board
ibevtModuleSw-LSV1QGS12SA1                OBJECT IDENTIFIER ::= { ibevtModuleSwitchType 1235 } -- 12-Port 40G BASE Ethernet Optical Interface Board(QSFP+)
ibevtModuleSw-LSV1MPUA1                   OBJECT IDENTIFIER ::= { ibevtModuleSwitchType 1236 } -- Supervisor Engine Board
ibevtModuleSw-LSX1SUP10A0                 OBJECT IDENTIFIER ::= { ibevtModuleSwitchType 1237 } -- Supervisor Engine Board
ibevtModuleSw-LSX1SUP16A0                 OBJECT IDENTIFIER ::= { ibevtModuleSwitchType 1238 } -- Supervisor Engine Board
ibevtModuleSw-LSX1SUP10A1                 OBJECT IDENTIFIER ::= { ibevtModuleSwitchType 1239 } -- Supervisor Engine Board
ibevtModuleSw-LSX1SUP16A1                 OBJECT IDENTIFIER ::= { ibevtModuleSwitchType 1240 } -- Supervisor Engine Board
ibevtModuleSw-LSX1FAB10B0                 OBJECT IDENTIFIER ::= { ibevtModuleSwitchType 1241 } -- Switch Fabric Board
ibevtModuleSw-LSX1FAB16B0                 OBJECT IDENTIFIER ::= { ibevtModuleSwitchType 1242 } -- Switch Fabric Board
ibevtModuleSw-LSX1FAB10B1                 OBJECT IDENTIFIER ::= { ibevtModuleSwitchType 1243 } -- Switch Fabric Board
ibevtModuleSw-LSX1FAB16B1                 OBJECT IDENTIFIER ::= { ibevtModuleSwitchType 1244 } -- Switch Fabric Board
ibevtModuleSw-LSX1QGS16EA0                OBJECT IDENTIFIER ::= { ibevtModuleSwitchType 1245 } -- Switch Fabric Board16-Port 40G BASE Ethernet Optical Interface Board(QSFP+,MPO)
ibevtModuleSw-LSX1TGS48EA0                OBJECT IDENTIFIER ::= { ibevtModuleSwitchType 1246 } -- 48-Port 10GBASE Ethernet SFP+ Optical Interface Board
ibevtModuleSw-LSX1QGS16EA1                OBJECT IDENTIFIER ::= { ibevtModuleSwitchType 1247 } -- Switch Fabric Board16-Port 40G BASE Ethernet Optical Interface Board(QSFP+,MPO)
ibevtModuleSw-LSX1TGS48EA1                OBJECT IDENTIFIER ::= { ibevtModuleSwitchType 1248 } -- 48-Port 10GBASE Ethernet SFP+ Optical Interface Board
ibevtModuleSw-LSU1TGT24SF9                OBJECT IDENTIFIER ::= { ibevtModuleSwitchType 1249 } -- 24-Port 10GBASE-T Ethernet Electrical Interface Board(RJ45)(SF)
ibevtModuleSw-LSU1QGS8SF9                 OBJECT IDENTIFIER ::= { ibevtModuleSwitchType 1250 } -- 8-Port 40G BASE Ethernet Optical Interface Board(QSFP+,MPO)(SF)
ibevtModuleSw-LSU1QGS4SF9                 OBJECT IDENTIFIER ::= { ibevtModuleSwitchType 1251 } -- 4-Port 40GBASE Ethernet QSFP+ Optical Interface Board(QSFP+,MPO)(SF)
ibevtModuleSw-LSU1TGS48SF9                OBJECT IDENTIFIER ::= { ibevtModuleSwitchType 1252 } -- 48-Port 10GBASE Ethernet SFP+ Optical Interface Board
ibevtModuleSw-LSU1TGS32SF9                OBJECT IDENTIFIER ::= { ibevtModuleSwitchType 1253 } -- 32-Port 10GBASE Ethernet SFP+ Optical Interface Board
ibevtModuleSw-LSU1FAB08D9                 OBJECT IDENTIFIER ::= { ibevtModuleSwitchType 1254 } -- Switching Fabric Module
ibevtModuleSw-LSU1SUPB9                   OBJECT IDENTIFIER ::= { ibevtModuleSwitchType 1255 } -- Supervisor Engine Board
ibevtModuleSw-LSQ3GV48SC0                 OBJECT IDENTIFIER ::= { ibevtModuleSwitchType 1256 } -- 48-Port 1000Base-T Gigabit Ethernet Interface Board(RJ45), PoE Plus
ibevtModuleSw-LSX1QGS12EC1                OBJECT IDENTIFIER ::= { ibevtModuleSwitchType 1257 } -- 12-Port 40GBASE Ethernet Optical Interface Board(QSFP+)
ibevtModuleSw-LSX1QGS12EC0                OBJECT IDENTIFIER ::= { ibevtModuleSwitchType 1258 } -- 12-Port 40GBASE Ethernet Optical Interface Board(QSFP+)
ibevtModuleSw-LSX1TGS48EC0                OBJECT IDENTIFIER ::= { ibevtModuleSwitchType 1259 } -- 48-Port 10GBASE Ethernet SFP+ Optical Interface Board
ibevtModuleSw-LSX1TGS48EC1                OBJECT IDENTIFIER ::= { ibevtModuleSwitchType 1260 } -- 48-Port 10GBASE Ethernet SFP+ Optical Interface Board
ibevtModuleSw-LSX1TGS24EC0                OBJECT IDENTIFIER ::= { ibevtModuleSwitchType 1261 } -- 24-Port 10GBASE Ethernet SFP+ Optical Interface Board(EC)
ibevtModuleSw-LSX1TGS24EC1                OBJECT IDENTIFIER ::= { ibevtModuleSwitchType 1262 } -- 24-Port 10GBASE Ethernet SFP+ Optical Interface Board(EC)
ibevtModuleSw-LSX1FAB10A0                 OBJECT IDENTIFIER ::= { ibevtModuleSwitchType 1263 } -- Switch Fabric Board,For 10 Slots Chassis
ibevtModuleSw-LSX1FAB16A1                 OBJECT IDENTIFIER ::= { ibevtModuleSwitchType 1264 } -- Switch Fabric Board,For 16 Slots Chassis
ibevtModuleSw-LSX1QGS12FB0                OBJECT IDENTIFIER ::= { ibevtModuleSwitchType 1265 } -- 12-Port 40GBASE Ethernet Optical Interface Board(QSFP+)
ibevtModuleSw-LSX1TGS24FB0                OBJECT IDENTIFIER ::= { ibevtModuleSwitchType 1266 } -- 24-Port 10GBASE Ethernet SFP+ Optical Interface Board(FB)
ibevtModuleSw-LSX1TGS48FB0                OBJECT IDENTIFIER ::= { ibevtModuleSwitchType 1267 } -- 48-Port 10GBASE Ethernet SFP+ Optical Interface Board(FB)
ibevtModuleSw-LSX1QGS12EB1                OBJECT IDENTIFIER ::= { ibevtModuleSwitchType 1268 } -- 12-Port 40GBASE Ethernet Optical Interface Board(QSFP+)
ibevtModuleSw-LSX1TGS24EB1                OBJECT IDENTIFIER ::= { ibevtModuleSwitchType 1269 } -- 24-Port 10GBASE Ethernet SFP+ Optical Interface Board(EB)
ibevtModuleSw-LSX1FAB10A1                 OBJECT IDENTIFIER ::= { ibevtModuleSwitchType 1270 } -- Switch Fabric Board,For 10 Slots Chassis
ibevtModuleSw-LSX1TGS48EB1                OBJECT IDENTIFIER ::= { ibevtModuleSwitchType 1271 } -- 48-Port 10GBASE Ethernet SFP+ Optical Interface Board(EB)
ibevtModuleSw-LSX1GP48EB1                 OBJECT IDENTIFIER ::= { ibevtModuleSwitchType 1272 } -- 44-Port GE Optical Interface(SFP,LC)+4-Port 10GE Optical Interface Board(SFP+,LC)
ibevtModuleSw-LSX1GP48FB0                 OBJECT IDENTIFIER ::= { ibevtModuleSwitchType 1273 } -- 44-Port GE Optical Interface(SFP,LC)+4-Port 10GE Optical Interface Board(SFP+,LC)
ibevtModuleSw-LSX1GT48FC0                 OBJECT IDENTIFIER ::= { ibevtModuleSwitchType 1274 } -- 48-Port 1000Base-T Gigabit Ethernet Interface Module(RJ45)(FC)
ibevtModuleSw-LSX1GT48FC1                 OBJECT IDENTIFIER ::= { ibevtModuleSwitchType 1275 } -- 48-Port 1000Base-T Gigabit Ethernet Interface Module(RJ45)(FC)
ibevtModuleSw-LSX1GP48FC0                 OBJECT IDENTIFIER ::= { ibevtModuleSwitchType 1276 } -- 48-Port 1000BASE-X Gigabit Ethernet Optical Interface Module(SFP,LC)(FC)
ibevtModuleSw-LSX1GP48FC1                 OBJECT IDENTIFIER ::= { ibevtModuleSwitchType 1277 } -- 48-Port 1000BASE-X Gigabit Ethernet Optical Interface Module(SFP,LC)(FC)
ibevtModuleSw-LSX1QGS12FC0                OBJECT IDENTIFIER ::= { ibevtModuleSwitchType 1278 } -- 12-Port 40GBASE Ethernet Optical Interface Module(QSFP+)(FC)
ibevtModuleSw-LSX1QGS12FC1                OBJECT IDENTIFIER ::= { ibevtModuleSwitchType 1279 } -- 12-Port 40GBASE Ethernet Optical Interface Module(QSFP+)(FC)
ibevtModuleSw-LSX2TGS48EA1                OBJECT IDENTIFIER ::= { ibevtModuleSwitchType 1280 } -- 48-Port 10GBASE Ethernet SFP+ Optical Interface Board(EA)
ibevtModuleSw-LSX1CGC4EB1                 OBJECT IDENTIFIER ::= { ibevtModuleSwitchType 1281 } -- 4-Port 100GBASE Ethernet Optical Interface Board(CFP),Monolithic
ibevtModuleSw-LSX1CGC4EC0                 OBJECT IDENTIFIER ::= { ibevtModuleSwitchType 1282 } -- 4-Port 100GBASE Ethernet Optical Interface Board(CFP),Monolithic
ibevtModuleSw-LSX1GT48EB1                 OBJECT IDENTIFIER ::= { ibevtModuleSwitchType 1283 } -- 48-Port 1000Base-T Gigabit Ethernet Interface Board(RJ45)
ibevtModuleSw-LSX1GT48FB0                 OBJECT IDENTIFIER ::= { ibevtModuleSwitchType 1284 } -- 48-Port 1000Base-T Gigabit Ethernet Interface Board(RJ45)
ibevtModuleSw-LSX1FAB16S1                 OBJECT IDENTIFIER ::= { ibevtModuleSwitchType 1285 } -- Switch Fabric Board,For 16 Slots Chassis
ibevtModuleSw-LSQ1SUPB3                   OBJECT IDENTIFIER ::= { ibevtModuleSwitchType 1286 } -- Supervisor Engine Board
ibevtModuleSw-LSU1CGC2SE0                 OBJECT IDENTIFIER ::= { ibevtModuleSwitchType 1287 } -- 2 Port 100GBASE Ethernet Optical Interface Board(CFP)(SE)
ibevtModuleSw-LSU1TGS16SF0                OBJECT IDENTIFIER ::= { ibevtModuleSwitchType 1288 } -- 16-Port 10GBASE Ethernet SFP+ Optical Interface Board
ibevtModuleSw-LSU1TGS8SF0                 OBJECT IDENTIFIER ::= { ibevtModuleSwitchType 1289 } -- 8-Port 10GBASE Ethernet SFP+ Optical Interface Board
ibevtModuleSw-LSQ1TGS4SC0                 OBJECT IDENTIFIER ::= { ibevtModuleSwitchType 1290 } -- 4-Port 10GBASE Ethernet SFP+ Optical Interface Board
ibevtModuleSw-LSU1GT48SE3                 OBJECT IDENTIFIER ::= { ibevtModuleSwitchType 1291 } -- 48-Port 1000Base-T Gigabit Ethernet Interface Board(RJ45)
ibevtModuleSw-LSU1GP48SE3                 OBJECT IDENTIFIER ::= { ibevtModuleSwitchType 1292 } -- 48-Port 1000BASE Ethernet Optical Interface Board(SFP,LC)
ibevtModuleSw-LSX1SUP10B0                 OBJECT IDENTIFIER ::= { ibevtModuleSwitchType 1293 } -- Supervisor Engine Board
ibevtModuleSw-LSX1SUP16B0                 OBJECT IDENTIFIER ::= { ibevtModuleSwitchType 1294 } -- Supervisor Engine Board
ibevtModuleSw-LSX1SUP10B1                 OBJECT IDENTIFIER ::= { ibevtModuleSwitchType 1295 } -- Supervisor Engine Board
ibevtModuleSw-LSX1SUP16B1                 OBJECT IDENTIFIER ::= { ibevtModuleSwitchType 1296 } -- Supervisor Engine Board
ibevtModuleSw-LSQ1CGV24PSC3               OBJECT IDENTIFIER ::= { ibevtModuleSwitchType 1297 } -- Switching and Routing Processing Unit with 24 10/100/1000BASE-T Electrical Ports(RJ45),including 4 Combo Ports,SFP Req,PoE,No Spell
ibevtModuleSw-LSQ1SRPA8                   OBJECT IDENTIFIER ::= { ibevtModuleSwitchType 1298 } -- Supervisor Engine Board
ibevtModuleSw-LSQ1CGP24TSC8               OBJECT IDENTIFIER ::= { ibevtModuleSwitchType 1299 } -- Supervisor Engine Board
ibevtModuleSw-LSQ1CGT24PSC8               OBJECT IDENTIFIER ::= { ibevtModuleSwitchType 1300 } -- Supervisor Engine Board
ibevtModuleSw-LSQ1GT24PSA8                OBJECT IDENTIFIER ::= { ibevtModuleSwitchType 1301 } -- 24-Port 10/100/1000BASE-T Electrical(RJ45) Interface Board,including 4 Combo Ports,SFP Req,Upgradeable to PoE
ibevtModuleSw-LSQ1GP24TSA8                OBJECT IDENTIFIER ::= { ibevtModuleSwitchType 1302 } -- 16-Port 1000BASE-X Gigabit Ethernet Optical(SFP,LC) And 8-Port 10/100/1000BASE-T RJ45/1000BASE-X SFP Combo Interface Board
ibevtModuleSw-LSQ1GT48SA8                 OBJECT IDENTIFIER ::= { ibevtModuleSwitchType 1303 } -- 48-Port 1000Base-T Gigabit Ethernet Interface Board(RJ45)
ibevtModuleSw-LSQ1GP48SA8                 OBJECT IDENTIFIER ::= { ibevtModuleSwitchType 1304 } -- 48-Port 1000BASE-X Ethernet Optical Interface Board(SFP,LC)
ibevtModuleSw-LSQ1TGS4SC8                 OBJECT IDENTIFIER ::= { ibevtModuleSwitchType 1305 } -- 4-Port 10GBASE Ethernet SFP+ Optical Interface Board
ibevtModuleSw-LSQ1TGS8SC8                 OBJECT IDENTIFIER ::= { ibevtModuleSwitchType 1306 } -- 8-Port 10GBASE Ethernet SFP+ Optical Interface Board
ibevtModuleSw-LSU1GT24SE3                 OBJECT IDENTIFIER ::= { ibevtModuleSwitchType 1307 } -- 24-Port 1000BASE-T Ethernet Interface Board (RJ45)
ibevtModuleSw-LSU1GP12SE3                 OBJECT IDENTIFIER ::= { ibevtModuleSwitchType 1308 } -- 12-Port 1000BASE-X Ethernet Optical Interface Board(SFP,LC)
ibevtModuleSw-LSU1GP24SE3                 OBJECT IDENTIFIER ::= { ibevtModuleSwitchType 1309 } -- 24 Port 1000BASE-X Ethernet Optical Interface Board(SFP,LC)
ibevtModuleSw-LSU1T24XGSE3                OBJECT IDENTIFIER ::= { ibevtModuleSwitchType 1310 } -- 24-Port 1000BASE-T Gigabit Ethernet Interface(RJ45)+2-Port 10GBASE Ethernet Optical Interface Board(XFP,LC)
ibevtModuleSw-LSU1P24XGSE3                OBJECT IDENTIFIER ::= { ibevtModuleSwitchType 1311 } -- 24-Port 1000BASE-X Gigabit Ethernet Optical Interface(SFP,LC)+2-Port 10GBASE Ethernet Optical Interface Board(XFP,LC)
ibevtModuleSw-LSU1GP24TSE3                OBJECT IDENTIFIER ::= { ibevtModuleSwitchType 1312 } -- 16-Port 1000BASE-X Gigabit Ethernet Optical(SFP,LC) And 8-Port 10/100/1000BASE-T RJ45/1000BASE-X SFP Combo Interface Board
ibevtModuleSw-LSU1GT40PSE3                OBJECT IDENTIFIER ::= { ibevtModuleSwitchType 1313 } -- 40-Port 10/100/1000BASE-T Electrical(RJ45) And 8-Port 1000BASE-X Optical Ethernet Interface Board(SFP,LC),PoE
ibevtModuleSw-LSV1TGS24SA1                OBJECT IDENTIFIER ::= { ibevtModuleSwitchType 1314 } -- 24-Port 10G BASE Ethernet Optical Interface Board(SFP+)
ibevtModuleSw-LSVM1SRPA1                  OBJECT IDENTIFIER ::= { ibevtModuleSwitchType 1315 } -- Switching Fabric Module
ibevtModuleSw-LSVM1SRPC1                  OBJECT IDENTIFIER ::= { ibevtModuleSwitchType 1316 } -- Switching Fabric Module
ibevtModuleSw-LSX1FAB16S0                 OBJECT IDENTIFIER ::= { ibevtModuleSwitchType 1317 } -- Switch Fabric Board,For 16 Slots Chassis
ibevtModuleSw-LSU1WCME0                   OBJECT IDENTIFIER ::= { ibevtModuleSwitchType 1318 } -- Access Controller Service Board
ibevtModuleSw-EWPX1WCME0                  OBJECT IDENTIFIER ::= { ibevtModuleSwitchType 1319 } -- Access Controller Service Board
ibevtModuleSw-LSUM1TGS48SG0               OBJECT IDENTIFIER ::= { ibevtModuleSwitchType 1320 } -- 48-Port 10GBASE-R Ethernet SFP+ Optical Interface Board(SG)
ibevtModuleSw-LSUM1QGS12SG0               OBJECT IDENTIFIER ::= { ibevtModuleSwitchType 1321 } -- 12-Port 40GBASE-R Ethernet QSFP+ Optical Interface Board(SG)
ibevtModuleSw-LSUM1GP44TSEC0              OBJECT IDENTIFIER ::= { ibevtModuleSwitchType 1322 } -- 44-Port 1000BASE-R Ethernet SFP Optical Interface Board(EC)+4-Port 10GBASE-R Ethernet SFP+ Optical Interface Board(EC)
ibevtModuleSw-LSUM1TGS24EC0               OBJECT IDENTIFIER ::= { ibevtModuleSwitchType 1323 } -- 24-Port 10GBASE-R Ethernet SFP+ Optical Interface Board(EC)
ibevtModuleSw-LSUM1QGS6EC0                OBJECT IDENTIFIER ::= { ibevtModuleSwitchType 1324 } -- 6-Port 40GBASE-R Ethernet QSFP+ Optical Interface Board(EC)
ibevtModuleSw-LSUM1CGC2EC0                OBJECT IDENTIFIER ::= { ibevtModuleSwitchType 1325 } -- 2-Port 100GBASE-R Ethernet CFP Optical Interface Board(EC)
ibevtModuleSw-LSU1CGC2SE9                 OBJECT IDENTIFIER ::= { ibevtModuleSwitchType 1326 } -- 2 Port 100GBASE Ethernet Optical Interface Board(CFP)(SE)
ibevtModuleSw-LSXM1QGS24EX1               OBJECT IDENTIFIER ::= { ibevtModuleSwitchType 1327 } -- 24 Ports 40G BASE Ethernet Optical Interface Board(QSFP+,MPO),No Spell
ibevtModuleSw-LSXM1QGS24FB0               OBJECT IDENTIFIER ::= { ibevtModuleSwitchType 1328 } -- 24 Ports 40G BASE Ethernet Optical Interface Board(QSFP+,MPO),No Spell
ibevtModuleSw-LSVM1QGS12FX1               OBJECT IDENTIFIER ::= { ibevtModuleSwitchType 1329 } -- 12-Port 40G BASE Ethernet Optical Interface Module(QSFP+,MPO/LC)
ibevtModuleSw-LSVM1TGS24FX1               OBJECT IDENTIFIER ::= { ibevtModuleSwitchType 1330 } -- 24-Port 10G BASE Ethernet Optical Interface Module(SFP+,LC)
ibevtModuleSw-LSVM1QGS6C2FX1              OBJECT IDENTIFIER ::= { ibevtModuleSwitchType 1331 } -- 2-Port 100GBASE Ethernet Optical Interface(CXP,MPO)+6-Port 40GBASE Ethernet Optical Interface(QSFP+,MPO/LC)+4-Port 10G BASE Ethernet Optical Interface Module(SFP+,LC)
ibevtModuleSw-LSQM2GP44TSSC0              OBJECT IDENTIFIER ::= { ibevtModuleSwitchType 1332 } -- 44-Port GE Optical Interface(SFP,LC)+4-Port 10GE Optical Interface Board(SFP+,LC)(SC)
ibevtModuleSw-LSQM2GP44TSSC3              OBJECT IDENTIFIER ::= { ibevtModuleSwitchType 1333 } -- 44-Port GE Optical Interface(SFP,LC)+4-Port 10GE Optical Interface Board(SFP+,LC)(SC)
ibevtModuleSw-LSQM2GP24TSSC0              OBJECT IDENTIFIER ::= { ibevtModuleSwitchType 1334 } -- 24-Port GE Optical Interface(SFP,LC)+4-Port 10GE Optical Interface Board(SFP+,LC)(SC)
ibevtModuleSw-LSQM2GP24TSSC3              OBJECT IDENTIFIER ::= { ibevtModuleSwitchType 1335 } -- 24-Port GE Optical Interface(SFP,LC)+4-Port 10GE Optical Interface Board(SFP+,LC)(SC)
ibevtModuleSw-LSQM2GT24PTSSC0             OBJECT IDENTIFIER ::= { ibevtModuleSwitchType 1336 } -- 24-Port 1000Base-T Gigabit Ethernet Interface Board(RJ45)+20-Port GE Optical Interface(SFP,LC)+4-Port 10GE Optical Interface Board(SFP+,LC)(SC)
ibevtModuleSw-LSQM2GT24PTSSC3             OBJECT IDENTIFIER ::= { ibevtModuleSwitchType 1337 } -- 24-Port 1000Base-T Gigabit Ethernet Interface Board(RJ45)+20-Port GE Optical Interface(SFP,LC)+4-Port 10GE Optical Interface Board(SFP+,LC)(SC)
ibevtModuleSw-LSQM2GT24TSSC0              OBJECT IDENTIFIER ::= { ibevtModuleSwitchType 1338 } -- 24-Port 1000Base-T Gigabit Ethernet Interface Board(RJ45)+4-Port 10GE Optical Interface Board(SFP+,LC)(SC)
ibevtModuleSw-LSQM2GT24TSSC3              OBJECT IDENTIFIER ::= { ibevtModuleSwitchType 1339 } -- 24-Port 1000Base-T Gigabit Ethernet Interface Board(RJ45)+4-Port 10GE Optical Interface Board(SFP+,LC)(SC)
ibevtModuleSw-LSQM2GT48SC0                OBJECT IDENTIFIER ::= { ibevtModuleSwitchType 1340 } -- 48-Port 1000Base-T Gigabit Ethernet Interface Board(RJ45)(SC)
ibevtModuleSw-LSQM2GT48SC3                OBJECT IDENTIFIER ::= { ibevtModuleSwitchType 1341 } -- 48-Port 1000Base-T Gigabit Ethernet Interface Board(RJ45)(SC)
ibevtModuleSw-LSQM4GV48SC0                OBJECT IDENTIFIER ::= { ibevtModuleSwitchType 1342 } -- 48-Port 1000Base-T Gigabit Ethernet Interface Board(RJ45)(SC)-POE
ibevtModuleSw-LSQM4GV48SC3                OBJECT IDENTIFIER ::= { ibevtModuleSwitchType 1343 } -- 48-Port 1000Base-T Gigabit Ethernet Interface Board(RJ45)(SC)-POE
ibevtModuleSw-LSQM2TGS16SF0               OBJECT IDENTIFIER ::= { ibevtModuleSwitchType 1344 } -- 16-Port 10GE Optical Interface Board(SFP+,LC)(SF)
ibevtModuleSw-LSQM2TGS16SF3               OBJECT IDENTIFIER ::= { ibevtModuleSwitchType 1345 } -- 16-Port 10GE Optical Interface Board(SFP+,LC)(SF)
ibevtModuleSw-LSQM2MPUD0                  OBJECT IDENTIFIER ::= { ibevtModuleSwitchType 1346 } -- Supervisor Engine Board
ibevtModuleSw-LSQM2MPUD3                  OBJECT IDENTIFIER ::= { ibevtModuleSwitchType 1347 } -- Supervisor Engine Board
ibevtModuleSw-LSQM3MPUA0                  OBJECT IDENTIFIER ::= { ibevtModuleSwitchType 1348 } -- Supervisor Engine Board
ibevtModuleSw-LSQM3MPUA3                  OBJECT IDENTIFIER ::= { ibevtModuleSwitchType 1349 } -- Supervisor Engine Board
ibevtModuleSw-LSUM2GP44TSSE0              OBJECT IDENTIFIER ::= { ibevtModuleSwitchType 1350 } -- 44-Port GE Optical Interface(SFP,LC)+4-Port 10GE Optical Interface Board(SFP+,LC)(SE)
ibevtModuleSw-LSUM2GP44TSSC3              OBJECT IDENTIFIER ::= { ibevtModuleSwitchType 1351 } -- 44-Port GE Optical Interface(SFP,LC)+4-Port 10GE Optical Interface Board(SFP+,LC)(SC)
ibevtModuleSw-LSUM2GP24TSSE0              OBJECT IDENTIFIER ::= { ibevtModuleSwitchType 1352 } -- 24-Port GE Optical Interface(SFP,LC)+4-Port 10GE Optical Interface Board(SFP+,LC)(SE)
ibevtModuleSw-LSUM2GP24TSSC3              OBJECT IDENTIFIER ::= { ibevtModuleSwitchType 1353 } -- 24-Port GE Optical Interface(SFP,LC)+4-Port 10GE Optical Interface Board(SFP+,LC)(SC)
ibevtModuleSw-LSUM2GT24PTSSE0             OBJECT IDENTIFIER ::= { ibevtModuleSwitchType 1354 } -- 24-Port 1000Base-T Gigabit Ethernet Interface Board(RJ45)+20-Port GE Optical Interface(SFP,LC)+4-Port 10GE Optical Interface Board(SFP+,LC)(SE)
ibevtModuleSw-LSUM2GT24PTSSC3             OBJECT IDENTIFIER ::= { ibevtModuleSwitchType 1355 } -- 24-Port 1000Base-T Gigabit Ethernet Interface Board(RJ45)+20-Port GE Optical Interface(SFP,LC)+4-Port 10GE Optical Interface Board(SFP+,LC)(SC)
ibevtModuleSw-LSUM2GT24TSSE0              OBJECT IDENTIFIER ::= { ibevtModuleSwitchType 1356 } -- 24-Port 1000Base-T Gigabit Ethernet Interface Board(RJ45)+4-Port 10GE Optical Interface Board(SFP+,LC)(SE)
ibevtModuleSw-LSUM2GT24TSSC3              OBJECT IDENTIFIER ::= { ibevtModuleSwitchType 1357 } -- 24-Port 1000Base-T Gigabit Ethernet Interface Board(RJ45)+4-Port 10GE Optical Interface Board(SFP+,LC)(SC)
ibevtModuleSw-LSUM2GT48SE0                OBJECT IDENTIFIER ::= { ibevtModuleSwitchType 1358 } -- 48-Port 1000Base-T Gigabit Ethernet Interface Board(RJ45)(SE)
ibevtModuleSw-LSUM2GT48SC3                OBJECT IDENTIFIER ::= { ibevtModuleSwitchType 1359 } -- 48-Port 1000Base-T Gigabit Ethernet Interface Board(RJ45)(SC)
ibevtModuleSw-LSUM2GV48SE0                OBJECT IDENTIFIER ::= { ibevtModuleSwitchType 1360 } -- 48-Port 1000Base-T Gigabit Ethernet Interface Board(RJ45)(SE)-POE
ibevtModuleSw-LSUM2GV48SC3                OBJECT IDENTIFIER ::= { ibevtModuleSwitchType 1361 } -- 48-Port 1000Base-T Gigabit Ethernet Interface Board(RJ45)(SC)-POE
ibevtModuleSw-LSUM2TGS16SF0               OBJECT IDENTIFIER ::= { ibevtModuleSwitchType 1362 } -- 16-Port 10GE Optical Interface Board(SFP+,LC)(SF)
ibevtModuleSw-LSUM2TGS16SF3               OBJECT IDENTIFIER ::= { ibevtModuleSwitchType 1363 } -- 16-Port 10GE Optical Interface Board(SFP+,LC)(SF)
ibevtModuleSw-LSUM1MPU06B0                OBJECT IDENTIFIER ::= { ibevtModuleSwitchType 1364 } -- Supervisor Engine Board
ibevtModuleSw-LSUM1MPU06B3                OBJECT IDENTIFIER ::= { ibevtModuleSwitchType 1365 } -- Supervisor Engine Board
ibevtModuleSw-LSUM1MPU10C0                OBJECT IDENTIFIER ::= { ibevtModuleSwitchType 1366 } -- Supervisor Engine Board
ibevtModuleSw-LSUM1MPU10C3                OBJECT IDENTIFIER ::= { ibevtModuleSwitchType 1367 } -- Supervisor Engine Board
ibevtModuleSw-LSUM1FAB06C0                OBJECT IDENTIFIER ::= { ibevtModuleSwitchType 1368 } -- Switching Fabric Module
ibevtModuleSw-LSUM1FAB06C3                OBJECT IDENTIFIER ::= { ibevtModuleSwitchType 1369 } -- Switching Fabric Module
ibevtModuleSw-LSUM1FAB10C0                OBJECT IDENTIFIER ::= { ibevtModuleSwitchType 1370 } -- Switching Fabric Module
ibevtModuleSw-LSUM1FAB10C3                OBJECT IDENTIFIER ::= { ibevtModuleSwitchType 1371 } -- Switching Fabric Module
ibevtModuleSw-LSXM1SUPA1                  OBJECT IDENTIFIER ::= { ibevtModuleSwitchType 1372 } -- Supervisor Engine Module
ibevtModuleSw-LSXM1SFF16B1                OBJECT IDENTIFIER ::= { ibevtModuleSwitchType 1373 } -- Switch Fabric Board
ibevtModuleSw-LSUM1SPMAEC0                OBJECT IDENTIFIER ::= { ibevtModuleSwitchType 1374 } -- 4-Port Multiservice Processing Engine
ibevtModuleSw-LSXM1SUPB1                  OBJECT IDENTIFIER ::= { ibevtModuleSwitchType 1375 } -- Supervisor Engine Module
ibevtModuleSw-LSXM1SFF08B1                OBJECT IDENTIFIER ::= { ibevtModuleSwitchType 1376 } -- Switching Fabric Module,Type B(F1)
ibevtModuleSw-LSXM1TGS4GPEB1              OBJECT IDENTIFIER ::= { ibevtModuleSwitchType 1377 } -- 44-Port GE Optical Interface(SFP,LC)+4-Port 10GE Optical Interface Module(SFP+,LC)(EB)
ibevtModuleSw-LSXM1TGS16EA1               OBJECT IDENTIFIER ::= { ibevtModuleSwitchType 1378 } -- 16-Port 10GBASE Ethernet Optical Interface Module(SFP+,LC)(EA)
ibevtModuleSw-LSXM1TGS8EA1                OBJECT IDENTIFIER ::= { ibevtModuleSwitchType 1379 } -- 8-Port 10GBASE Ethernet Optical Interface Module(SFP+,LC)(EA)
ibevtModuleSw-LSXM1QGS36FX1               OBJECT IDENTIFIER ::= { ibevtModuleSwitchType 1380 } -- 36-Port 40GBASE Ethernet Optical Interface Module(QSFP+)(FX)
ibevtModuleSw-LSXM1SFF16C1                OBJECT IDENTIFIER ::= { ibevtModuleSwitchType 1381 } -- Switching Fabric Module
ibevtModuleSw-LSQM3MPUB0                  OBJECT IDENTIFIER ::= { ibevtModuleSwitchType 1382 } -- Supervisor Engine Board
ibevtModuleSw-LSQM3MPUB3                  OBJECT IDENTIFIER ::= { ibevtModuleSwitchType 1383 } -- Supervisor Engine Board
ibevtModuleSw-LSQM2MPUC0                  OBJECT IDENTIFIER ::= { ibevtModuleSwitchType 1384 } -- Supervisor Engine Board
ibevtModuleSw-LSQM2MPUC3                  OBJECT IDENTIFIER ::= { ibevtModuleSwitchType 1385 } -- Supervisor Engine Board
ibevtModuleSw-LST1FW3B1                   OBJECT IDENTIFIER ::= { ibevtModuleSwitchType 1386 } -- Firewall Board
ibevtModuleSw-LSX1NSCEA1                  OBJECT IDENTIFIER ::= { ibevtModuleSwitchType 1387 } -- NetStream Service Board
ibevtModuleSw-LSX1FWCEA1                  OBJECT IDENTIFIER ::= { ibevtModuleSwitchType 1388 } -- Firewall Service Board
ibevtModuleSw-LSXM1ADECEA1                OBJECT IDENTIFIER ::= { ibevtModuleSwitchType 1389 } -- Application Dilevery Engine Module,Domestic&Overseas Version
ibevtModuleSw-LSXM1SFF16A1                OBJECT IDENTIFIER ::= { ibevtModuleSwitchType 1390 } -- Switching Fabric Module
ibevtModuleSw-LSV1MPUA0                   OBJECT IDENTIFIER ::= { ibevtModuleSwitchType 1391 } -- Supervisor Engine Board
ibevtModuleSw-LSVM1SRPA0                  OBJECT IDENTIFIER ::= { ibevtModuleSwitchType 1392 } -- Switching Fabric Module
ibevtModuleSw-LSVM1SRPC0                  OBJECT IDENTIFIER ::= { ibevtModuleSwitchType 1393 } -- Switching Fabric Module
ibevtModuleSw-LSV1QGS12SA0                OBJECT IDENTIFIER ::= { ibevtModuleSwitchType 1394 } -- 12-Port 40G BASE Ethernet Optical Interface Board(QSFP+)
ibevtModuleSw-LSVM1QGS12FX0               OBJECT IDENTIFIER ::= { ibevtModuleSwitchType 1395 } -- 12-Port 40G BASE Ethernet Optical Interface Module(QSFP+,MPO/LC)
ibevtModuleSw-LSVM1TGS24FX0               OBJECT IDENTIFIER ::= { ibevtModuleSwitchType 1396 } -- 24-Port 10G BASE Ethernet Optical Interface Module(SFP+,LC)
ibevtModuleSw-LSVM1QGS6C2FX0              OBJECT IDENTIFIER ::= { ibevtModuleSwitchType 1397 } -- 2-Port 100GBASE Ethernet Optical Interface(CXP,MPO)+6-Port 40GBASE Ethernet Optical Interface(QSFP+,MPO/LC)+4-Port 10G BASE Ethernet Optical Interface Module(SFP+,LC)
ibevtModuleSw-LSQ2FWBSC0                  OBJECT IDENTIFIER ::= { ibevtModuleSwitchType 1398 } -- Gigabit Firewall Card, 4 Gigabit Port for Management
ibevtModuleSw-LSQM1SRP8X2QE0              OBJECT IDENTIFIER ::= { ibevtModuleSwitchType 1399 } -- Supervisor Engine Board With 8-Port 10GBASE Ethernet SFP+ Optical Interfaces+2-Port 40GBASE-R Ethernet QSFP+ Optical Interfaces

--
-- 1400 to 1599 reserved for switche RPU logical modules
--
ibevtModulesw-PEX-Common                  OBJECT IDENTIFIER ::= { ibevtModuleSwitchType 1400 } -- The general logical module type for PEX
ibevtModuleSw-CSPEX-1812X                 OBJECT IDENTIFIER ::= { ibevtModuleSwitchType 1401 } -- Service Processing Unit Module(1812X)
ibevtModuleSw-CSPEX-1612X                 OBJECT IDENTIFIER ::= { ibevtModuleSwitchType 1402 } -- Service Processing Unit Module(1612X)
ibevtModuleSw-CSPEX-1512X                 OBJECT IDENTIFIER ::= { ibevtModuleSwitchType 1403 } -- Service Processing Unit Module(1512X)
ibevtModuleSw-NIC-XP20L                   OBJECT IDENTIFIER ::= { ibevtModuleSwitchType 1404 } -- 20-port 10GBASE-R/W Ethernet Optical Interface Card Module(SFP+,LC)(NIC)
ibevtModuleSw-NIC-XP10L                   OBJECT IDENTIFIER ::= { ibevtModuleSwitchType 1405 } -- 10-port 10GBASE-R/W Ethernet Optical Interface Card Module(SFP+,LC)(NIC)
ibevtModuleSw-NIC-CC2L                    OBJECT IDENTIFIER ::= { ibevtModuleSwitchType 1406 } -- 2-port 100G Ethernet Optical Interface Card Module(CFP2,LC)(NIC)
ibevtModuleSw-NIC-CC1L                    OBJECT IDENTIFIER ::= { ibevtModuleSwitchType 1407 } -- 1-port 100G Ethernet Optical Interface Card Module(CFP2,LC)(NIC)
ibevtModuleSw-NIC-XP5L                    OBJECT IDENTIFIER ::= { ibevtModuleSwitchType 1408 } -- 5-port 10GBASE-R/W Ethernet Optical Interface Card Module(SFP+,LC)(NIC)
ibevtModuleSw-NIC-GP20L                   OBJECT IDENTIFIER ::= { ibevtModuleSwitchType 1409 } -- 20-port 1000BASE-X Ethernet Optical Interface Card Module(SFP,LC)(NIC)
ibevtModuleSw-NIC-GT20L                   OBJECT IDENTIFIER ::= { ibevtModuleSwitchType 1410 } -- 20-port 1000BASE-T Ethernet Copper Interface Card Module(RJ45)(NIC)
ibevtModuleSw-MIC-CQ1L                    OBJECT IDENTIFIER ::= { ibevtModuleSwitchType 1411 } -- 1-port 100G Ethernet Optical Interface Card Module(QSFP28,LC)
ibevtModuleSw-MIC-XP10CQ1L                OBJECT IDENTIFIER ::= { ibevtModuleSwitchType 1412 } -- 10-port 10GBASE-R/W Ethernet Optical Interface(SFP+,LC)+1-port 100G Ethernet Optical Interface Card Module(QSFP28,LC)
ibevtModuleSw-CSPEX-1502X                 OBJECT IDENTIFIER ::= { ibevtModuleSwitchType 1413 } -- Service Processing Unit(1502X)
ibevtModuleSw-EPC-CP4RX                   OBJECT IDENTIFIER ::= { ibevtModuleSwitchType 1414 } -- 4-port 100GBASE Ethernet Optical Line Processing Unit(CFP2)
ibevtModuleSw-EPC-CQ4LX                   OBJECT IDENTIFIER ::= { ibevtModuleSwitchType 1415 } -- 4-port 100GBASE Ethernet Optical Line Processing Unit(QSFP28)
ibevtModuleSw-MIC-XP4L1-E                 OBJECT IDENTIFIER ::= { ibevtModuleSwitchType 1416 } -- 4-port 10GBASE-R/W Ethernet Optical Interface Card 1(SFP+,LC)
ibevtModuleSw-MIC-CQ1L-E                  OBJECT IDENTIFIER ::= { ibevtModuleSwitchType 1417 } -- 1-port 100G Ethernet Optical Interface Card 1(QSFP28)
ibevtModuleSw-MIC-XP8L                    OBJECT IDENTIFIER ::= { ibevtModuleSwitchType 1418 } -- 8-port 10GBASE-R/W Ethernet Optical Interface Card (SFP+,LC)
ibevtModuleSw-IM-OAPX                     OBJECT IDENTIFIER ::= { ibevtModuleSwitchType 1419 } -- Universal Open Platform(IM-OAPX)
ibevtModuleSw-MIC-GP20L1                  OBJECT IDENTIFIER ::= { ibevtModuleSwitchType 1420 } -- 20-port 1000BASE-X Ethernet Optical Interface Card(SFP,LC)
ibevtModuleSw-CSPEX-1802X                 OBJECT IDENTIFIER ::= { ibevtModuleSwitchType 1421 } -- Service Processing Unit(1802X)
ibevtModuleSw-MIC-CQ2L                    OBJECT IDENTIFIER ::= { ibevtModuleSwitchType 1422 } -- 2-port 100G Ethernet Optical Interface Card(QSFP28,LC)
ibevtModuleSw-IMMSUX                      OBJECT IDENTIFIER ::= { ibevtModuleSwitchType 1423 } -- Universal Line Processing Unit(IM-MSUX)(China Telecom)
ibevtModuleSw-CSPEX-1104-E                OBJECT IDENTIFIER ::= { ibevtModuleSwitchType 1424 } -- Service Processing Unit(1104E)
ibevtModuleSw-IMSMUX                      OBJECT IDENTIFIER ::= { ibevtModuleSwitchType 1425 } -- Security Monitor Unit(IM-SMUX)
ibevtModuleSw-MIC-XP10L                   OBJECT IDENTIFIER ::= { ibevtModuleSwitchType 1426 } -- 10-port 10GBASE-R/W Ethernet Optical Interface Card(SFP+,LC)
ibevtModuleSw-RX-SRP1P3                   OBJECT IDENTIFIER ::= { ibevtModuleSwitchType 1427 } -- RX8800 Main Processing Unit(1P3)
ibevtModuleSw-RX-SFC-08T                  OBJECT IDENTIFIER ::= { ibevtModuleSwitchType 1428 } -- 1Tbps Fabric Module(08)
ibevtModuleSw-RX-SFC-16T                  OBJECT IDENTIFIER ::= { ibevtModuleSwitchType 1429 } -- 1Tbps Fabric Module(16)
ibevtModuleSw-RX-SPE100                   OBJECT IDENTIFIER ::= { ibevtModuleSwitchType 1430 } -- 100G Service Processing Unit(SPE100)
ibevtModuleSw-RX-SPE200                   OBJECT IDENTIFIER ::= { ibevtModuleSwitchType 1431 } -- 200G Service Processing Unit(SPE200)
ibevtModuleSw-RX-SPE400                   OBJECT IDENTIFIER ::= { ibevtModuleSwitchType 1432 } -- 400G Service Processing Unit(SPE400)
ibevtModuleSw-RX-NIC-GP20L                OBJECT IDENTIFIER ::= { ibevtModuleSwitchType 1433 } -- 20-port 1000BASE-X Ethernet Optical Interface Card(SFP,LC)(RX-NIC,SPE100)
ibevtModuleSw-RX-NIC-XP5L                 OBJECT IDENTIFIER ::= { ibevtModuleSwitchType 1434 } -- 5-port 10GBASE-R/W Ethernet Optical Interface Card(SFP+,LC)(RX-NIC,SPE100)
ibevtModuleSw-RX-NIC-XP10L                OBJECT IDENTIFIER ::= { ibevtModuleSwitchType 1435 } -- 10-port 10GBASE-R/W Ethernet Optical Interface Card(SFP+,LC)(RX-NIC,SPE200)
ibevtModuleSw-RX-NIC-CC1L                 OBJECT IDENTIFIER ::= { ibevtModuleSwitchType 1436 } -- 1-port 100G Ethernet Optical Interface Card(CFP2,LC)(RX-NIC,SPE200)
ibevtModuleSw-RX-NIC-CC2L                 OBJECT IDENTIFIER ::= { ibevtModuleSwitchType 1437 } -- 2-port 100G Ethernet Optical Interface Card(CFP2,LC)(RX-NIC,SPE400)
ibevtModuleSw-RX-NIC-XP20L                OBJECT IDENTIFIER ::= { ibevtModuleSwitchType 1438 } -- 20-port 10GBASE-R/W Ethernet Optical Interface Card(SFP+,LC)(RX-NIC,SPE400)
ibevtModuleSw-CSPC-GE24L-E                OBJECT IDENTIFIER ::= { ibevtModuleSwitchType 1439 } -- 24-port 1000BASE-X Ethernet Combo Interface Line Processing Unit(E Type)
ibevtModuleSw-CSPC-GP24GE8XP2L-E          OBJECT IDENTIFIER ::= { ibevtModuleSwitchType 1440 } -- 24-port 1000BASE-X Ethernet Optical Interface(SFP,LC)+ 8-port 1000BASE-X Ethernet Combo Interface+2-port 10GBASE-R/W Ethernet Optical Interface Line Processing Unit(SFP+,LC)(E Type)
ibevtModuleSw-CSPC-GE16XP4L-E             OBJECT IDENTIFIER ::= { ibevtModuleSwitchType 1441 } -- 16-port 1000BASE-X Ethernet Combo Interface+4-port 10GBASE-R/W Ethernet Optical Interface Line Processing Unit(SFP+,LC)(E Type)
ibevtModuleSw-CSFC-04E                    OBJECT IDENTIFIER ::= { ibevtModuleSwitchType 1442 } -- CR16006-F Fabric Module(E Type)
ibevtModuleSw-SFC-04E                     OBJECT IDENTIFIER ::= { ibevtModuleSwitchType 1443 } -- SR8804-X Fabric Module(E Type)
ibevtModuleSw-IM-MSUX-II                  OBJECT IDENTIFIER ::= { ibevtModuleSwitchType 1444 } -- Universal Line Processing Unit(IM-MSUX-II)
ibevtModuleSw-RX-NIC-YGS4L                OBJECT IDENTIFIER ::= { ibevtModuleSwitchType 1445 } -- 4-port 25G Ethernet Optical Interface Card(SFP28,LC)
ibevtModuleSw-RX-NIC-CQ2LF                OBJECT IDENTIFIER ::= { ibevtModuleSwitchType 1446 } -- 2-port 100G Flexible Ethernet Optical Interface Card(QSFP28,LC)
ibevtModuleSw-RX-SRP1Q3                   OBJECT IDENTIFIER ::= { ibevtModuleSwitchType 1447 } -- RX8800 Main Processing Unit(1Q3)
ibevtModuleSw-RX-SFC-08E                  OBJECT IDENTIFIER ::= { ibevtModuleSwitchType 1448 } -- 400Gbps Fabric Module(08)
ibevtModuleSw-RX-SFC-16E                  OBJECT IDENTIFIER ::= { ibevtModuleSwitchType 1449 } -- 400Gbps Fabric Module(16)
ibevtModuleSw-RX-NIC-LGQ2L                OBJECT IDENTIFIER ::= { ibevtModuleSwitchType 1450 } -- 2-port 50G Ethernet Optical Interface Card(QSFP28,LC)(RX-NIC)

ibevtModuleSw-RX-NIC-CQ1LF                OBJECT IDENTIFIER ::= { ibevtModuleSwitchType 1452 } -- 1-port 100G Flexible Ethernet Optical Interface Card(QSFP28,LC)(RX-NIC)
ibevtModuleSw-IM-SFMX                     OBJECT IDENTIFIER ::= { ibevtModuleSwitchType 1453 } -- Network Data Encryption Service Processing Unit(IM-SFMX)
ibevtModuleSw-MIC-SM                      OBJECT IDENTIFIER ::= { ibevtModuleSwitchType 1454 } -- Network Data Encryption Interface Card(MIC-SM)
ibevtModuleSw-RX-NIC-CQ1L                 OBJECT IDENTIFIER ::= { ibevtModuleSwitchType 1455 } -- 1-port 100G Ethernet Optical Interface Card(QSFP28,LC)(RX-NIC)
ibevtModuleSw-RX-NIC-CQ2L                 OBJECT IDENTIFIER ::= { ibevtModuleSwitchType 1456 } -- 2-port 100G Ethernet Optical Interface Card(QSFP28,LC)(RX-NIC)
ibevtModuleSw-NIC-GP24L                   OBJECT IDENTIFIER ::= { ibevtModuleSwitchType 1457 } -- 24-port 1000BASE-X Ethernet Optical Interface Card(SFP,LC)(NIC)
ibevtModuleSw-NIC-CQ1L                    OBJECT IDENTIFIER ::= { ibevtModuleSwitchType 1458 } -- 1-port 100G Ethernet Optical Interface Card(QSFP28,LC)(NIC)
ibevtModuleSw-NIC-CQ2L                    OBJECT IDENTIFIER ::= { ibevtModuleSwitchType 1459 } -- 2-port 100G Ethernet Optical Interface Card(QSFP28,LC)(NIC)
-- 1600 to 1799 reserved for secondary switches part III
--
ibevtModuleSw-LSUM2GP44TSSE9              OBJECT IDENTIFIER ::= { ibevtModuleSwitchType 1600 } -- 44-Port GE Optical Interface(SFP,LC)+4-Port 10GE Optical Interface Board(SFP+,LC)(SE)
ibevtModuleSw-LSUM2GP24TSSE9              OBJECT IDENTIFIER ::= { ibevtModuleSwitchType 1601 } -- 24-Port GE Optical Interface(SFP,LC)+4-Port 10GE Optical Interface Board(SFP+,LC)(SE)
ibevtModuleSw-LSUM2GT24TSSE9              OBJECT IDENTIFIER ::= { ibevtModuleSwitchType 1602 } -- 24-Port 1000Base-T Gigabit Ethernet Interface Board(RJ45)+4-Port 10GE Optical Interface Board(SFP+,LC)(SE)
ibevtModuleSw-LSUM2GT48SE9                OBJECT IDENTIFIER ::= { ibevtModuleSwitchType 1603 } -- 48-Port 1000Base-T Gigabit Ethernet Interface Board(RJ45)(SE)
ibevtModuleSw-LSUM1SUPD0                  OBJECT IDENTIFIER ::= { ibevtModuleSwitchType 1604 } -- Supervisor Engine Board
ibevtModuleSw-LSUM1SUPD9                  OBJECT IDENTIFIER ::= { ibevtModuleSwitchType 1605 } -- Supervisor Engine Board
ibevtModuleSw-LSXM1TGT48FX0               OBJECT IDENTIFIER ::= { ibevtModuleSwitchType 1606 } -- 48-Port 10GBASE-T Ethernet Electrical Interface Module(RJ45)(FX)
ibevtModuleSw-LSXM1TGS48FX0               OBJECT IDENTIFIER ::= { ibevtModuleSwitchType 1607 } -- 48-Port 10GBASE-T Ethernet Electrical Interface Module(RJ45)(FX)
ibevtModuleSw-LSXM1TGS48FE0               OBJECT IDENTIFIER ::= { ibevtModuleSwitchType 1608 } -- 48-Port 10GBASE Ethernet Optical Interface Module(SFP+,LC)(FE)
ibevtModuleSw-LSXM1QGS36FX0               OBJECT IDENTIFIER ::= { ibevtModuleSwitchType 1609 } -- 36-Port 40GBASE Ethernet Optical Interface Module(QSFP+)(FX)
ibevtModuleSw-LSXM1QGS24FX0               OBJECT IDENTIFIER ::= { ibevtModuleSwitchType 1610 } -- 24-Port 40GBASE Ethernet Optical Interface Module(QSFP+)(FX)
ibevtModuleSw-LSXM1QGS24FE0               OBJECT IDENTIFIER ::= { ibevtModuleSwitchType 1611 } -- 24-Port 40GBASE Ethernet Optical Interface Module(QSFP+)(FE)
ibevtModuleSw-LSXM1CGX8FX0                OBJECT IDENTIFIER ::= { ibevtModuleSwitchType 1612 } -- 8-Port 100GBASE Ethernet Optical Interface Module(CXP)(FX)
ibevtModuleSw-LSXM1CGP12FX0               OBJECT IDENTIFIER ::= { ibevtModuleSwitchType 1613 } -- 12-Port 100GBASE Ethernet Optical Interface Module(CFP2)(FX)
ibevtModuleSw-LSXM1SUPB0                  OBJECT IDENTIFIER ::= { ibevtModuleSwitchType 1614 } -- Supervisor Engine Module
ibevtModuleSw-LSXM1SFF16C0                OBJECT IDENTIFIER ::= { ibevtModuleSwitchType 1615 } -- Switching Fabric Module,Type F(Class C)
ibevtModuleSw-LSXM1SFF16A0                OBJECT IDENTIFIER ::= { ibevtModuleSwitchType 1616 } -- Switching Fabric Module,Type F(Class A)
ibevtModuleSw-LSXM1SFF08B0                OBJECT IDENTIFIER ::= { ibevtModuleSwitchType 1617 } -- Switching Fabric Module,Type F(Class B)
ibevtModuleSw-LSQM6GV48SC0                OBJECT IDENTIFIER ::= { ibevtModuleSwitchType 1618 } -- 48-Port 10/100/1000BASE-T Ethernet Interface Module(RJ45),Upgradeable to PoE
ibevtModuleSw-LSXM1SUP04B1                OBJECT IDENTIFIER ::= { ibevtModuleSwitchType 1619 } -- Supervisor Engine Module
ibevtModuleSw-LSXM1SFF04B1                OBJECT IDENTIFIER ::= { ibevtModuleSwitchType 1620 } -- Switching Fabric Module,Type F(Class B)
ibevtModuleSw-LSXM1SUP04B0                OBJECT IDENTIFIER ::= { ibevtModuleSwitchType 1621 } -- Supervisor Engine Module
ibevtModuleSw-LSXM1SFF04B0                OBJECT IDENTIFIER ::= { ibevtModuleSwitchType 1622 } -- Switching Fabric Module,Type F(Class B)
ibevtModuleSw-LSU1ADECEA0                 OBJECT IDENTIFIER ::= { ibevtModuleSwitchType 1623 } -- Application Dilevery Engine Module,Domestic&Overseas Version
ibevtModuleSw-LSU1NSCEA0                  OBJECT IDENTIFIER ::= { ibevtModuleSwitchType 1624 } -- NetStream Service Board
ibevtModuleSw-LSU3FWCEA0                  OBJECT IDENTIFIER ::= { ibevtModuleSwitchType 1625 } -- Firewall Service Board
ibevtModuleSw-LSXM1MPU06B3                OBJECT IDENTIFIER ::= { ibevtModuleSwitchType 1626 } -- Supervisor Engine Board
ibevtModuleSw-LSXM1MPU10C3                OBJECT IDENTIFIER ::= { ibevtModuleSwitchType 1627 } -- Supervisor Engine Board
ibevtModuleSw-LSXM1SUPD3                  OBJECT IDENTIFIER ::= { ibevtModuleSwitchType 1628 } -- Supervisor Engine Board
ibevtModuleSw-LSXM1FAB06C3                OBJECT IDENTIFIER ::= { ibevtModuleSwitchType 1629 } -- Switching Fabric Module
ibevtModuleSw-LSXM1FAB10C3                OBJECT IDENTIFIER ::= { ibevtModuleSwitchType 1630 } -- Switching Fabric Module
ibevtModuleSw-LSXM1FAB12D3                OBJECT IDENTIFIER ::= { ibevtModuleSwitchType 1631 } -- Switching Fabric Module
ibevtModuleSw-LSXM1FAB04D3                OBJECT IDENTIFIER ::= { ibevtModuleSwitchType 1632 } -- Switching Fabric Module
ibevtModuleSw-LSXM1FAB08D3                OBJECT IDENTIFIER ::= { ibevtModuleSwitchType 1633 } -- Switching Fabric Module
ibevtModuleSw-LSXM1GP44TSSE3              OBJECT IDENTIFIER ::= { ibevtModuleSwitchType 1634 } -- 44-Port GE Optical Interface(SFP,LC)+4-Port 10GE Optical Interface Board(SFP+,LC)(SE)
ibevtModuleSw-LSXM1GP24TSSE3              OBJECT IDENTIFIER ::= { ibevtModuleSwitchType 1635 } -- 24-Port GE Optical Interface(SFP,LC)+4-Port 10GE Optical Interface Board(SFP+,LC)(SE)
ibevtModuleSw-LSXM1GT24PTSSE3             OBJECT IDENTIFIER ::= { ibevtModuleSwitchType 1636 } -- 24-Port 1000Base-T Gigabit Ethernet Interface Board(RJ45)+20-Port GE Optical Interface(SFP,LC)+4-Port 10GE Optical Interface Board(SFP+,LC)(SE)
ibevtModuleSw-LSXM1GT48SE3                OBJECT IDENTIFIER ::= { ibevtModuleSwitchType 1637 } -- 48-Port 1000Base-T Gigabit Ethernet Interface Board(RJ45)(SE)
ibevtModuleSw-LSXM1TGS24EC3               OBJECT IDENTIFIER ::= { ibevtModuleSwitchType 1638 } -- 24-Port 10GBASE-R Ethernet SFP+ Optical Interface Board(EC)
ibevtModuleSw-LSXM1CGC2EC3                OBJECT IDENTIFIER ::= { ibevtModuleSwitchType 1639 } -- 2-Port 100GBASE-R Ethernet CFP Optical Interface Board(EC)
ibevtModuleSw-LSXM1TGT24SF3               OBJECT IDENTIFIER ::= { ibevtModuleSwitchType 1640 } -- 24-Port 10GBASE-T Ethernet Electrical Interface Board(RJ45)(SF)
ibevtModuleSw-LSXM1TGS16SF3               OBJECT IDENTIFIER ::= { ibevtModuleSwitchType 1641 } -- 16-Port 10GE Optical Interface Board(SFP+,LC)(SF)
ibevtModuleSw-LSXM1QGS12SG3               OBJECT IDENTIFIER ::= { ibevtModuleSwitchType 1642 } -- 12-Port 40GBASE-R Ethernet QSFP+ Optical Interface Board(SG)
ibevtModuleSw-LSXM1TGS48SG3               OBJECT IDENTIFIER ::= { ibevtModuleSwitchType 1643 } -- 48-Port 10GBASE-R Ethernet SFP+ Optical Interface Board(SG)
ibevtModuleSw-LSQM1FAB04B3                OBJECT IDENTIFIER ::= { ibevtModuleSwitchType 1644 } -- Switching Fabric Module
ibevtModuleSw-LSQM1FAB08B3                OBJECT IDENTIFIER ::= { ibevtModuleSwitchType 1645 } -- Switching Fabric Module
ibevtModuleSw-LSQM1FAB12B3                OBJECT IDENTIFIER ::= { ibevtModuleSwitchType 1646 } -- Switching Fabric Module
ibevtModuleSw-LSXM1SFF08A0                OBJECT IDENTIFIER ::= { ibevtModuleSwitchType 1647 } -- Switching Fabric Board
ibevtModuleSw-LSXM1SFF08A1                OBJECT IDENTIFIER ::= { ibevtModuleSwitchType 1648 } -- Switching Fabric Board
ibevtModuleSw-LSXM1FWDF1                  OBJECT IDENTIFIER ::= { ibevtModuleSwitchType 1649 } -- FW IV Next Generation Firewall Module
ibevtModuleSw-LSQM1PT8TSSC0               OBJECT IDENTIFIER ::= { ibevtModuleSwitchType 1650 } -- 8-Port 1G EPON OLT Optical Interface(SFP,SC)+2-Port 10GE Optical Interface Board(SFP+,LC)(SC)
ibevtModuleSw-LSQM1PT24TSSC0              OBJECT IDENTIFIER ::= { ibevtModuleSwitchType 1651 } -- 24-Port 1G EPON OLT Optical Interface(SFP,SC)+2-Port 10GE Optical Interface Board(SFP+,LC)(SC)
ibevtModuleSw-LSQM1TGS12EC0               OBJECT IDENTIFIER ::= { ibevtModuleSwitchType 1652 } -- 12-Port 10GBASE-R Ethernet SFP+ Optical Interface Board(EC)
ibevtModuleSw-LSX1M1CGQ32TB1              OBJECT IDENTIFIER ::= { ibevtModuleSwitchType 1653 } -- 32-Port 100GBASE Ethernet Optical Interface Board(QSFP28),Monolithic,LF
ibevtModuleSw-LSX1M1CGQ48TB1              OBJECT IDENTIFIER ::= { ibevtModuleSwitchType 1654 } -- 48-Port 100GBASE Ethernet Optical Interface Board(QSFP28),Monolithic
ibevtModuleSw-LSXM1QGS48TB1               OBJECT IDENTIFIER ::= { ibevtModuleSwitchType 1655 } -- 48-Port 40GBASE Ethernet Optical Interface Board(QSFP+),Monolithic
ibevtModuleSw-LSXM1SRT08E1                OBJECT IDENTIFIER ::= { ibevtModuleSwitchType 1656 } -- Switch Fabric Board
ibevtModuleSw-LSXM1SRT16E1                OBJECT IDENTIFIER ::= { ibevtModuleSwitchType 1657 } -- Switch Fabric Board
ibevtModuleSw-LSXM1SRT02E1                OBJECT IDENTIFIER ::= { ibevtModuleSwitchType 1658 } -- Switch Fabric Board
ibevtModuleSw-LSXM1SUP02B1                OBJECT IDENTIFIER ::= { ibevtModuleSwitchType 1659 } -- Supervisor Engine Module
ibevtModuleSw-LSUM1SUPC0                  OBJECT IDENTIFIER ::= { ibevtModuleSwitchType 1660 } -- Supervisor Engine Board
ibevtModuleSw-LSUM1SUPC3                  OBJECT IDENTIFIER ::= { ibevtModuleSwitchType 1661 } -- Supervisor Engine Board
ibevtModuleSw-LSXM1SUPC3                  OBJECT IDENTIFIER ::= { ibevtModuleSwitchType 1662 } -- Supervisor Engine Board
ibevtModuleSw-LSQM1GP44TSSE0              OBJECT IDENTIFIER ::= { ibevtModuleSwitchType 1663 } -- 44-Port GE Optical Interface(SFP,LC)+4-Port 10GE Optical Interface Board(SFP+,LC)(SC)
ibevtModuleSw-LSQM1GP24TSSE0              OBJECT IDENTIFIER ::= { ibevtModuleSwitchType 1664 } -- 24-Port GE Optical Interface(SFP,LC)+4-Port 10GE Optical Interface Board(SFP+,LC)(SC)
ibevtModuleSw-LSQM1GT48SE0                OBJECT IDENTIFIER ::= { ibevtModuleSwitchType 1665 } -- 48-Port 1000Base-T Gigabit Ethernet Interface Board(RJ45)(SC)
ibevtModuleSw-LSQM1GV48SE0                OBJECT IDENTIFIER ::= { ibevtModuleSwitchType 1666 } -- 48-Port 1000Base-T Gigabit Ethernet Interface Board(RJ45)(SC)-POE
ibevtModuleSw-LSXM1QGS12FX0               OBJECT IDENTIFIER ::= { ibevtModuleSwitchType 1667 } -- 12-Port 40GBASE Ethernet Optical Interface Module(QSFP+)(FX)
ibevtModuleSw-LSXM3QGS24FE1               OBJECT IDENTIFIER ::= { ibevtModuleSwitchType 1668 } -- 24-Port 40GBASE Ethernet Optical Interface Module(QSFP+)(FE)
ibevtModuleSw-LSXM3QGS24FX1               OBJECT IDENTIFIER ::= { ibevtModuleSwitchType 1669 } -- 24-Port 40GBASE Ethernet Optical Interface Module(QSFP+)(FX)
ibevtModuleSw-LSXM3QGS36FX1               OBJECT IDENTIFIER ::= { ibevtModuleSwitchType 1670 } -- 36-Port 40GBASE Ethernet Optical Interface Module(QSFP+)(FX)
ibevtModuleSw-LSXM3TGS48FE1               OBJECT IDENTIFIER ::= { ibevtModuleSwitchType 1671 } -- 48-Port 10GBASE Ethernet Optical Interface Module(SFP+,LC)(FX)
ibevtModuleSw-LSXM3TGS48FX1               OBJECT IDENTIFIER ::= { ibevtModuleSwitchType 1672 } -- 48-Port 10GBASE Ethernet Optical Interface Module(SFP+,LC)(FX)
ibevtModuleSw-LSXM2TGS48FX1               OBJECT IDENTIFIER ::= { ibevtModuleSwitchType 1673 } -- 48-Port 10GBASE Ethernet Optical Interface Module(SFP+,LC)(FX)
ibevtModuleSw-LSQM1MPU06B0                OBJECT IDENTIFIER ::= { ibevtModuleSwitchType 1674 } -- Supervisor Engine Board
ibevtModuleSw-LSQM1MPU10C0                OBJECT IDENTIFIER ::= { ibevtModuleSwitchType 1675 } -- Supervisor Engine Board
ibevtModuleSw-LSQM1FAB06C0                OBJECT IDENTIFIER ::= { ibevtModuleSwitchType 1676 } -- Switching Fabric Module
ibevtModuleSw-LSQM1FAB10C0                OBJECT IDENTIFIER ::= { ibevtModuleSwitchType 1677 } -- Switching Fabric Module
ibevtModuleSw-LSQM1QGS12SG0               OBJECT IDENTIFIER ::= { ibevtModuleSwitchType 1678 } -- 12-Port 40GBASE-R Ethernet QSFP+ Optical Interface Board(SG)
ibevtModuleSw-LSQM1TGS48SG0               OBJECT IDENTIFIER ::= { ibevtModuleSwitchType 1679 } -- 48-Port 10GBASE-R Ethernet SFP+ Optical Interface Board(SG)
ibevtModuleSw-LSQM1TGT24SF0               OBJECT IDENTIFIER ::= { ibevtModuleSwitchType 1680 } -- 24-Port 10GBASE-T Ethernet Electrical Interface Board(RJ45)(SF)
ibevtModuleSw-LSQM1QGS8A0                 OBJECT IDENTIFIER ::= { ibevtModuleSwitchType 1681 } -- 8-Port QSFP+ Module
ibevtModuleSw-LSQM1TGS24QSM0              OBJECT IDENTIFIER ::= { ibevtModuleSwitchType 1682 } -- 24-Port SFP+ and 2-Port QSFP+ Module
ibevtModuleSw-LSQM1TGT24QSM0              OBJECT IDENTIFIER ::= { ibevtModuleSwitchType 1683 } -- 24-Port 10G BASE-T and 2-Port QSFP+ Module
ibevtModuleSw-LSQM1TGS24QSA0              OBJECT IDENTIFIER ::= { ibevtModuleSwitchType 1684 } -- 24-Port SFP+ and 2-Port QSFP+ Module
ibevtModuleSw-LSUM1FWCEAB0                OBJECT IDENTIFIER ::= { ibevtModuleSwitchType 1685 } -- Firewall Board
ibevtModuleSw-LSQM2GP24TSSA0              OBJECT IDENTIFIER ::= { ibevtModuleSwitchType 1686 } -- 24-Port GE Optical Interface(SFP,LC)+4-Port 10GE Optical Interface Board(SFP+,LC)(SA)
ibevtModuleSw-LSQM2GT48SA0                OBJECT IDENTIFIER ::= { ibevtModuleSwitchType 1687 } -- 48-Port 1000Base-T Gigabit Ethernet Interface Board(RJ45)(SA)
ibevtModuleSw-LSQM2GP48SA0                OBJECT IDENTIFIER ::= { ibevtModuleSwitchType 1688 } -- 48-Port 1000BASE-X Ethernet Optical Interface Board(SFP,LC)(SA)
ibevtModuleSw-LSQM2GP24TSSA3              OBJECT IDENTIFIER ::= { ibevtModuleSwitchType 1689 } -- 24-Port GE Optical Interface(SFP,LC)+4-Port 10GE Optical Interface Board(SFP+,LC)(SA)
ibevtModuleSw-LSQM2GT48SA3                OBJECT IDENTIFIER ::= { ibevtModuleSwitchType 1690 } -- 48-Port 1000Base-T Gigabit Ethernet Interface Board(RJ45)(SA)
ibevtModuleSw-LSQM2GP48SA3                OBJECT IDENTIFIER ::= { ibevtModuleSwitchType 1691 } -- 48-Port 1000BASE-X Ethernet Optical Interface Board(SFP,LC)(SA)
ibevtModuleSw-LSUM2GP24TSSA0              OBJECT IDENTIFIER ::= { ibevtModuleSwitchType 1692 } -- 24-Port GE Optical Interface(SFP,LC)+4-Port 10GE Optical Interface Board(SFP+,LC)(SA)
ibevtModuleSw-LSUM2GT48SA0                OBJECT IDENTIFIER ::= { ibevtModuleSwitchType 1693 } -- 48-Port 1000Base-T Gigabit Ethernet Interface Board(RJ45)(SA)
ibevtModuleSw-LSUM2GP48SA0                OBJECT IDENTIFIER ::= { ibevtModuleSwitchType 1694 } -- 48-Port 1000BASE-X Ethernet Optical Interface Board(SFP,LC)(SA)
ibevtModuleSw-LSXM1SUPT1                  OBJECT IDENTIFIER ::= { ibevtModuleSwitchType 1695 } -- Supervisor Engine Module
ibevtModuleSw-LSXM1SUP02T1                OBJECT IDENTIFIER ::= { ibevtModuleSwitchType 1696 } -- Supervisor Engine Module
ibevtModuleSw-LSXM1SFF16B0                OBJECT IDENTIFIER ::= { ibevtModuleSwitchType 1697 } -- Switch Fabric Board
ibevtModuleSw-LSXM4TGS48FX1               OBJECT IDENTIFIER ::= { ibevtModuleSwitchType 1698 } -- 48-Port 10GBASE Ethernet Optical Interface Module(SFP+,LC)(FX)
ibevtModuleSw-LSXM4QGS24FX1               OBJECT IDENTIFIER ::= { ibevtModuleSwitchType 1699 } -- 24-Port 40GBASE Ethernet Optical Interface Module(QSFP+)(FX)
ibevtModuleSw-LSXM1TGS48FD1               OBJECT IDENTIFIER ::= { ibevtModuleSwitchType 1700 } -- 48-Port 10GBASE Ethernet Optical Interface Module(SFP+,LC)(FD)
ibevtModuleSw-LSXM1QGS24FD1               OBJECT IDENTIFIER ::= { ibevtModuleSwitchType 1701 } -- 24-Port 40GBASE Ethernet Optical Interface Module(QSFP+)(FD)
ibevtModuleSw-LSXM2QGS24FX1               OBJECT IDENTIFIER ::= { ibevtModuleSwitchType 1702 } -- 24-Port 40GBASE Ethernet Optical Interface Module(QSFP+)(FX)
ibevtModuleSw-LSXM1TGS48FD0               OBJECT IDENTIFIER ::= { ibevtModuleSwitchType 1703 } -- 48-Port 10GBASE Ethernet Optical Interface Module(SFP+,LC)
ibevtModuleSw-LSXM1QGS24FD0               OBJECT IDENTIFIER ::= { ibevtModuleSwitchType 1704 } -- 24-Port 40GBASE Ethernet Optical Interface Module(QSFP+)(FD)
ibevtModuleSw-LSXM2TGS48FX0               OBJECT IDENTIFIER ::= { ibevtModuleSwitchType 1705 } -- 48-Port 10GBASE Ethernet Optical Interface Module(SFP+,LC)(FX)
ibevtModuleSw-LSXM2QGS24FX0               OBJECT IDENTIFIER ::= { ibevtModuleSwitchType 1706 } -- 24-Port 40GBASE Ethernet Optical Interface Module(QSFP+)(FX)
ibevtModuleSw-LSXM4TGS48FX0               OBJECT IDENTIFIER ::= { ibevtModuleSwitchType 1707 } -- 48-Port 10GBASE Ethernet Optical Interface Module(SFP+,LC)(FX)
ibevtModuleSw-LSXM4QGS24FX0               OBJECT IDENTIFIER ::= { ibevtModuleSwitchType 1708 } -- 24-Port 40GBASE Ethernet Optical Interface Module(QSFP+)(FX)
ibevtModuleSw-LSXM1TGW48FX1               OBJECT IDENTIFIER ::= { ibevtModuleSwitchType 1709 } -- 48-Port 10GBASE Ethernet WAN Optical Interface Module(SFP+,LC)(FX)
ibevtModuleSw-LSUM1MPU10A0                OBJECT IDENTIFIER ::= { ibevtModuleSwitchType 1710 } -- Supervisor Engine Board
ibevtModuleSw-LSUM1FAB10A0                OBJECT IDENTIFIER ::= { ibevtModuleSwitchType 1711 } -- Switching Fabric Module
ibevtModuleSw-LSUM2TGS32QSSG0             OBJECT IDENTIFIER ::= { ibevtModuleSwitchType 1712 } -- 32-Port 10GBASE-R Ethernet Optical Interface(SFP+,LC)+4-Port 40GBASE-R Ethernet Optical Interface Board(QSFP+,LC)(SG)
ibevtModuleSw-LSUM2QGS12SG0               OBJECT IDENTIFIER ::= { ibevtModuleSwitchType 1713 } -- 12-Port 40GBASE-R Ethernet QSFP+ Optical Interface Board(SG)
ibevtModuleSw-LSUM2TGS48SG0               OBJECT IDENTIFIER ::= { ibevtModuleSwitchType 1714 } -- 48-Port 10GBASE-R Ethernet SFP+ Optical Interface Board(SG)
ibevtModuleSw-LSXM2QGS12SG3               OBJECT IDENTIFIER ::= { ibevtModuleSwitchType 1715 } -- 12-Port 40GBASE-R Ethernet QSFP+ Optical Interface Board(SG)
ibevtModuleSw-LSXM2TGS48SG3               OBJECT IDENTIFIER ::= { ibevtModuleSwitchType 1716 } -- 48-Port 10GBASE-R Ethernet SFP+ Optical Interface Board(SG)
ibevtModuleSw-LSUM1FWDEC0                 OBJECT IDENTIFIER ::= { ibevtModuleSwitchType 1717 } -- Firewall Service Board
ibevtModuleSw-LSQM1FWDSC0                 OBJECT IDENTIFIER ::= { ibevtModuleSwitchType 1718 } -- Firewall Service Board
ibevtModuleSw-LSQM1TGS48RSG0              OBJECT IDENTIFIER ::= { ibevtModuleSwitchType 1719 } -- 48-Port 10GBASE-R Ethernet SFP+ Optical Interface Board(SG)
ibevtModuleSw-LSQM2TGS48XSG0              OBJECT IDENTIFIER ::= { ibevtModuleSwitchType 1720 } -- 48-Port 10GBASE-R Ethernet SFP+ Optical Interface Board(SG)
ibevtModuleSw-LSQM2QGS12XSG0              OBJECT IDENTIFIER ::= { ibevtModuleSwitchType 1721 } -- 12-Port 40GBASE-R Ethernet QSFP+ Optical Interface Board(SG)
ibevtModuleSw-LSQM3GP44TSSC0              OBJECT IDENTIFIER ::= { ibevtModuleSwitchType 1722 } -- 44-Port GE Optical Interface(SFP,LC)+4-Port 10GE Optical Interface Board(SFP+,LC)(SC)
ibevtModuleSw-LSXM1CGQ36HB1               OBJECT IDENTIFIER ::= { ibevtModuleSwitchType 1723 } -- 36-Port 100GBASE Ethernet Optical Interface Module(QSFP28)(HB)
ibevtModuleSw-LSXM1CGQ36HC1               OBJECT IDENTIFIER ::= { ibevtModuleSwitchType 1724 } -- 36-Port 100GBASE Ethernet Optical Interface Module(QSFP28)(HC)
ibevtModuleSw-LSXM1CGQ18QGHB1             OBJECT IDENTIFIER ::= { ibevtModuleSwitchType 1725 } -- 18-Port 100GBASE (QSFP28) + 18-Port 40GBASE Ethernet Optical Interface Module (QSFP+)(HB)
ibevtModuleSw-LSXM1CGQ18QGHC1             OBJECT IDENTIFIER ::= { ibevtModuleSwitchType 1726 } -- 18-Port 100GBASE (QSFP28) + 18-Port 40GBASE Ethernet Optical Interface Module (QSFP+)(HC)
ibevtModuleSw-LSXM1QGS48HB1               OBJECT IDENTIFIER ::= { ibevtModuleSwitchType 1727 } -- 48-Port 40GBASE Ethernet Optical Interface Module(QSFP+)(HB)
ibevtModuleSw-LSXM1QGS48HC1               OBJECT IDENTIFIER ::= { ibevtModuleSwitchType 1728 } -- 48-Port 40GBASE Ethernet Optical Interface Module(QSFP+)(HC)
ibevtModuleSw-LSXM1TGS48C2HB1             OBJECT IDENTIFIER ::= { ibevtModuleSwitchType 1729 } -- 48-Port 10G BASE Ethernet Optical Interface(SFP+,LC)+2-Port 100GBASE Ethernet Optical Interface Module(QSFP28)(HB)
ibevtModuleSw-LSXM1SFH04D1                OBJECT IDENTIFIER ::= { ibevtModuleSwitchType 1730 } -- Switch Fabric Board,Type H(Class D)
ibevtModuleSw-LSXM1SFH08D1                OBJECT IDENTIFIER ::= { ibevtModuleSwitchType 1731 } -- Switch Fabric Board For S12508X-AF,Type D(F2)
ibevtModuleSw-LSXM1SFH12D1                OBJECT IDENTIFIER ::= { ibevtModuleSwitchType 1732 } -- Fabric Module,Type H(Class D)
ibevtModuleSw-LSXM1SFH16C1                OBJECT IDENTIFIER ::= { ibevtModuleSwitchType 1733 } -- Switch Fabric Board,Type H(Class C)
ibevtModuleSw-LSXM1GP48FD0                OBJECT IDENTIFIER ::= { ibevtModuleSwitchType 1737 } -- 48-Port 1000BASE-X Gigabit Ethernet Optical Interface Module(SFP,LC)(FD)
ibevtModuleSw-LSXM1GP48FD1                OBJECT IDENTIFIER ::= { ibevtModuleSwitchType 1738 } -- 48-Port 1000BASE-X Gigabit Ethernet Optical Interface Module(SFP,LC)(FD)
ibevtModuleSw-LSXM1GT48FD0                OBJECT IDENTIFIER ::= { ibevtModuleSwitchType 1739 } -- 48-Port 1000Base-T Gigabit Ethernet Interface Module(RJ45)(FD)
ibevtModuleSw-LSXM1GT48FD1                OBJECT IDENTIFIER ::= { ibevtModuleSwitchType 1740 } -- 48-Port 1000Base-T Gigabit Ethernet Interface Module(RJ45)(FD)
ibevtModuleSw-LSXM1FAB10B0                OBJECT IDENTIFIER ::= { ibevtModuleSwitchType 1741 } -- Switching Fabric Module
ibevtModuleSw-LSUM1MPU10A3                OBJECT IDENTIFIER ::= { ibevtModuleSwitchType 1742 } -- Supervisor Engine Board
ibevtModuleSw-LSUM1FAB10A3                OBJECT IDENTIFIER ::= { ibevtModuleSwitchType 1743 } -- Switching Fabric Module
ibevtModuleSw-LSQM1MPU10A0                OBJECT IDENTIFIER ::= { ibevtModuleSwitchType 1744 } -- Supervisor Engine Board
ibevtModuleSw-LSQM1FAB10A0                OBJECT IDENTIFIER ::= { ibevtModuleSwitchType 1745 } -- Switching Fabric Module
ibevtModuleSw-LSQM2TGS32QSXSG0            OBJECT IDENTIFIER ::= { ibevtModuleSwitchType 1746 } -- 32-Port 10GBASE-R Ethernet Optical Interface(SFP+,LC)+4-Port 40GBASE-R Ethernet Optical Interface Board(QSFP+,LC)(SG)
ibevtModuleSw-LSQM1TGS48RSG3              OBJECT IDENTIFIER ::= { ibevtModuleSwitchType 1747 } -- 48-Port 10GBASE-R Ethernet SFP+ Optical Interface Board(SG)
ibevtModuleSw-LSXM2TGS32QSSG3             OBJECT IDENTIFIER ::= { ibevtModuleSwitchType 1748 } -- 32-Port 10GBASE-R Ethernet Optical Interface(SFP+,LC)+4-Port 40GBASE-R Ethernet Optical Interface Board(QSFP+,LC)(SG)
ibevtModuleSw-LSUM1NSDEC0                 OBJECT IDENTIFIER ::= { ibevtModuleSwitchType 1749 } -- NetStream Service Board
ibevtModuleSw-LSQM1NSDSC0                 OBJECT IDENTIFIER ::= { ibevtModuleSwitchType 1750 } -- NetStream Service Board
ibevtModuleSw-LSQM1QGS4SC0                OBJECT IDENTIFIER ::= { ibevtModuleSwitchType 1751 } -- 4-Port 40G BASE Ethernet Optical Interface Board(QSFP+,MPO)(SC)
ibevtModuleSw-LLSQM2MPUD3                 OBJECT IDENTIFIER ::= { ibevtModuleSwitchType 1752 } -- Supervisor Engine Board
ibevtModuleSw-LLSQM3MPUB3                 OBJECT IDENTIFIER ::= { ibevtModuleSwitchType 1753 } -- Supervisor Engine Board
ibevtModuleSw-LSQM3MPUB4                  OBJECT IDENTIFIER ::= { ibevtModuleSwitchType 1754 } -- Supervisor Engine Board
ibevtModuleSw-LSQM2MPUDS0                 OBJECT IDENTIFIER ::= { ibevtModuleSwitchType 1755 } -- Supervisor Engine Board
ibevtModuleSw-LSQM4GV48SA0                OBJECT IDENTIFIER ::= { ibevtModuleSwitchType 1756 } -- 48-Port 1000Base-T Gigabit Ethernet Interface Board(RJ45)(SA)-POE
ibevtModuleSw-LSQM1WCMX20                 OBJECT IDENTIFIER ::= { ibevtModuleSwitchType 1757 } -- Access Controller Service Board
ibevtModuleSw-LSQM1WCMX40                 OBJECT IDENTIFIER ::= { ibevtModuleSwitchType 1758 } -- Access Controller Service Board
ibevtModuleSw-LSUM1WCMX20RT               OBJECT IDENTIFIER ::= { ibevtModuleSwitchType 1759 } -- Access Controller Service Board
ibevtModuleSw-LSUM1WCMX40RT               OBJECT IDENTIFIER ::= { ibevtModuleSwitchType 1760 } -- Access Controller Service Board
ibevtModuleSw-LSXM1CGQ18QGHB0             OBJECT IDENTIFIER ::= { ibevtModuleSwitchType 1761 } -- 18-PORT 100GBASE Ethernet Optical Interface (QSFP28)/36-PORT 40GBASE Ethernet Optical Interface Module(QSFP+)(HB)
ibevtModuleSw-LSXM1SFH08C0                OBJECT IDENTIFIER ::= { ibevtModuleSwitchType 1762 } -- Fabric Module,Type H(Class C)
ibevtModuleSw-LSXM1SFH08C1                OBJECT IDENTIFIER ::= { ibevtModuleSwitchType 1763 } -- Fabric Module,Type H(Class C)
ibevtModuleSw-LSXM2SFH16C0                OBJECT IDENTIFIER ::= { ibevtModuleSwitchType 1764 } -- Fabric Module,Type H(Class C)
ibevtModuleSw-LSXM2SFH16C1                OBJECT IDENTIFIER ::= { ibevtModuleSwitchType 1765 } -- Fabric Module,Type H(Class C)
ibevtModuleSw-LSXM1NSDF1                  OBJECT IDENTIFIER ::= { ibevtModuleSwitchType 1766 } -- SecBlade IV NetStream Module
ibevtModuleSw-LSUM2TGS48SG3               OBJECT IDENTIFIER ::= { ibevtModuleSwitchType 1767 } -- 48-Port 10GBASE-R Ethernet SFP+ Optical Interface Board(SG)
ibevtModuleSw-DS-3E7602-MPU               OBJECT IDENTIFIER ::= { ibevtModuleSwitchType 1768 } -- Supervisor Engine Board
ibevtModuleSw-DS-3E7606-MPU               OBJECT IDENTIFIER ::= { ibevtModuleSwitchType 1769 } -- Supervisor Engine Board
ibevtModuleSw-DS-3E7600-24T4X-SC          OBJECT IDENTIFIER ::= { ibevtModuleSwitchType 1770 } -- 24-Port 1000Base-T Gigabit Ethernet Interface Board(RJ45)+4-Port 10GE Optical Interface Board(SFP+,LC)(SC)
ibevtModuleSw-DS-3E7600-24F4X-SA          OBJECT IDENTIFIER ::= { ibevtModuleSwitchType 1771 } -- 24-Port GE Optical Interface(SFP,LC)+4-Port 10GE Optical Interface Board(SFP+,LC)(SA)
ibevtModuleSw-DS-3E7600-48T-SA            OBJECT IDENTIFIER ::= { ibevtModuleSwitchType 1772 } -- 48-Port 1000Base-T Gigabit Ethernet Interface Board(RJ45)(SA)
ibevtModuleSw-DS-3E7600-48F-SA            OBJECT IDENTIFIER ::= { ibevtModuleSwitchType 1773 } -- 48-Port 1000BASE-X Ethernet Optical Interface Board(SFP,LC)(SA)
ibevtModuleSw-DS-3E7600-24F4X-SC          OBJECT IDENTIFIER ::= { ibevtModuleSwitchType 1774 } -- 24-Port GE Optical Interface(SFP,LC)+4-Port 10GE Optical Interface Board(SFP+,LC)(SC)
ibevtModuleSw-DS-3E7600-44F4X-SC          OBJECT IDENTIFIER ::= { ibevtModuleSwitchType 1775 } -- 44-Port GE Optical Interface(SFP,LC)+4-Port 10GE Optical Interface Board(SFP+,LC)(SC)
ibevtModuleSw-DS-3E7600-48T-SC            OBJECT IDENTIFIER ::= { ibevtModuleSwitchType 1776 } -- 48-Port 1000Base-T Gigabit Ethernet Interface Board(RJ45)(SC)
ibevtModuleSw-DS-3E7600-16X-SC            OBJECT IDENTIFIER ::= { ibevtModuleSwitchType 1777 } -- 16-Port 10GE Optical Interface Board(SFP+,LC)(SF)
ibevtModuleSw-S7602-MPU                   OBJECT IDENTIFIER ::= { ibevtModuleSwitchType 1778 } -- Supervisor Engine Board
ibevtModuleSw-S7606-MPU                   OBJECT IDENTIFIER ::= { ibevtModuleSwitchType 1779 } -- Supervisor Engine Board
ibevtModuleSw-S76-24GT4XFSC               OBJECT IDENTIFIER ::= { ibevtModuleSwitchType 1780 } -- 24-Port 1000Base-T Gigabit Ethernet Interface Board(RJ45)+4-Port 10GE Optical Interface Board(SFP+,LC)(SC)
ibevtModuleSw-S76-24GF4XFSA               OBJECT IDENTIFIER ::= { ibevtModuleSwitchType 1781 } -- 24-Port GE Optical Interface(SFP,LC)+4-Port 10GE Optical Interface Board(SFP+,LC)(SA)
ibevtModuleSw-S76-48GTSA                  OBJECT IDENTIFIER ::= { ibevtModuleSwitchType 1782 } -- 48-Port 1000Base-T Gigabit Ethernet Interface Board(RJ45)(SA)
ibevtModuleSw-S76-48GFSA                  OBJECT IDENTIFIER ::= { ibevtModuleSwitchType 1783 } -- 48-Port 1000BASE-X Ethernet Optical Interface Board(SFP,LC)(SA)
ibevtModuleSw-S76-24GT20GF4XFSC           OBJECT IDENTIFIER ::= { ibevtModuleSwitchType 1784 } -- 24-Port 1000Base-T Gigabit Ethernet Interface Board(RJ45)+20-Port GE Optical Interface(SFP,LC)+4-Port 10GE Optical Interface Board(SFP+,LC)(SC)
ibevtModuleSw-LSXM1TGS48C2HB0             OBJECT IDENTIFIER ::= { ibevtModuleSwitchType 1785 } -- 48-PORT 10GBASE Ethernet Optical Interface (SFP+,LC)+2-PORT 100GBASE Ethernet Optical Interface Module(QSFP28)(HB)
ibevtModuleSw-LSXM1CGQ18QGHC0             OBJECT IDENTIFIER ::= { ibevtModuleSwitchType 1786 } -- 18-PORT 100GBASE Ethernet Optical Interface (QSFP28)/36-PORT 40GBASE Ethernet Optical Interface Module(QSFP+)(HC)
ibevtModuleSw-LSXM1TGS48HB1               OBJECT IDENTIFIER ::= { ibevtModuleSwitchType 1787 } -- 48-Port 10G BASE Ethernet Optical Interface Module(SFP+,LC)(HB)
ibevtModuleSw-LSXM1TGS48HB0               OBJECT IDENTIFIER ::= { ibevtModuleSwitchType 1788 } -- 48-Port 10G BASE Ethernet Optical Interface Module(SFP+,LC)(HB)
ibevtModuleSw-LSQM1CGP24TSSC0             OBJECT IDENTIFIER ::= { ibevtModuleSwitchType 1789 } -- Supervisor Engine Board With 24-Port 1000BASE-X Ethernet SFP Optical Interface+4-Port 10GBASE-R Ethernet SFP+ Optical Interfaces
ibevtModuleSw-LSQM1CGP24TSSA0             OBJECT IDENTIFIER ::= { ibevtModuleSwitchType 1790 } -- Supervisor Engine Board With 24-Port 1000BASE-X Ethernet SFP Optical Interface+4-Port 10GBASE-R Ethernet SFP+ Optical Interfaces
ibevtModuleSw-LSQM1CGT24TSSC0             OBJECT IDENTIFIER ::= { ibevtModuleSwitchType 1791 } -- Supervisor Engine Board With 24-Port 10/100/1000BASE-T Ethernet Interface+4-Port 10GBASE-R Ethernet SFP+ Optical Interfaces
ibevtModuleSw-LSQM1CGT24TSSA0             OBJECT IDENTIFIER ::= { ibevtModuleSwitchType 1792 } -- Supervisor Engine Board With 24-Port 10/100/1000BASE-T Ethernet Interface+4-Port 10GBASE-R Ethernet SFP+ Optical Interfaces
ibevtModuleSw-LSQM2GP24SA0                OBJECT IDENTIFIER ::= { ibevtModuleSwitchType 1793 } -- 24-Port GE Optical Interface(SFP,LC)(SA)
ibevtModuleSw-LSX1SUPH1                   OBJECT IDENTIFIER ::= { ibevtModuleSwitchType 1794 } -- Supervisor Engine Board
ibevtModuleSw-LSX1SUPH0                   OBJECT IDENTIFIER ::= { ibevtModuleSwitchType 1795 } -- Supervisor Engine Board
ibevtModuleSw-LSX1SUP04H1                 OBJECT IDENTIFIER ::= { ibevtModuleSwitchType 1796 } -- Supervisor Engine Board
ibevtModuleSw-LSX1SUP04H0                 OBJECT IDENTIFIER ::= { ibevtModuleSwitchType 1797 } -- Supervisor Engine Board
ibevtModuleSw-LSXM1SFH08D0                OBJECT IDENTIFIER ::= { ibevtModuleSwitchType 1798 } -- Fabric Module,Type H(Class D)
ibevtModuleSw-LSXM1SFH04D0                OBJECT IDENTIFIER ::= { ibevtModuleSwitchType 1799 } -- Fabric Module,Type H(Class D)
--
-- 1800 for united assignment
--
ibevtModuleSw-LSXM1SFH16C0                OBJECT IDENTIFIER ::= { ibevtModuleSwitchType 1800 } -- Fabric Module,Type H(Class C+)
ibevtModuleSw-LSXM1SFH12D0                OBJECT IDENTIFIER ::= { ibevtModuleSwitchType 1801 } -- Fabric Module,Type H(Class D)
ibevtModuleSw-LSXM1QGS48HB0               OBJECT IDENTIFIER ::= { ibevtModuleSwitchType 1802 } -- 48-Port 40GBASE Ethernet Optical Interface Module(QSFP+)(HB)
ibevtModuleSw-LSXM1QGS48HC0               OBJECT IDENTIFIER ::= { ibevtModuleSwitchType 1803 } -- 48-Port 40GBASE Ethernet Optical Interface Module(QSFP+)(HC)
ibevtModuleSw-LSXM1CGQ36HB0               OBJECT IDENTIFIER ::= { ibevtModuleSwitchType 1804 } -- 36-Port 100GBASE Ethernet Optical Interface Module(QSFP28)(HB)
ibevtModuleSw-LSXM1TGS48C2HC0             OBJECT IDENTIFIER ::= { ibevtModuleSwitchType 1805 } -- 48-PORT 10GBASE Ethernet Optical Interface (SFP+,LC)+2-PORT 100GBASE Ethernet Optical Interface Module(QSFP28)(HC)
ibevtModuleSw-LSQM2GP44TSSE0              OBJECT IDENTIFIER ::= { ibevtModuleSwitchType 1806 } -- 44-Port GE Optical Interface(SFP,LC)+4-Port 10GE Optical Interface Board(SFP+,LC)(SE)
ibevtModuleSw-LSQM2GP24TSSA8              OBJECT IDENTIFIER ::= { ibevtModuleSwitchType 1807 } -- 24-Port GE Optical Interface(SFP,LC)+4-Port 10GE Optical Interface Board(SFP+,LC)(SA)
ibevtModuleSw-LSQM2GT48SA8                OBJECT IDENTIFIER ::= { ibevtModuleSwitchType 1808 } -- 48-Port 1000Base-T Gigabit Ethernet Interface Board(RJ45)(SA)
ibevtModuleSw-LSQM2GP48SA8                OBJECT IDENTIFIER ::= { ibevtModuleSwitchType 1809 } -- 48-Port 1000BASE-X Ethernet Optical Interface Board(SFP,LC)(SA)
ibevtModuleSw-EWPXM1CGP24TSSC0            OBJECT IDENTIFIER ::= { ibevtModuleSwitchType 1810 } -- Supervisor Engine Board With 24-Port 1000BASE-X Ethernet SFP Optical Interface+4-Port 10GBASE-R Ethernet SFP+ Optical Interfaces
ibevtModuleSw-EWPXM3MPUB0                 OBJECT IDENTIFIER ::= { ibevtModuleSwitchType 1811 } -- Supervisor Engine Board
ibevtModuleSw-EWPXM2MPUDS0                OBJECT IDENTIFIER ::= { ibevtModuleSwitchType 1812 } -- Supervisor Engine Board
ibevtModuleSw-EWPXM2TGS16SF0              OBJECT IDENTIFIER ::= { ibevtModuleSwitchType 1813 } -- 16-Port 10GE Optical Interface Board(SFP+,LC)(SF)
ibevtModuleSw-EWPXM2GP44TSSC0             OBJECT IDENTIFIER ::= { ibevtModuleSwitchType 1814 } -- 44-Port GE Optical Interface(SFP,LC)+4-Port 10GE Optical Interface Board(SFP+,LC)(SC)
ibevtModuleSw-EWPXM2GP24TSSC0             OBJECT IDENTIFIER ::= { ibevtModuleSwitchType 1815 } -- 24-Port GE Optical Interface(SFP,LC)+4-Port 10GE Optical Interface Board(SFP+,LC)(SC)
ibevtModuleSw-EWPXM1MAC0F                 OBJECT IDENTIFIER ::= { ibevtModuleSwitchType 1816 } -- Access Controller Service Board
ibevtModuleSw-LSQM1CGP24TSSA8             OBJECT IDENTIFIER ::= { ibevtModuleSwitchType 1817 } -- Supervisor Engine Board With 24-Port 1000BASE-X Ethernet SFP Optical Interface+4-Port 10GBASE-R Ethernet SFP+ Optical Interfaces
ibevtModuleSw-LSQM1CGT24TSSA8             OBJECT IDENTIFIER ::= { ibevtModuleSwitchType 1818 } -- Supervisor Engine Board With 24-Port 10/100/1000BASE-T Ethernet Interface+4-Port 10GBASE-R Ethernet SFP+ Optical Interfaces
ibevtModuleSw-LSWM1FWD0                   OBJECT IDENTIFIER ::= { ibevtModuleSwitchType 1819 } -- Firewall Service Board
ibevtModuleSw-LSUM2MPU10C0                OBJECT IDENTIFIER ::= { ibevtModuleSwitchType 1820 } -- Supervisor Engine Board
ibevtModuleSw-LSQM2MPU10C0                OBJECT IDENTIFIER ::= { ibevtModuleSwitchType 1821 } -- Supervisor Engine Board
ibevtModuleSw-LSUM2MPU10C3                OBJECT IDENTIFIER ::= { ibevtModuleSwitchType 1822 } -- Supervisor Engine Board
ibevtModuleSw-LSUM2FAB10C0                OBJECT IDENTIFIER ::= { ibevtModuleSwitchType 1823 } -- Switching Fabric Module
ibevtModuleSw-LSQM2FAB10C0                OBJECT IDENTIFIER ::= { ibevtModuleSwitchType 1824 } -- Switching Fabric Module
ibevtModuleSw-LSUM2FAB10C3                OBJECT IDENTIFIER ::= { ibevtModuleSwitchType 1825 } -- Switching Fabric Module
ibevtModuleSw-LSUM2CQGS12SG0              OBJECT IDENTIFIER ::= { ibevtModuleSwitchType 1826 } -- 12-Port 40GBASE-R QSFP+ or 4-Port 100GBASE-R QSFP28 Optical Interface Board(SG)
ibevtModuleSw-LSXM2CQGS12SG3              OBJECT IDENTIFIER ::= { ibevtModuleSwitchType 1827 } -- 12-Port 40GBASE-R QSFP+ or 4-Port 100GBASE-R QSFP28 Optical Interface Board(SG)
ibevtModuleSw-LSQM2CQGS12XSG0             OBJECT IDENTIFIER ::= { ibevtModuleSwitchType 1828 } -- 12-Port 40GBASE-R QSFP+ or 4-Port 100GBASE-R QSFP28 Optical Interface Board(SG)
ibevtModuleSw-LSQM1CQGS12SG0              OBJECT IDENTIFIER ::= { ibevtModuleSwitchType 1829 } -- 12-Port 40GBASE-R QSFP+ or 4-Port 100GBASE-R QSFP28 Optical Interface Board(SG)
ibevtModuleSw-LSXM1CGQ6QGHB0              OBJECT IDENTIFIER ::= { ibevtModuleSwitchType 1830 } -- 6-Port 100GBASE Ethernet Optical Interface(QSFP28)/12-Port 40GBASE Ethernet Optical Interface Module(QSFP+)(HB)
ibevtModuleSw-LSXM1CGQ6QGHB1              OBJECT IDENTIFIER ::= { ibevtModuleSwitchType 1831 } -- 6-Port 100GBASE Ethernet Optical Interface(QSFP28)/12-Port 40GBASE Ethernet Optical Interface Module(QSFP+)(HB)
ibevtModuleSw-LSXM1CGQ6QGHC0              OBJECT IDENTIFIER ::= { ibevtModuleSwitchType 1832 } -- 6-Port 100GBASE Ethernet Optical Interface(QSFP28)/12-Port 40GBASE Ethernet Optical Interface Module(QSFP+)(HC)
ibevtModuleSw-LSXM1QGS36HB0               OBJECT IDENTIFIER ::= { ibevtModuleSwitchType 1833 } -- 36-Port 40GBASE Ethernet Optical Interface Module(QSFP+)(HB)
ibevtModuleSw-LSXM1QGS36HB1               OBJECT IDENTIFIER ::= { ibevtModuleSwitchType 1834 } -- 36-Port 40GBASE Ethernet Optical Interface Module(QSFP+)(HB)
ibevtModuleSw-LSXM1QGS36HC0               OBJECT IDENTIFIER ::= { ibevtModuleSwitchType 1835 } -- 36-Port 40GBASE Ethernet Optical Interface Module(QSFP+)(HC)
ibevtModuleSw-LSXM1SUPC0                  OBJECT IDENTIFIER ::= { ibevtModuleSwitchType 1836 } -- Supervisor Engine Unit
ibevtModuleSw-LSXM1SUPC1                  OBJECT IDENTIFIER ::= { ibevtModuleSwitchType 1837 } -- Supervisor Engine Unit
ibevtModuleSw-LSXM1SUP04H0                OBJECT IDENTIFIER ::= { ibevtModuleSwitchType 1838 } -- Supervisor Engine Unit
ibevtModuleSw-LSXM1SUP04H1                OBJECT IDENTIFIER ::= { ibevtModuleSwitchType 1839 } -- Supervisor Engine Unit
ibevtModuleSw-LSXM1SUPH0                  OBJECT IDENTIFIER ::= { ibevtModuleSwitchType 1840 } -- Supervisor Engine Unit
ibevtModuleSw-LSXM1SUPH1                  OBJECT IDENTIFIER ::= { ibevtModuleSwitchType 1841 } -- Supervisor Engine Unit
ibevtModuleSw-EWPXM2WCMD0F                OBJECT IDENTIFIER ::= { ibevtModuleSwitchType 1842 } -- 20G Access Controller Module
ibevtModuleSw-LSUM2QGS24RSG0              OBJECT IDENTIFIER ::= { ibevtModuleSwitchType 1843 } -- 24-Port 40GBASE-R Ethernet QSFP+ Optical Interface Board(SG)
ibevtModuleSw-LSQM1QGS24RSG0              OBJECT IDENTIFIER ::= { ibevtModuleSwitchType 1844 } -- 24-Port 40GBASE-R Ethernet QSFP+ Optical Interface Board(SG)
ibevtModuleSw-LSXM2QGS24RSG3              OBJECT IDENTIFIER ::= { ibevtModuleSwitchType 1845 } -- 24-Port 40GBASE-R Ethernet QSFP+ Optical Interface Board(SG)
ibevtModuleSw-LSQM2QGS24RXSG0             OBJECT IDENTIFIER ::= { ibevtModuleSwitchType 1846 } -- 24-Port 40GBASE-R Ethernet QSFP+ Optical Interface Board(SG)
ibevtModuleSw-LSQM2TGS48RSG0              OBJECT IDENTIFIER ::= { ibevtModuleSwitchType 1847 } -- 48-Port 10GBASE-R Ethernet SFP+ Optical Interface Board(SG)
ibevtModuleSw-LSXM1X86SUPE0               OBJECT IDENTIFIER ::= { ibevtModuleSwitchType 1848 } -- Cloud Supervisor Engine Unit
ibevtModuleSw-LSXM1X86SUPE1               OBJECT IDENTIFIER ::= { ibevtModuleSwitchType 1849 } -- Cloud Supervisor Engine Unit
ibevtModuleSw-LSQM1CGS2QSA0               OBJECT IDENTIFIER ::= { ibevtModuleSwitchType 1850 } -- 2-Port 100G Ethernet Optical Interface(QSFP28)+2-Port 40G Ethernet Optical Interface Module(QSFP+)
ibevtModuleSw-LSUM1ACGDEC0                OBJECT IDENTIFIER ::= { ibevtModuleSwitchType 1851 } -- SecBlade IV Application Control Module
ibevtModuleSw-LSQM1ACGDSC0                OBJECT IDENTIFIER ::= { ibevtModuleSwitchType 1852 } -- SecBlade IV Application Control Module
ibevtModuleSw-LSXM1CGQ36HF1               OBJECT IDENTIFIER ::= { ibevtModuleSwitchType 1853 } -- 36-Port 100GBASE Ethernet Optical Interface Module(QSFP28)(HF)
ibevtModuleSw-LSXM1QGS48HF1               OBJECT IDENTIFIER ::= { ibevtModuleSwitchType 1854 } -- 48-Port 40GBASE Ethernet Optical Interface Module(QSFP+)(HF)
ibevtModuleSw-LSXM1CGQ18QGHF1             OBJECT IDENTIFIER ::= { ibevtModuleSwitchType 1855 } -- 18-PORT 100GBASE Ethernet Optical Interface(QSFP28)/36-Port 40GBASE Ethernet Optical Interface Module(QSFP+)(HF)
ibevtModuleSw-LSXM1QGS36HF1               OBJECT IDENTIFIER ::= { ibevtModuleSwitchType 1856 } -- 36-Port 40GBASE Ethernet Optical Interface Module(QSFP+)(HF)
ibevtModuleSw-LSXM1CGQ6QGHF1              OBJECT IDENTIFIER ::= { ibevtModuleSwitchType 1857 } -- 6-Port 100GBASE Ethernet Optical Interface(QSFP28)/12-Port 40GBASE Ethernet Optical Interface Module(QSFP+)(HF)
ibevtModuleSw-LSXM1QGS48HF0               OBJECT IDENTIFIER ::= { ibevtModuleSwitchType 1858 } -- 48-Port 40GBASE Ethernet Optical Interface Module(QSFP+)(HF)
ibevtModuleSw-LSXM1CGQ18QGHF0             OBJECT IDENTIFIER ::= { ibevtModuleSwitchType 1859 } -- 18-PORT 100GBASE Ethernet Optical Interface(QSFP28)/36-Port 40GBASE Ethernet Optical Interface Module(QSFP+)(HF)
ibevtModuleSw-LSXM1CGQ6QGHF0              OBJECT IDENTIFIER ::= { ibevtModuleSwitchType 1860 } -- 6-Port 100GBASE Ethernet Optical Interface(QSFP28)/12-Port 40GBASE Ethernet Optical Interface Module(QSFP+)(HF)
ibevtModuleSw-LSXM1TGS48HF0               OBJECT IDENTIFIER ::= { ibevtModuleSwitchType 1861 } -- 48-Port 10GBASE Ethernet Optical Interface Module(SFP+,LC)(HF)
ibevtModuleSw-LSXM1TGS48HF1               OBJECT IDENTIFIER ::= { ibevtModuleSwitchType 1862 } -- 48-Port 10GBASE Ethernet Optical Interface Module(SFP+,LC)(HF)
ibevtModuleSw-LSQM1GP24FC3                OBJECT IDENTIFIER ::= { ibevtModuleSwitchType 1863 } -- 24-Port 1000BASE-X Optical Interface Board(SFP,LC)
ibevtModuleSw-LSQM1GP24FD3                OBJECT IDENTIFIER ::= { ibevtModuleSwitchType 1864 } -- 24-Port 1000BASE-X Optical Interface Board(SFP,LC)
ibevtModuleSw-LSQM1GP24TSFC3              OBJECT IDENTIFIER ::= { ibevtModuleSwitchType 1865 } -- 24-Port 1000BASE-X Optical Interface(SFP,LC)+4-Port 10GBASE-R Ethernet Optical Interface Board(SFP+,LC)
ibevtModuleSw-LSQM1GP24TSFD3              OBJECT IDENTIFIER ::= { ibevtModuleSwitchType 1866 } -- 24-Port 1000BASE-X Optical Interface(SFP,LC)+4-Port 10GBASE-R Ethernet Optical Interface Board(SFP+,LC)
ibevtModuleSw-LSQM1GP40TS8FD0             OBJECT IDENTIFIER ::= { ibevtModuleSwitchType 1867 } -- 40-Port 1000BASE-X Optical Interface(SFP,LC)+8-Port 10GBASE-R Ethernet Optical Interface Board(SFP+,LC)
ibevtModuleSw-LSQM1GP48FC3                OBJECT IDENTIFIER ::= { ibevtModuleSwitchType 1868 } -- 48-Port 1000BASE-X Optical Interface Board(SFP,LC)
ibevtModuleSw-LSQM1GP48FD0                OBJECT IDENTIFIER ::= { ibevtModuleSwitchType 1869 } -- 48-Port 1000BASE-X Optical Interface Board(SFP,LC)
ibevtModuleSw-LSQM1GP48FD3                OBJECT IDENTIFIER ::= { ibevtModuleSwitchType 1870 } -- 48-Port 1000BASE-X Optical Interface Board(SFP,LC)
ibevtModuleSw-LSQM1GT48FC3                OBJECT IDENTIFIER ::= { ibevtModuleSwitchType 1871 } -- 48-Port 10/100/1000BASE-T Electrical Interface Board(RJ45)
ibevtModuleSw-LSQM1GT48FD0                OBJECT IDENTIFIER ::= { ibevtModuleSwitchType 1872 } -- 48-Port 10/100/1000BASE-T Electrical Interface Board(RJ45)
ibevtModuleSw-LSQM1GT48FD3                OBJECT IDENTIFIER ::= { ibevtModuleSwitchType 1873 } -- 48-Port 10/100/1000BASE-T Electrical Interface Board(RJ45)
ibevtModuleSw-LSQM1TGS24FC3               OBJECT IDENTIFIER ::= { ibevtModuleSwitchType 1874 } -- 24-Port 10GBASE-R Ethernet Optical Interface Board(SFP+,LC)
ibevtModuleSw-LSQM1TGS24FD0               OBJECT IDENTIFIER ::= { ibevtModuleSwitchType 1875 } -- 24-Port 10GBASE-R Ethernet Optical Interface Board(SFP+,LC)
ibevtModuleSw-LSQM1TGS24FD3               OBJECT IDENTIFIER ::= { ibevtModuleSwitchType 1876 } -- 24-Port 10GBASE-R Ethernet Optical Interface Board(SFP+,LC)
ibevtModuleSw-LSQM1TGS24XFD0              OBJECT IDENTIFIER ::= { ibevtModuleSwitchType 1877 } -- 24-Port 10GBASE-R Ethernet Optical Interface Board(SFP+,LC)
ibevtModuleSw-LSQM1TGS48RFE0              OBJECT IDENTIFIER ::= { ibevtModuleSwitchType 1878 } -- 48-Port 10GBASE-R Ethernet Optical Interface Board(SFP+,LC)
ibevtModuleSw-LSQM1TGS8FC3                OBJECT IDENTIFIER ::= { ibevtModuleSwitchType 1879 } -- 8-Port 10GBASE-R Ethernet Optical Interface Board(SFP+,LC)
ibevtModuleSw-LSQM1TGS8FD3                OBJECT IDENTIFIER ::= { ibevtModuleSwitchType 1880 } -- 8-Port 10GBASE-R Ethernet Optical Interface Board(SFP+,LC)
ibevtModuleSw-LSUM1GP40TS8FD0             OBJECT IDENTIFIER ::= { ibevtModuleSwitchType 1881 } -- 40-Port 1000BASE-X Optical Interface(SFP,LC)+8-Port 10GBASE-R Ethernet Optical Interface Board(SFP+,LC)
ibevtModuleSw-LSUM1GP48FD0                OBJECT IDENTIFIER ::= { ibevtModuleSwitchType 1882 } -- 48-Port 1000BASE-X Optical Interface Board(SFP,LC)
ibevtModuleSw-LSUM1GP48FD3                OBJECT IDENTIFIER ::= { ibevtModuleSwitchType 1883 } -- 48-Port 1000BASE-X Optical Interface Board(SFP,LC)
ibevtModuleSw-LSUM1GT48FD0                OBJECT IDENTIFIER ::= { ibevtModuleSwitchType 1884 } -- 48-Port 10/100/1000BASE-T Electrical Interface Board(RJ45)
ibevtModuleSw-LSUM1GT48FD3                OBJECT IDENTIFIER ::= { ibevtModuleSwitchType 1885 } -- 48-Port 10/100/1000BASE-T Electrical Interface Board(RJ45)
ibevtModuleSw-LSUM1TGS24FD0               OBJECT IDENTIFIER ::= { ibevtModuleSwitchType 1886 } -- 24-Port 10GBASE-R Ethernet Optical Interface Board(SFP+,LC)
ibevtModuleSw-LSUM1TGS24FD3               OBJECT IDENTIFIER ::= { ibevtModuleSwitchType 1887 } -- 24-Port 10GBASE-R Ethernet Optical Interface Board(SFP+,LC)
ibevtModuleSw-LSXM1GP40TS8FD0             OBJECT IDENTIFIER ::= { ibevtModuleSwitchType 1888 } -- 40-Port 1000BASE-X Optical Interface(SFP,LC)+8-Port 10GBASE-R Ethernet Optical Interface Board(SFP+,LC)
ibevtModuleSw-LSXM1GT48FD3                OBJECT IDENTIFIER ::= { ibevtModuleSwitchType 1889 } -- 48-Port 10/100/1000BASE-T Electrical Interface Board(RJ45)
ibevtModuleSw-LSXM1TGS24FD3               OBJECT IDENTIFIER ::= { ibevtModuleSwitchType 1890 } -- 24-Port 10GBASE-R Ethernet Optical Interface Board(SFP+,LC)
ibevtModuleSw-LSQM1MPUS10C3               OBJECT IDENTIFIER ::= { ibevtModuleSwitchType 1891 } -- Supervisor Engine Board
ibevtModuleSw-LSQM1MPUSA3                 OBJECT IDENTIFIER ::= { ibevtModuleSwitchType 1892 } -- Supervisor Engine Board
ibevtModuleSw-LSQM2SUPA3                  OBJECT IDENTIFIER ::= { ibevtModuleSwitchType 1893 } -- Supervisor Engine Board
ibevtModuleSw-LSXM1SFH16E1                OBJECT IDENTIFIER ::= { ibevtModuleSwitchType 1894 } -- S12516X-AF Fabric Module,Type H(Class E)
ibevtModuleSw-LSXM1SFH16E0                OBJECT IDENTIFIER ::= { ibevtModuleSwitchType 1895 } -- S12516X-AF Fabric Module,Type H(Class E)
ibevtModuleSw-LSXM1GP40TS8FD3             OBJECT IDENTIFIER ::= { ibevtModuleSwitchType 1896 } -- 40-Port 1000BASE-X Optical Interface(SFP,LC)+8-Port 10GBASE-R Ethernet Optical Interface Board(SFP+,LC)
ibevtModuleSw-LSQM1MPUS10C0               OBJECT IDENTIFIER ::= { ibevtModuleSwitchType 1897 } -- Supervisor Engine Board
ibevtModuleSw-LSQM1MPUSA0                 OBJECT IDENTIFIER ::= { ibevtModuleSwitchType 1898 } -- Supervisor Engine Board
ibevtModuleSw-LSQM2SUPA0                  OBJECT IDENTIFIER ::= { ibevtModuleSwitchType 1899 } -- Supervisor Engine Board
ibevtModuleSw-LSQM1TGS16FC3               OBJECT IDENTIFIER ::= { ibevtModuleSwitchType 1900 } -- 16-Port 10GBASE-R Ethernet SFP+ Optical Interface Board(FC)
ibevtModuleSw-LSQM1TGS16FD0               OBJECT IDENTIFIER ::= { ibevtModuleSwitchType 1901 } -- 16-Port 10GBASE-R Ethernet SFP+ Optical Interface Board(FD)
ibevtModuleSw-LSQM1TGS16FD3               OBJECT IDENTIFIER ::= { ibevtModuleSwitchType 1902 } -- 16-Port 10GBASE-R Ethernet SFP+ Optical Interface Board(FD)
ibevtModuleSw-LSQM2TGS48SG0               OBJECT IDENTIFIER ::= { ibevtModuleSwitchType 1903 } -- 48-Port 10GBASE-R Ethernet SFP+ Optical Interface Board(SG)
ibevtModuleSw-LSQM2TGS48SG3               OBJECT IDENTIFIER ::= { ibevtModuleSwitchType 1904 } -- 48-Port 10GBASE-R Ethernet SFP+ Optical Interface Board(SG)
ibevtModuleSw-LSXM1CGQ48HB1               OBJECT IDENTIFIER ::= { ibevtModuleSwitchType 1905 } -- 48-Port 100GBASE Ethernet Optical Interface Module(QSFP+)(HB)
ibevtModuleSw-LSQM1MPUS06A8               OBJECT IDENTIFIER ::= { ibevtModuleSwitchType 1906 } -- Supervisor Engine Board
ibevtModuleSw-LSQM1TGS16FD8               OBJECT IDENTIFIER ::= { ibevtModuleSwitchType 1907 } -- 16-Port 10GBASE-R Ethernet SFP+ Optical Interface Board(FD)
ibevtModuleSw-LSXM1SFH08E1                OBJECT IDENTIFIER ::= { ibevtModuleSwitchType 1908 } -- Fabric Module,Type H(Class E)

ibevtModuleSw-LSXM1SFH08CC0               OBJECT IDENTIFIER ::= { ibevtModuleSwitchType 1909 } -- S12508M-AF Fabric Module,Type H(Class C)
ibevtModuleSw-LSXM1SUP08C0                OBJECT IDENTIFIER ::= { ibevtModuleSwitchType 1910 } -- S12508M-AF Supervisor Engine Unit
ibevtModuleSw-LSUM2FAB04D0                OBJECT IDENTIFIER ::= { ibevtModuleSwitchType 1911 } -- Switching Fabric Module
ibevtModuleSw-LSUM2FAB04D3                OBJECT IDENTIFIER ::= { ibevtModuleSwitchType 1912 } -- Switching Fabric Module
ibevtModuleSw-LSXM2FAB04D3                OBJECT IDENTIFIER ::= { ibevtModuleSwitchType 1913 } -- Switching Fabric Module
ibevtModuleSw-LSUM2FAB04B0                OBJECT IDENTIFIER ::= { ibevtModuleSwitchType 1914 } -- Switching Fabric Module
ibevtModuleSw-LSUM2FAB04B3                OBJECT IDENTIFIER ::= { ibevtModuleSwitchType 1915 } -- Switching Fabric Module
ibevtModuleSw-LSUM2FAB08D0                OBJECT IDENTIFIER ::= { ibevtModuleSwitchType 1916 } -- Switching Fabric Module
ibevtModuleSw-LSUM2FAB08D3                OBJECT IDENTIFIER ::= { ibevtModuleSwitchType 1917 } -- Switching Fabric Module
ibevtModuleSw-LSXM2FAB08D3                OBJECT IDENTIFIER ::= { ibevtModuleSwitchType 1918 } -- Switching Fabric Module
ibevtModuleSw-LSUM2FAB08B0                OBJECT IDENTIFIER ::= { ibevtModuleSwitchType 1919 } -- Switching Fabric Module
ibevtModuleSw-LSUM2FAB08B3                OBJECT IDENTIFIER ::= { ibevtModuleSwitchType 1920 } -- Switching Fabric Module
ibevtModuleSw-LSUM2FAB12D0                OBJECT IDENTIFIER ::= { ibevtModuleSwitchType 1921 } -- Switching Fabric Module
ibevtModuleSw-LSUM2FAB12D3                OBJECT IDENTIFIER ::= { ibevtModuleSwitchType 1922 } -- Switching Fabric Module
ibevtModuleSw-LSXM2FAB12D3                OBJECT IDENTIFIER ::= { ibevtModuleSwitchType 1923 } -- Switching Fabric Module
ibevtModuleSw-LSUM2FAB12B0                OBJECT IDENTIFIER ::= { ibevtModuleSwitchType 1924 } -- Switching Fabric Module
ibevtModuleSw-LSUM2FAB12B3                OBJECT IDENTIFIER ::= { ibevtModuleSwitchType 1925 } -- Switching Fabric Module
ibevtModuleSw-LSQM1CGS2FE0                OBJECT IDENTIFIER ::= { ibevtModuleSwitchType 1926 } -- 2-Port 100GBASE-R Ethernet QSFP28 Optical Interface Board(FE)
ibevtModuleSw-LSQM1CGS2FE3                OBJECT IDENTIFIER ::= { ibevtModuleSwitchType 1927 } -- 2-Port 100GBASE-R Ethernet QSFP28 Optical Interface Board(FE)
ibevtModuleSw-LSQM1CGS2XFE0               OBJECT IDENTIFIER ::= { ibevtModuleSwitchType 1928 } -- 2-Port 100GBASE-R Ethernet QSFP28 Optical Interface Board(FE)
ibevtModuleSw-LSUM1CGS2FE0                OBJECT IDENTIFIER ::= { ibevtModuleSwitchType 1929 } -- 2-Port 100GBASE-R Ethernet QSFP28 Optical Interface Board(FE)
ibevtModuleSw-LSUM1CGS2FE3                OBJECT IDENTIFIER ::= { ibevtModuleSwitchType 1930 } -- 2-Port 100GBASE-R Ethernet QSFP28 Optical Interface Board(FE)
ibevtModuleSw-LSXM1CGS2FE3                OBJECT IDENTIFIER ::= { ibevtModuleSwitchType 1931 } -- 2-Port 100GBASE-R Ethernet QSFP28 Optical Interface Board(FE)
ibevtModuleSw-LSUM1TGS16FD0               OBJECT IDENTIFIER ::= { ibevtModuleSwitchType 1932 } -- 16-Port 10GBASE-R Ethernet SFP+ Optical Interface Board(FD)
ibevtModuleSw-LSUM1TGS16FD3               OBJECT IDENTIFIER ::= { ibevtModuleSwitchType 1933 } -- 16-Port 10GBASE-R Ethernet SFP+ Optical Interface Board(FD)
ibevtModuleSw-LSQM1TGS16XFD0              OBJECT IDENTIFIER ::= { ibevtModuleSwitchType 1934 } -- 16-Port 10GBASE-R Ethernet SFP+ Optical Interface Board(FD)
ibevtModuleSw-LSQM1GP40TS8FC3             OBJECT IDENTIFIER ::= { ibevtModuleSwitchType 1935 } -- 40-Port 1000BASE-X Optical Interface(SFP,LC)+8-Port 10GBASE-R Ethernet Optical Interface Board(SFP+,LC)
ibevtModuleSw-S76-16XFSF                  OBJECT IDENTIFIER ::= { ibevtModuleSwitchType 1936 } -- 16-Port 10GE Optical Interface Board(SFP+,LC)(SF)
ibevtModuleSw-S76-24EP2XFSC-OLT           OBJECT IDENTIFIER ::= { ibevtModuleSwitchType 1937 } -- 24-Port 1G EPON OLT Optical Interface(SFP,SC)+2-Port 10GE Optical Interface Board(SFP+,LC)(SC)
ibevtModuleSw-DS-3E7600-24T20F4X-SC       OBJECT IDENTIFIER ::= { ibevtModuleSwitchType 1938 } -- 24-Port 1000Base-T Gigabit Ethernet Interface Board(RJ45)+20-Port GE Optical Interface(SFP,LC)+4-Port 10GE Optical Interface Board(SFP+,LC)(SC)
ibevtModuleSw-LSUM1FAB04E0                OBJECT IDENTIFIER ::= { ibevtModuleSwitchType 1939 } -- Switching Fabric Module
ibevtModuleSw-LSUM1FAB08E0                OBJECT IDENTIFIER ::= { ibevtModuleSwitchType 1940 } -- Switching Fabric Module
ibevtModuleSw-LSUM1FAB12E0                OBJECT IDENTIFIER ::= { ibevtModuleSwitchType 1941 } -- Switching Fabric Module
ibevtModuleSw-LSXM1CGQ8FX1                OBJECT IDENTIFIER ::= { ibevtModuleSwitchType 1942 } -- 8-Port 100GBASE Ethernet Optical Interface Module(QSFP28)(FX)
ibevtModuleSw-LSQM1IPSDSC0                OBJECT IDENTIFIER ::= { ibevtModuleSwitchType 1943 } -- SecBlade IV Intrusion Prevention System Module
ibevtModuleSw-LSQM2ACGDSC0                OBJECT IDENTIFIER ::= { ibevtModuleSwitchType 1944 } -- SecBlade IV Application Control Module
ibevtModuleSw-LSQM1ADEDSC0                OBJECT IDENTIFIER ::= { ibevtModuleSwitchType 1945 } -- SecBlade IV Load Balancing Module
ibevtModuleSw-LSWM1ADED0                  OBJECT IDENTIFIER ::= { ibevtModuleSwitchType 1946 } -- SecBlade IV Load Balancing Card
ibevtModuleSw-LSWM1IPSD0                  OBJECT IDENTIFIER ::= { ibevtModuleSwitchType 1947 } -- SecBlade IV Intrusion Prevention System Card
ibevtModuleSw-LSQM1GP40TS8FD3             OBJECT IDENTIFIER ::= { ibevtModuleSwitchType 1948 } -- 40-Port 1000BASE-X Optical Interface(SFP,LC)+8-Port 10GBASE-R Ethernet Optical Interface Board(SFP+,LC)
ibevtModuleSw-LSUM1SUPXD0                 OBJECT IDENTIFIER ::= { ibevtModuleSwitchType 1949 } -- Supervisor Engine Board
ibevtModuleSw-LSUM1CQGS32SF0              OBJECT IDENTIFIER ::= { ibevtModuleSwitchType 1950 } -- 32-Port 40GBASE-R QSFP+ or 16-Port 100GBASE-R QSFP28 Optical Interface Board(SF)
ibevtModuleSw-LSUM1TGS48XSG0              OBJECT IDENTIFIER ::= { ibevtModuleSwitchType 1951 } -- 48-Port 10GBASE-R Ethernet SFP+ Optical Interface Board(SG)
ibevtModuleSw-LSUM1FAB08XE0               OBJECT IDENTIFIER ::= { ibevtModuleSwitchType 1952 } -- Switching Fabric Module
ibevtModuleSw-LSUM1FAB16XD0               OBJECT IDENTIFIER ::= { ibevtModuleSwitchType 1953 } -- Switching Fabric Module
ibevtModuleSw-LSXM1SFH02E0                OBJECT IDENTIFIER ::= { ibevtModuleSwitchType 1954 } -- Switching Fabric Module
ibevtModuleSw-LSXM1SFH02E1                OBJECT IDENTIFIER ::= { ibevtModuleSwitchType 1955 } -- Switching Fabric Module
ibevtModuleSw-LSXM1SFH12C0                OBJECT IDENTIFIER ::= { ibevtModuleSwitchType 1956 } -- Fabric Module,Type H(Class C)
ibevtModuleSw-LSXM1SFH12C1                OBJECT IDENTIFIER ::= { ibevtModuleSwitchType 1957 } -- Fabric Module,Type H(Class C)
ibevtModuleSw-LSUM1CQGS12XSG0             OBJECT IDENTIFIER ::= { ibevtModuleSwitchType 1958 } -- 12-Port 40GBASE-R QSFP+ or 4-Port 100GBASE-R QSFP28 Optical Interface Board(SG)
ibevtModuleSw-LSQM1CTGS24QSFD0            OBJECT IDENTIFIER ::= { ibevtModuleSwitchType 1959 } -- Supervisor Engine Board With 24-Port 10GBASE-R SFP+ Optical Interface+2-Port 40GBASE-R QSFP+ Optical Interfaces or 1-Port 100GBASE-R QSFP28 Optical Interfaces
ibevtModuleSw-LSQM1TGS24QSFD0             OBJECT IDENTIFIER ::= { ibevtModuleSwitchType 1960 } -- 24-Port 10GBASE-R Optical Interface(SFP+,LC)+2-Port 40GBASE-R Optical Interface Board(QSFP+) or 1-Port 100GBASE-R Optical Interface Board(QSFP28)
ibevtModuleSw-LSUM1WBCZ720RT              OBJECT IDENTIFIER ::= { ibevtModuleSwitchType 1961 } -- Access Controller Service Board
ibevtModuleSw-LSQM1WBCZ720                OBJECT IDENTIFIER ::= { ibevtModuleSwitchType 1962 } -- Access Controller Service Board
ibevtModuleSw-DS-3E7610X-MPU              OBJECT IDENTIFIER ::= { ibevtModuleSwitchType 1963 } -- Supervisor Engine Board
ibevtModuleSw-DS-3E7610X-CLOS             OBJECT IDENTIFIER ::= { ibevtModuleSwitchType 1964 } -- Switching Fabric Module
ibevtModuleSw-DS-3E7610X-32X4QX-SF        OBJECT IDENTIFIER ::= { ibevtModuleSwitchType 1965 } -- 32-Port 10GBASE-R Ethernet Optical Interface(SFP+,LC)+4-Port 40GBASE-R Ethernet Optical Interface Board(QSFP+,LC)(SF)
ibevtModuleSw-DS-3E7610X-16X-SF           OBJECT IDENTIFIER ::= { ibevtModuleSwitchType 1966 } -- 16-Port 10GBASE-R Ethernet SFP+ Optical
ibevtModuleSw-DS-3E7610X-44F4X-SE         OBJECT IDENTIFIER ::= { ibevtModuleSwitchType 1967 } -- 44-Port GE Optical Interface(SFP,LC)+4-Port 10GE Optical Interface Board(SFP+,LC)(SE)
ibevtModuleSw-DS-3E7610X-48T-SE           OBJECT IDENTIFIER ::= { ibevtModuleSwitchType 1968 } -- 48-Port 1000Base-T Gigabit Ethernet Interface Board(RJ45)(SE)
ibevtModuleSw-LSQM2GT24PTSSC8             OBJECT IDENTIFIER ::= { ibevtModuleSwitchType 1969 } -- 24-Port 1000Base-T Gigabit Ethernet Interface Board(RJ45)+20-Port GE Optical Interface(SFP,LC)+4-Port 10GE Optical Interface Board(SFP+,LC)(SC)
ibevtModuleSw-LSQM1CGP24TSSC8             OBJECT IDENTIFIER ::= { ibevtModuleSwitchType 1970 } -- Supervisor Engine Board With 24-Port 1000BASE-X Ethernet SFP Optical Interface+4-Port 10GBASE-R Ethernet SFP+ Optical Interfaces
ibevtModuleSw-LSQM1CGT24TSSC8             OBJECT IDENTIFIER ::= { ibevtModuleSwitchType 1971 } -- Supervisor Engine Board With 24-Port 10/100/1000BASE-T Ethernet Interface+4-Port 10GBASE-R Ethernet SFP+ Optical Interfaces
ibevtModuleSw-LSQM1MPUS06B8               OBJECT IDENTIFIER ::= { ibevtModuleSwitchType 1972 } -- Supervisor Engine Board
ibevtModuleSw-LSVM1MPUB1                  OBJECT IDENTIFIER ::= { ibevtModuleSwitchType 1973 } -- Supervisor Engine Unit
ibevtModuleSw-LSXM1TGS24QGMODHB0          OBJECT IDENTIFIER ::= { ibevtModuleSwitchType 1974 } -- 24-Port 10GBASE Ethernet Optical Interface(SFP+,LC)+4-Port 40GBASE Ethernet Optical Interface Module(QSFP+)(HB),With 1 Expansion Slot
ibevtModuleSw-LSXM1TGS24QGMODHB1          OBJECT IDENTIFIER ::= { ibevtModuleSwitchType 1975 } -- 24-Port 10GBASE Ethernet Optical Interface(SFP+,LC)+4-Port 40GBASE Ethernet Optical Interface Module(QSFP+)(HB),With 1 Expansion Slot
ibevtModuleSw-LSXM1TGS48QGHA0             OBJECT IDENTIFIER ::= { ibevtModuleSwitchType 1976 } -- 48-Port 10GBASE Ethernet Optical Interface(SFP+,LC)+4-Port 40GBASE Ethernet Optical Interface Module(QSFP+)(HA)
ibevtModuleSw-LSXM1TGS48QGHA1             OBJECT IDENTIFIER ::= { ibevtModuleSwitchType 1977 } -- 48-Port 10GBASE Ethernet Optical Interface(SFP+,LC)+4-Port 40GBASE Ethernet Optical Interface Module(QSFP+)(HA)
ibevtModuleSw-LSXM1CGC2A0                 OBJECT IDENTIFIER ::= { ibevtModuleSwitchType 1978 } -- 2-Ports 100G CFP Ethernet Optical Interface Module(CFP)
ibevtModuleSw-LSXM1CGC2A1                 OBJECT IDENTIFIER ::= { ibevtModuleSwitchType 1979 } -- 2-Ports 100G CFP Ethernet Optical Interface Module(CFP)
ibevtModuleSw-LSQM2FWDSC0                 OBJECT IDENTIFIER ::= { ibevtModuleSwitchType 1980 } -- Firewall Service Board
ibevtModuleSw-LSQM1XPT12TSFD0             OBJECT IDENTIFIER ::= { ibevtModuleSwitchType 1981 } -- 12-Port 10/1GBASE EPON OLT Optical Interface(XFP,LC)+8-Port 10GBASE-R Ethernet Optical Interface Board(SFP+,LC)
ibevtModuleSw-LSXM1QGS24HB0               OBJECT IDENTIFIER ::= { ibevtModuleSwitchType 1982 } -- 24-Port 40GBASE Ethernet Optical Interface Module(QSFP+)(HB)
ibevtModuleSw-LSXM1QGS24HB1               OBJECT IDENTIFIER ::= { ibevtModuleSwitchType 1983 } -- 24-Port 40GBASE Ethernet Optical Interface Module(QSFP+)(HB)
ibevtModuleSw-LSXM1QGS24HC0               OBJECT IDENTIFIER ::= { ibevtModuleSwitchType 1984 } -- 24-Port 40GBASE Ethernet Optical Interface Module(QSFP+)(HC)
ibevtModuleSw-LSXM1SUP01B1                OBJECT IDENTIFIER ::= { ibevtModuleSwitchType 1985 } -- Supervisor Engine Board
ibevtModuleSw-LSCM1SUP03A0                OBJECT IDENTIFIER ::= { ibevtModuleSwitchType 1986 } -- Supervisor Engine Board
ibevtModuleSw-LSCM1SUP03A0-Z              OBJECT IDENTIFIER ::= { ibevtModuleSwitchType 1987 } -- Supervisor Engine Board
ibevtModuleSw-LSCM1MPUS06A0               OBJECT IDENTIFIER ::= { ibevtModuleSwitchType 1988 } -- Supervisor Engine Board
ibevtModuleSw-LSCM1MPUS06A0-Z             OBJECT IDENTIFIER ::= { ibevtModuleSwitchType 1989 } -- Supervisor Engine Board
ibevtModuleSw-LSCM1GT48SC0                OBJECT IDENTIFIER ::= { ibevtModuleSwitchType 1990 } -- 48-Port 10/100/1000BASE-T Electrical Interface Board(RJ45)(SC)
ibevtModuleSw-LSCM1GT48SC0-Z              OBJECT IDENTIFIER ::= { ibevtModuleSwitchType 1991 } -- 48-Port 10/100/1000BASE-T Electrical Interface Board(RJ45)(SC)
ibevtModuleSw-LSCM1TGS48SE0               OBJECT IDENTIFIER ::= { ibevtModuleSwitchType 1992 } -- 48-Port 10GBASE-R Ethernet SFP+ Optical Interface Board(SE)
ibevtModuleSw-LSCM1TGS48SE0-Z             OBJECT IDENTIFIER ::= { ibevtModuleSwitchType 1993 } -- 48-Port 10GBASE-R Ethernet SFP+ Optical Interface Board(SE)
ibevtModuleSw-LSCM1QGS8CSSE0              OBJECT IDENTIFIER ::= { ibevtModuleSwitchType 1994 } -- 8-Port 40GBASE-R QSFP+ + 4-Port 100GBASE-R QSFP28 Optical Interface Board(SE)
ibevtModuleSw-LSCM1QGS8CSSE0-Z            OBJECT IDENTIFIER ::= { ibevtModuleSwitchType 1995 } -- 8-Port 40GBASE-R QSFP+ + 4-Port 100GBASE-R QSFP28 Optical Interface Board(SE)
ibevtModuleSw-LSWM2SP4P                   OBJECT IDENTIFIER ::= { ibevtModuleSwitchType 1996 } -- 4-Port 10GBASE-R Ethernet SFP+ Optical Interface Module
ibevtModuleSw-LSWM2SP4P-Z                 OBJECT IDENTIFIER ::= { ibevtModuleSwitchType 1997 } -- 4-Port 10GBASE-R Ethernet SFP+ Optical Interface Module
ibevtModuleSw-LSQM1MPUS10B0               OBJECT IDENTIFIER ::= { ibevtModuleSwitchType 1998 } -- Supervisor Engine Board
ibevtModuleSw-LSQM1MPUS10B3               OBJECT IDENTIFIER ::= { ibevtModuleSwitchType 1999 } -- Supervisor Engine Board
ibevtModuleSw-LSQM1MPUSC0                 OBJECT IDENTIFIER ::= { ibevtModuleSwitchType 2000 } -- Supervisor Engine Board
ibevtModuleSw-LSQM1MPUSC3                 OBJECT IDENTIFIER ::= { ibevtModuleSwitchType 2001 } -- Supervisor Engine Board
ibevtModuleSw-LSQM2GP24TSSC8              OBJECT IDENTIFIER ::= { ibevtModuleSwitchType 2002 } -- 24-Port 1000BASE-X Optical Interface(SFP,LC)+4-Port 10GBASE-R Ethernet Optical Interface Board(SFP+,LC)(SC)
ibevtModuleSw-LSQM2GT24TSSC8              OBJECT IDENTIFIER ::= { ibevtModuleSwitchType 2003 } -- 24-Port 10/100/1000BASE-T Electrical Interface(RJ45)+4-Port 10GBASE-R Ethernet Optical Interface Board(SFP+,LC)(SC)
ibevtModuleSw-LSXM1TGS24CGMODHD0          OBJECT IDENTIFIER ::= { ibevtModuleSwitchType 2004 } -- 24-Port 10GBASE Ethernet Optical Interface(SFP+,LC)+4-Port 100GBASE Ethernet Optical Interface Module(QSFP28)(HD),With 1 Expansion Slot
ibevtModuleSw-LSXM1TGS24CGMODHD1          OBJECT IDENTIFIER ::= { ibevtModuleSwitchType 2005 } -- 24-Port 10GBASE Ethernet Optical Interface(SFP+,LC)+4-Port 100GBASE Ethernet Optical Interface Module(QSFP28)(HD),With 1 Expansion Slot
ibevtModuleSw-LSQM1TGS16GPSA0             OBJECT IDENTIFIER ::= { ibevtModuleSwitchType 2006 } -- 24-Port 1000BASE-R Ethernet Optical Interface(SFP,LC)+16-Port 10GBASE-R Ethernet Optical Interface Board(SFP+,LC)
ibevtModuleSw-EWPXM2TGS48SG0              OBJECT IDENTIFIER ::= { ibevtModuleSwitchType 2007 } -- 48-Port 10GBASE-R Ethernet SFP+ Optical Interface Board(SG)
ibevtModuleSw-EWPXM1TGS16FD0              OBJECT IDENTIFIER ::= { ibevtModuleSwitchType 2008 } -- 16-Port 10GBASE-R Ethernet SFP+ Optical Interface Board(FD)
ibevtModuleSw-LSXM1CGQ36HF0               OBJECT IDENTIFIER ::= { ibevtModuleSwitchType 2009 } -- 36-Port 100GBASE Ethernet Optical Interface Module(QSFP28)(HF)
ibevtModuleSw-LSXM2SUPT0                  OBJECT IDENTIFIER ::= { ibevtModuleSwitchType 2010 } -- Supervisor Engine Board
ibevtModuleSw-LSXM2SUPT1                  OBJECT IDENTIFIER ::= { ibevtModuleSwitchType 2011 } -- Supervisor Engine Board
ibevtModuleSw-LSXM1SFT16E0                OBJECT IDENTIFIER ::= { ibevtModuleSwitchType 2012 } -- Switch Fabric Board
ibevtModuleSw-LSXM1SFT16E1                OBJECT IDENTIFIER ::= { ibevtModuleSwitchType 2013 } -- Switch Fabric Board
ibevtModuleSw-lsxM1CGQ36TD0               OBJECT IDENTIFIER ::= { ibevtModuleSwitchType 2014 } -- 36-Port 100GBASE Ethernet Optical Interface Board(QSFP28)
ibevtModuleSw-lsxM1CGQ36TD1               OBJECT IDENTIFIER ::= { ibevtModuleSwitchType 2015 } -- 36-Port 100GBASE Ethernet Optical Interface Board(QSFP28)
ibevtModuleSw-LSQM1TGT24FD0               OBJECT IDENTIFIER ::= { ibevtModuleSwitchType 2016 } -- 24-Port 10GBASE-T Ethernet Copper Interface Module(RJ45)(FD)
ibevtModuleSw-LSUM1TGT24FD0               OBJECT IDENTIFIER ::= { ibevtModuleSwitchType 2017 } -- 24-Port 10GBASE-T Ethernet Copper Interface Module(RJ45)(FD)
ibevtModuleSw-LSXM2SFT08E0                OBJECT IDENTIFIER ::= { ibevtModuleSwitchType 2018 } -- S12508F-AF Fabric Module,Type T(Class E)
ibevtModuleSw-LSXM2SFT08E1                OBJECT IDENTIFIER ::= { ibevtModuleSwitchType 2019 } -- S12508F-AF Fabric Module,Type T(Class E)
ibevtModuleSw-LSXM1CCP8HF0                OBJECT IDENTIFIER ::= { ibevtModuleSwitchType 2020 } -- 8-Port 200GBASE Ethernet Optical Interface Module(CFP2)(HF)
ibevtModuleSw-LSXM1CCP8HF1                OBJECT IDENTIFIER ::= { ibevtModuleSwitchType 2021 } -- 8-Port 200GBASE Ethernet Optical Interface Module(CFP2)(HF)



ibevtModuleSw-S8610-MPU                   OBJECT IDENTIFIER ::= { ibevtModuleSwitchType 2028 } -- Supervisor Engine Board
ibevtModuleSw-S8610-NET                   OBJECT IDENTIFIER ::= { ibevtModuleSwitchType 2029 } -- Switching Fabric Module
ibevtModuleSw-S86-44GF4XFSE               OBJECT IDENTIFIER ::= { ibevtModuleSwitchType 2030 } -- 44-Port GE Optical Interface(SFP,LC)+4-Port 10GE Optical Interface Board(SFP+,LC)(SE)
ibevtModuleSw-S86-48GTSE                  OBJECT IDENTIFIER ::= { ibevtModuleSwitchType 2031 } -- 48-Port 1000Base-T Gigabit Ethernet Interface Board(RJ45)(SE)
ibevtModuleSw-S86-12QFSG                  OBJECT IDENTIFIER ::= { ibevtModuleSwitchType 2032 } -- 12-Port 40GBASE-R Ethernet QSFP+ Optical Interface Board(SG)
ibevtModuleSw-S86-48XFSG                  OBJECT IDENTIFIER ::= { ibevtModuleSwitchType 2033 } -- 48-Port 10GBASE-R Ethernet SFP+ Optical Interface Board(SG)
ibevtModuleSw-LSUM1MPUS06XEC0             OBJECT IDENTIFIER ::= { ibevtModuleSwitchType 2034 } -- Supervisor Engine Board
ibevtModuleSw-LSUM1MPUS10XE0              OBJECT IDENTIFIER ::= { ibevtModuleSwitchType 2035 } -- Supervisor Engine Board
ibevtModuleSw-LSUM1MPUS10XEB0             OBJECT IDENTIFIER ::= { ibevtModuleSwitchType 2036 } -- Supervisor Engine Board
ibevtModuleSw-LSUM1FAB06XEC0              OBJECT IDENTIFIER ::= { ibevtModuleSwitchType 2037 } -- Switch Fabric Board
ibevtModuleSw-LSUM1FAB10XE0               OBJECT IDENTIFIER ::= { ibevtModuleSwitchType 2038 } -- Switch Fabric Board
ibevtModuleSw-LSUM1FAB10XEB0              OBJECT IDENTIFIER ::= { ibevtModuleSwitchType 2039 } -- Switch Fabric Board
ibevtModuleSw-LSUM1FAB08XEB0              OBJECT IDENTIFIER ::= { ibevtModuleSwitchType 2040 } -- Switch Fabric Board
ibevtModuleSw-LSUM1TGS48SH0               OBJECT IDENTIFIER ::= { ibevtModuleSwitchType 2041 } -- 48-Port 10G Ethernet Optical Interface Module(SFP+,LC)(SH)
ibevtModuleSw-LSUM1CGS8SH0                OBJECT IDENTIFIER ::= { ibevtModuleSwitchType 2042 } -- 8-Port 100G Ethernet Optical Interface Module(QSFP28)(SH)
ibevtModuleSw-LSUM1YGS24CSSH0             OBJECT IDENTIFIER ::= { ibevtModuleSwitchType 2043 } -- 24-Port 25G Ethernet Optical Interface(SFP28,LC)+4-Port 100G Ethernet Optical Interface Module(QSFP28)(SH)
ibevtModuleSw-LSUM1CGS20XSH0              OBJECT IDENTIFIER ::= { ibevtModuleSwitchType 2044 } -- 20-Port 100G Ethernet Optical Interface Module(QSFP28)(SH)
ibevtModuleSw-LSUM1CGS32XSH0              OBJECT IDENTIFIER ::= { ibevtModuleSwitchType 2045 } -- 32-Port 100G Ethernet Optical Interface Module(QSFP28)(SH)
ibevtModuleSw-LSUM1CGS8QSSH0              OBJECT IDENTIFIER ::= { ibevtModuleSwitchType 2046 } -- 8-Port 100G Ethernet Optical Interface Module(QSFP28) +8-port 40G/4-Port 100G Ethernet Optical Interface Module(QSFP28)(SH)
ibevtModuleSw-LSUM1YGS48XSH0              OBJECT IDENTIFIER ::= { ibevtModuleSwitchType 2047 } -- 48-Port 25G Ethernet Optical Interface(SFP28,LC)(SH)
ibevtModuleSw-LSXM3SUPT1                  OBJECT IDENTIFIER ::= { ibevtModuleSwitchType 2048 } -- Comware 9 Type-H Supervisor Engine Unit
ibevtModuleSw-LSXM4SUPT1                  OBJECT IDENTIFIER ::= { ibevtModuleSwitchType 2049 } -- Comware 9 Type-T Supervisor Engine Unit
ibevtModuleSw-LSQM2GP24TSSA0-Z            OBJECT IDENTIFIER ::= { ibevtModuleSwitchType 2050 } -- 24-Port GE Optical Interface(SFP,LC)+4-Port 10GE Optical Interface Board(SFP+,LC)(SA)
ibevtModuleSw-LSQM2GT48SA0-Z              OBJECT IDENTIFIER ::= { ibevtModuleSwitchType 2051 } -- 48-Port 1000Base-T Gigabit Ethernet Interface Board(RJ45)(SA)
ibevtModuleSw-LSQM2GP48SA0-Z              OBJECT IDENTIFIER ::= { ibevtModuleSwitchType 2052 } -- 48-Port 1000BASE-X Ethernet Optical Interface Board(SFP,LC)(SA)
ibevtModuleSw-LSUM2TGS48SG0-Z             OBJECT IDENTIFIER ::= { ibevtModuleSwitchType 2053 } -- 48-Port 10GBASE-R Ethernet SFP+ Optical Interface Board(SG)
ibevtModuleSw-LSUM2QGS12SG0-Z             OBJECT IDENTIFIER ::= { ibevtModuleSwitchType 2054 } -- 12-Port 40GBASE-R Ethernet QSFP+ Optical Interface Board(SG)
ibevtModuleSw-LSUM2TGS32QSSG0-Z           OBJECT IDENTIFIER ::= { ibevtModuleSwitchType 2055 } -- 32-Port 10GBASE-R Ethernet Optical Interface(SFP+,LC)+4-Port 40GBASE-R Ethernet Optical Interface Board(QSFP+,LC)(SG)
ibevtModuleSw-LSUM1TGS48RSH0              OBJECT IDENTIFIER ::= { ibevtModuleSwitchType 2056 } -- 48-Port 10GBASE-R Ethernet Optical Interface Module(SFP+,LC)(SH)
ibevtModuleSw-LSUM1MPUS06XEB0             OBJECT IDENTIFIER ::= { ibevtModuleSwitchType 2057 } -- Supervisor Engine Board
ibevtModuleSw-LSUM1MPUS10XEA0             OBJECT IDENTIFIER ::= { ibevtModuleSwitchType 2058 } -- Supervisor Engine Board
ibevtModuleSw-LSUM1FAB06XEB0              OBJECT IDENTIFIER ::= { ibevtModuleSwitchType 2059 } -- Switch Fabric Board
ibevtModuleSw-LSUM1FAB10XEA0              OBJECT IDENTIFIER ::= { ibevtModuleSwitchType 2060 } -- Switch Fabric Board
ibevtModuleSw-EWPXM1WCMX100               OBJECT IDENTIFIER ::= { ibevtModuleSwitchType 2061 } -- Access Controller Service Board
ibevtModuleSw-LSQM1WBCZ720X               OBJECT IDENTIFIER ::= { ibevtModuleSwitchType 2062 } -- Access Controller Service Board
ibevtModuleSw-LSUM1WBCZ720XRT             OBJECT IDENTIFIER ::= { ibevtModuleSwitchType 2063 } -- Access Controller Service Board
ibevtModuleSw-LSXM1CGQ8TD1                OBJECT IDENTIFIER ::= { ibevtModuleSwitchType 2064 } -- 8-Port 100GBASE  Ethernet Optical Interface Board(QSFP28)
ibevtModuleSw-LSXM1CGQ12TD1               OBJECT IDENTIFIER ::= { ibevtModuleSwitchType 2065 } -- 12-Port 100GBASE  Ethernet Optical Interface Board(QSFP28)
ibevtModuleSw-LSXM1CGQ18TD1               OBJECT IDENTIFIER ::= { ibevtModuleSwitchType 2066 } -- 18-Port 100GBASE  Ethernet Optical Interface Board(QSFP28)
ibevtModuleSw-LSXM1QGS24C6TD1             OBJECT IDENTIFIER ::= { ibevtModuleSwitchType 2067 } -- 24-Port 40GBASE Ethernet Optical Interface Module (QSFP+) + 6-Port 100GBASE (QSFP28)
ibevtModuleSw-LSXM1QGS36TD1               OBJECT IDENTIFIER ::= { ibevtModuleSwitchType 2068 } -- 36-Port 40GBASE Ethernet Optical Interface Module(QSFP+)
ibevtModuleSw-LSXM1QGS48TD1               OBJECT IDENTIFIER ::= { ibevtModuleSwitchType 2069 } -- 48-Port 40GBASE Ethernet Optical Interface Module(QSFP+)
ibevtModuleSw-LSXM1TGS48C4TD1             OBJECT IDENTIFIER ::= { ibevtModuleSwitchType 2070 } -- 48-Port 10GBASE Ethernet Optical Interface(SFP+,LC)+4-Port 100GBASE Ethernet Optical Interface Module(QSFP28)
ibevtModuleSw-LSXM1GP48TD1                OBJECT IDENTIFIER ::= { ibevtModuleSwitchType 2071 } -- 48-Port GE BASE Ethernet Optical Interface Module(SFP,LC))
ibevtModuleSw-LSXM1TGS48TD1               OBJECT IDENTIFIER ::= { ibevtModuleSwitchType 2072 } -- 48-Port 10G BASE Ethernet Optical Interface Module(SFP+,LC))




ibevtModuleSw-LSWM124TG2H1               OBJECT IDENTIFIER ::= { ibevtModuleSwitchType 2076 }
ibevtModuleSw-LSQM2FWDSC8                OBJECT IDENTIFIER ::= { ibevtModuleSwitchType 2077 }

ibevtModuleSw-IM-MSEX-B                  OBJECT IDENTIFIER ::= { ibevtModuleSwitchType 2080 }  -- Service Processing Unit(IM-MSEX-B)
ibevtModuleSw-IM-MSEX-B-IM-SP-B          OBJECT IDENTIFIER ::= { ibevtModuleSwitchType 2081 }  -- Service Processing Unit + Universal Line Processing Interface Card(IM-MSEX-B-IM-SP-B)
ibevtModuleSw-LSUM1MPUS06XEC0-Z          OBJECT IDENTIFIER ::= { ibevtModuleSwitchType 2082 }
ibevtModuleSw-LSUM1CGS8SH0-Z             OBJECT IDENTIFIER ::= { ibevtModuleSwitchType 2083 }
ibevtModuleSw-LSUM1SUPXD0-Z              OBJECT IDENTIFIER ::= { ibevtModuleSwitchType 2084 }
ibevtModuleSw-LSUM1FAB08XE0-Z            OBJECT IDENTIFIER ::= { ibevtModuleSwitchType 2085 }
ibevtModuleSw-LSUM1CGS20XSH0-Z           OBJECT IDENTIFIER ::= { ibevtModuleSwitchType 2086 }
ibevtModuleSw-LSUM1FAB06XEC0-Z           OBJECT IDENTIFIER ::= { ibevtModuleSwitchType 2087 }
ibevtModuleSw-LSUM1CQGS32SF0-Z           OBJECT IDENTIFIER ::= { ibevtModuleSwitchType 2088 }
ibevtModuleSw-LSXM1FAB10XE3              OBJECT IDENTIFIER ::= { ibevtModuleSwitchType 2089 }
ibevtModuleSw-LSXM1FAB08XE3              OBJECT IDENTIFIER ::= { ibevtModuleSwitchType 2090 }
ibevtModuleSw-LSXM1YGS48XSH3             OBJECT IDENTIFIER ::= { ibevtModuleSwitchType 2091 }
ibevtModuleSw-LSXM1YGS24CSSH3            OBJECT IDENTIFIER ::= { ibevtModuleSwitchType 2092 }
ibevtModuleSw-LSXM1CGS8QSSH3             OBJECT IDENTIFIER ::= { ibevtModuleSwitchType 2093 }
ibevtModuleSw-LSXM1TGS48SH3              OBJECT IDENTIFIER ::= { ibevtModuleSwitchType 2094 }
ibevtModuleSw-LSXM1MPUS10XE3             OBJECT IDENTIFIER ::= { ibevtModuleSwitchType 2095 }
ibevtModuleSw-LSXM1FAB06XEC3             OBJECT IDENTIFIER ::= { ibevtModuleSwitchType 2096 }
ibevtModuleSw-LSXM1MPUS06XEC3            OBJECT IDENTIFIER ::= { ibevtModuleSwitchType 2097 }
ibevtModuleSw-LSXM1CGS8SH3               OBJECT IDENTIFIER ::= { ibevtModuleSwitchType 2098 }
ibevtModuleSw-LSXM1SUPXD3                OBJECT IDENTIFIER ::= { ibevtModuleSwitchType 2099 }
ibevtModuleSw-LSXM1CGS20XSH3             OBJECT IDENTIFIER ::= { ibevtModuleSwitchType 2100 }
ibevtModuleSw-LSUM1GP48FD0-Z             OBJECT IDENTIFIER ::= { ibevtModuleSwitchType 2101 }
ibevtModuleSw-LSQM1TGS48RFE0-Z           OBJECT IDENTIFIER ::= { ibevtModuleSwitchType 2102 }
ibevtModuleSw-LSXM1CGS32XSH3             OBJECT IDENTIFIER ::= { ibevtModuleSwitchType 2103 }
ibevtModuleSw-LSQM2GP40TS8FD0            OBJECT IDENTIFIER ::= { ibevtModuleSwitchType 2104 }
ibevtModuleSw-LSUM1SUPXES0               OBJECT IDENTIFIER ::= { ibevtModuleSwitchType 2105 }
ibevtModuleSw-LSQM2SUPB0                 OBJECT IDENTIFIER ::= { ibevtModuleSwitchType 2106 }
ibevtModuleSw-LSUM2GP40TS8FD0            OBJECT IDENTIFIER ::= { ibevtModuleSwitchType 2107 }
ibevtModuleSw-LSXM1YGS48XXSH3            OBJECT IDENTIFIER ::= { ibevtModuleSwitchType 2108 }
ibevtModuleSw-LSXM2SFT08E2               OBJECT IDENTIFIER ::= { ibevtModuleSwitchType 2109 }
ibevtModuleSw-LSXM1TGS48TD2              OBJECT IDENTIFIER ::= { ibevtModuleSwitchType 2110 }
ibevtModuleSw-LSXM1CGQ36TD2              OBJECT IDENTIFIER ::= { ibevtModuleSwitchType 2111 }
ibevtModuleSw-RX-NIC-LGQ4L               OBJECT IDENTIFIER ::= { ibevtModuleSwitchType 2112 }  -- 4-port 50G Ethernet Optical Interface Card(QSFP28,LC)(RX-NIC)
ibevtModuleSw-LSXM1CDQ24KB1              OBJECT IDENTIFIER ::= { ibevtModuleSwitchType 2113 }
ibevtModuleSw-LSXM1SUP02L1               OBJECT IDENTIFIER ::= { ibevtModuleSwitchType 2114 }
ibevtModuleSw-LSXM1CGQ48KB1              OBJECT IDENTIFIER ::= { ibevtModuleSwitchType 2115 }
ibevtModuleSw-LSXM1SFK08F1               OBJECT IDENTIFIER ::= { ibevtModuleSwitchType 2116 }
ibevtModuleSw-CSPEX-1214X                OBJECT IDENTIFIER ::= { ibevtModuleSwitchType 2117 }
ibevtModuleSw-MIC-CQ1L1                  OBJECT IDENTIFIER ::= { ibevtModuleSwitchType 2118 }  -- 1-port 100G Ethernet Optical Interface Card(QSFP28)
ibevtModuleSw-DS-3E7600-16X-SCB          OBJECT IDENTIFIER ::= { ibevtModuleSwitchType 2119 }
ibevtModuleSw-DS-3E12508-MPU             OBJECT IDENTIFIER ::= { ibevtModuleSwitchType 2120 }
ibevtModuleSw-DS-3E12500-7610-48T-SE     OBJECT IDENTIFIER ::= { ibevtModuleSwitchType 2121 }
ibevtModuleSw-DS-3E7603-MPU              OBJECT IDENTIFIER ::= { ibevtModuleSwitchType 2122 }
ibevtModuleSw-DS-3E12500-7610-16X-SF     OBJECT IDENTIFIER ::= { ibevtModuleSwitchType 2123 }
ibevtModuleSw-DS-3E12500-24T20F4X-SE     OBJECT IDENTIFIER ::= { ibevtModuleSwitchType 2124 }
ibevtModuleSw-DS-3E12500-12Q-SG          OBJECT IDENTIFIER ::= { ibevtModuleSwitchType 2125 }
ibevtModuleSw-DS-3E12500-48X-SG          OBJECT IDENTIFIER ::= { ibevtModuleSwitchType 2126 }
ibevtModuleSw-DS-3E12500-7610-32X4QX-SF  OBJECT IDENTIFIER ::= { ibevtModuleSwitchType 2127 }
ibevtModuleSw-DS-3E12500-7610-44F4X-SE   OBJECT IDENTIFIER ::= { ibevtModuleSwitchType 2128 }
ibevtModuleSw-DS-3E12508-CLOS            OBJECT IDENTIFIER ::= { ibevtModuleSwitchType 2129 }
ibevtModuleSw-LSXM2SUPT2                 OBJECT IDENTIFIER ::= { ibevtModuleSwitchType 2130 }
ibevtModuleSw-CSR05SRP1P3A               OBJECT IDENTIFIER ::= { ibevtModuleSwitchType 2131 }  -- CR16000-FA Main Processing Unit(1P3A)
ibevtModuleSw-CSFC-08E1A                 OBJECT IDENTIFIER ::= { ibevtModuleSwitchType 2132 }  -- CR16010H-FA Fabric Module(E Type)
ibevtModuleSw-CSFC-16EA                  OBJECT IDENTIFIER ::= { ibevtModuleSwitchType 2133 }  -- CR16018-FA Fabric Module(E Type)
ibevtModuleSw-CSPEX-1602XA               OBJECT IDENTIFIER ::= { ibevtModuleSwitchType 2134 }  -- Service Processing Unit(1602XA)
ibevtModuleSw-CEPC-CP4RXA                OBJECT IDENTIFIER ::= { ibevtModuleSwitchType 2135 }  -- 4-port 100GBASE Ethernet Optical Interface Line Processing Unit A(CFP2)
ibevtModuleSw-CSPEX-1504XA               OBJECT IDENTIFIER ::= { ibevtModuleSwitchType 2136 }  -- Service Processing Unit(1504XA)
ibevtModuleSw-CSPEX-1804XA               OBJECT IDENTIFIER ::= { ibevtModuleSwitchType 2137 }  -- Service Processing Unit(1804XA)
ibevtModuleSw-MIC-GP10LA                 OBJECT IDENTIFIER ::= { ibevtModuleSwitchType 2138 }  -- 10-port 1000BASE-X Ethernet Optical Interface Card A(SFP,LC)
ibevtModuleSw-MIC-GT20LA                 OBJECT IDENTIFIER ::= { ibevtModuleSwitchType 2139 }  -- 20-port 1000BASE-X Ethernet Copper Interface Card A(RJ45)
ibevtModuleSw-MIC-XP20LA                 OBJECT IDENTIFIER ::= { ibevtModuleSwitchType 2140 }  -- 20-port 10GBASE-R/W Ethernet Optical Interface Card A(SFP+,LC)

ibevtModuleSw-LSDM1QGS12SE0-Z            OBJECT IDENTIFIER ::= { ibevtModuleSwitchType 2142 }
ibevtModuleSw-LSDM1TGS48SE0-Z            OBJECT IDENTIFIER ::= { ibevtModuleSwitchType 2143 }
ibevtModuleSw-LSDM1SUPA0-Z               OBJECT IDENTIFIER ::= { ibevtModuleSwitchType 2144 }
ibevtModuleSw-LSDM1FAB08D0-Z             OBJECT IDENTIFIER ::= { ibevtModuleSwitchType 2145 }
ibevtModuleSw-LSDM1GT24GPSE0-Z           OBJECT IDENTIFIER ::= { ibevtModuleSwitchType 2146 }
ibevtModuleSw-LSXM1CGQ18TD2              OBJECT IDENTIFIER ::= { ibevtModuleSwitchType 2147 }
ibevtModuleSw-LSXM1QGS36TD2              OBJECT IDENTIFIER ::= { ibevtModuleSwitchType 2148 }
ibevtModuleSw-RP-S-G                     OBJECT IDENTIFIER ::= { ibevtModuleSwitchType 2149 }
ibevtModuleSw-MOD20-G                    OBJECT IDENTIFIER ::= { ibevtModuleSwitchType 2150 }
ibevtModuleSw-MPA-PSP4L-G                OBJECT IDENTIFIER ::= { ibevtModuleSwitchType 2151 }
ibevtModuleSw-MPA-TCP8L-G                OBJECT IDENTIFIER ::= { ibevtModuleSwitchType 2152 }
ibevtModuleSw-MPA-ET16L-G                OBJECT IDENTIFIER ::= { ibevtModuleSwitchType 2153 }
ibevtModuleSw-MPA-GP10L-G                OBJECT IDENTIFIER ::= { ibevtModuleSwitchType 2154 }
ibevtModuleSw-MPA-XP4L-G                 OBJECT IDENTIFIER ::= { ibevtModuleSwitchType 2155 }
ibevtModuleSw-LSXM1SFH04DR1              OBJECT IDENTIFIER ::= { ibevtModuleSwitchType 2156 }
ibevtModuleSw-LSXM1SFH08CR1              OBJECT IDENTIFIER ::= { ibevtModuleSwitchType 2157 }
ibevtModuleSw-LSXM1SFH08DR1              OBJECT IDENTIFIER ::= { ibevtModuleSwitchType 2158 }
ibevtModuleSw-LSXM1SFH16CR1              OBJECT IDENTIFIER ::= { ibevtModuleSwitchType 2159 }
ibevtModuleSw-LSXM1SFH16ER1              OBJECT IDENTIFIER ::= { ibevtModuleSwitchType 2160 }
ibevtModuleSw-LSXM1TGS48HFR1             OBJECT IDENTIFIER ::= { ibevtModuleSwitchType 2161 }
ibevtModuleSw-LSXM1CGQ18QGHFR1           OBJECT IDENTIFIER ::= { ibevtModuleSwitchType 2162 }
ibevtModuleSw-LSXM1SUP04TR1              OBJECT IDENTIFIER ::= { ibevtModuleSwitchType 2163 }
ibevtModuleSw-LSXM1CGQ36HBR1             OBJECT IDENTIFIER ::= { ibevtModuleSwitchType 2164 }
ibevtModuleSw-LSXM1CGQ36HFR1             OBJECT IDENTIFIER ::= { ibevtModuleSwitchType 2165 }
ibevtModuleSw-LSXM1CGQ6QGHFR1            OBJECT IDENTIFIER ::= { ibevtModuleSwitchType 2166 }
ibevtModuleSw-LSXM1TGS48HBR1             OBJECT IDENTIFIER ::= { ibevtModuleSwitchType 2167 }
ibevtModuleSw-LSXM1CGQ18QGHBR1           OBJECT IDENTIFIER ::= { ibevtModuleSwitchType 2168 }
ibevtModuleSw-LSXM1SUPER1                OBJECT IDENTIFIER ::= { ibevtModuleSwitchType 2169 }
ibevtModuleSw-LSQM1SDNB0                 OBJECT IDENTIFIER ::= { ibevtModuleSwitchType 2170 }  -- SDN-engine Blade
ibevtModuleSw-LSUM1SDNB0                 OBJECT IDENTIFIER ::= { ibevtModuleSwitchType 2171 }  -- SDN-engine Blade
ibevtModuleSw-LSQM1EPSB0                 OBJECT IDENTIFIER ::= { ibevtModuleSwitchType 2172 }  -- EPS-engine Blade
ibevtModuleSw-LSUM1EPSB0                 OBJECT IDENTIFIER ::= { ibevtModuleSwitchType 2173 }  -- EPS-engine Blade
ibevtModuleSw-LSXM2TGS48HB2              OBJECT IDENTIFIER ::= { ibevtModuleSwitchType 2174 }
ibevtModuleSw-LSXM2CGQ18QGHB2            OBJECT IDENTIFIER ::= { ibevtModuleSwitchType 2175 }
ibevtModuleSw-LSUM1CGS8SH3               OBJECT IDENTIFIER ::= { ibevtModuleSwitchType 2176 }
ibevtModuleSw-LSUM1GT48FC3               OBJECT IDENTIFIER ::= { ibevtModuleSwitchType 2177 }
ibevtModuleSw-LSUM1FAB10XEA3             OBJECT IDENTIFIER ::= { ibevtModuleSwitchType 2178 }
ibevtModuleSw-LSUM1TGS48SH3              OBJECT IDENTIFIER ::= { ibevtModuleSwitchType 2179 }
ibevtModuleSw-LSUM1MPUS10XE3             OBJECT IDENTIFIER ::= { ibevtModuleSwitchType 2180 }
ibevtModuleSw-LSUM1GP48FC3               OBJECT IDENTIFIER ::= { ibevtModuleSwitchType 2181 }
ibevtModuleSw-LSQM1TGS16FD0-Z            OBJECT IDENTIFIER ::= { ibevtModuleSwitchType 2182 }
ibevtModuleSw-LSQM2SUPA0-Z               OBJECT IDENTIFIER ::= { ibevtModuleSwitchType 2183 }
ibevtModuleSw-LSUM1TGS16FD0-Z            OBJECT IDENTIFIER ::= { ibevtModuleSwitchType 2184 }
ibevtModuleSw-LSWM2FPGAB                 OBJECT IDENTIFIER ::= { ibevtModuleSwitchType 2185 }
ibevtModuleSw-LSWM2EC                    OBJECT IDENTIFIER ::= { ibevtModuleSwitchType 2186 }  -- EScaner
ibevtModuleSw-LSWM2FPGA                  OBJECT IDENTIFIER ::= { ibevtModuleSwitchType 2187 }
ibevtModuleSw-LSWM2ZSP4P                 OBJECT IDENTIFIER ::= { ibevtModuleSwitchType 2188 }
ibevtModuleSw-LSXM1CGQ8TD2               OBJECT IDENTIFIER ::= { ibevtModuleSwitchType 2189 }
ibevtModuleSw-LSXM1TGS48C4TD2            OBJECT IDENTIFIER ::= { ibevtModuleSwitchType 2190 }
ibevtModuleSw-LSXM1QGS24C6TD2            OBJECT IDENTIFIER ::= { ibevtModuleSwitchType 2191 }
ibevtModuleSw-LSCM1MPUS06A8              OBJECT IDENTIFIER ::= { ibevtModuleSwitchType 2192 }
ibevtModuleSw-LSCM1TGS48SC8              OBJECT IDENTIFIER ::= { ibevtModuleSwitchType 2193 }
ibevtModuleSw-LSQM1MPUS06S0              OBJECT IDENTIFIER ::= { ibevtModuleSwitchType 2194 }
ibevtModuleSw-LSQM1SRP4Y06A0             OBJECT IDENTIFIER ::= { ibevtModuleSwitchType 2195 }
ibevtModuleSw-S76-16XFSF-E               OBJECT IDENTIFIER ::= { ibevtModuleSwitchType 2196 }
ibevtModuleSw-S7603-MPU                  OBJECT IDENTIFIER ::= { ibevtModuleSwitchType 2197 }
ibevtModuleSw-LSCM2MPUS06AS8             OBJECT IDENTIFIER ::= { ibevtModuleSwitchType 2198 }  -- Supervisor Engine Board
ibevtModuleSw-LSCM2CGT24TSSC8            OBJECT IDENTIFIER ::= { ibevtModuleSwitchType 2199 }  -- Supervisor Engine Board With 24-Port 10/100/1000BASE-T Ethernet Interface+4-Port 10GBASE-R Ethernet SFP+ Optical Interfaces
ibevtModuleSw-LSCM2CGP24TSSC8            OBJECT IDENTIFIER ::= { ibevtModuleSwitchType 2200 }  -- Supervisor Engine Board With 24-Port 1000BASE-X Ethernet SFP Optical Interface+4-Port 10GBASE-R Ethernet SFP+ Optical Interfaces
ibevtModuleSw-LSCM2CTGS12GTSC8           OBJECT IDENTIFIER ::= { ibevtModuleSwitchType 2201 }  -- Supervisor Engine Board With 16-Port 10/100/1000BASE-T Ethernet Interface+12-Port 10GBASE-R Ethernet SFP+ Optical Interfaces
ibevtModuleSw-LSCM2CTGS12GPSC8           OBJECT IDENTIFIER ::= { ibevtModuleSwitchType 2202 }  -- Supervisor Engine Board With 16-Port 1000BASE-X Ethernet SFP Optical Interface+12-Port 10GBASE-R Ethernet SFP+ Optical Interfaces
ibevtModuleSw-LSCM2GT24GPTSSC8           OBJECT IDENTIFIER ::= { ibevtModuleSwitchType 2203 }  -- 24-Port 10/100/1000BASE-T Ethernet Interface Board(RJ45)+20-Port 1000BASE-X Ethernet SFP Optical Interface(SFP,LC)+4-Port 10GBASE-R Optical Interface Board(SFP+,LC)(SC)
ibevtModuleSw-LSCM2GT24GPSC8             OBJECT IDENTIFIER ::= { ibevtModuleSwitchType 2204 }  -- 24-Port 10/100/1000BASE-T Ethernet Interface Board(RJ45)+8-Port 1000BASE-X Ethernet SFP Optical Interface(SFP,LC)(SC)
ibevtModuleSw-LSCM2GP24GTSC8             OBJECT IDENTIFIER ::= { ibevtModuleSwitchType 2205 }  -- 8-Port 10/100/1000BASE-T Ethernet Interface Board(RJ45)+24-Port 1000BASE-X Ethernet SFP Optical Interface(SFP,LC)(SC)
ibevtModuleSw-LSCM2GT48SC8               OBJECT IDENTIFIER ::= { ibevtModuleSwitchType 2206 }  -- 48-Port 10/100/1000BASE-T Ethernet Interface Board(RJ45)(SC)
ibevtModuleSw-LSCM2GP48SC8               OBJECT IDENTIFIER ::= { ibevtModuleSwitchType 2207 }  -- 48-Port 1000BASE-X Ethernet Optical Interface Board(SFP,LC)
ibevtModuleSw-LSCM2TGS16GPSC8            OBJECT IDENTIFIER ::= { ibevtModuleSwitchType 2208 }  -- 24-Port 1000BASE-R Ethernet Optical Interface(SFP,LC)+16-Port 10GBASE-R Ethernet Optical Interface Board(SFP+,LC)

ibevtModuleSw-LSXM2SFH16CR1              OBJECT IDENTIFIER ::= { ibevtModuleSwitchType 2209 }  -- Fabric Module,Type H(Class C)
ibevtModuleSw-LSXM1SEERBXC2              OBJECT IDENTIFIER ::= { ibevtModuleSwitchType 2210 }
ibevtModuleSw-LSXM1SEERBG2               OBJECT IDENTIFIER ::= { ibevtModuleSwitchType 2211 }
ibevtModuleSw-LSXM1SEERBXD2              OBJECT IDENTIFIER ::= { ibevtModuleSwitchType 2212 }
ibevtModuleSw-LSXM1SFK08FR1              OBJECT IDENTIFIER ::= { ibevtModuleSwitchType 2213 }
ibevtModuleSw-LSXM1CDQ24KBR1             OBJECT IDENTIFIER ::= { ibevtModuleSwitchType 2214 }
ibevtModuleSw-LSXM1SUP02LR1              OBJECT IDENTIFIER ::= { ibevtModuleSwitchType 2215 }
ibevtModuleSw-LSXM1CGQ48KBR1             OBJECT IDENTIFIER ::= { ibevtModuleSwitchType 2216 }
ibevtModuleSw-LSXM1CGQ36HC0              OBJECT IDENTIFIER ::= { ibevtModuleSwitchType 2217 }
ibevtModuleSw-LSXM1TGS48TE2              OBJECT IDENTIFIER ::= { ibevtModuleSwitchType 2218 }
ibevtModuleSw-LSXM1CGQ36TE2              OBJECT IDENTIFIER ::= { ibevtModuleSwitchType 2219 }
ibevtModuleSw-LSXM1SFT16F1               OBJECT IDENTIFIER ::= { ibevtModuleSwitchType 2220 }
ibevtModuleSw-LSXM1CGQ18TE2              OBJECT IDENTIFIER ::= { ibevtModuleSwitchType 2221 }
ibevtModuleSw-LSXM1CGQ8TE2               OBJECT IDENTIFIER ::= { ibevtModuleSwitchType 2222 }
ibevtModuleSw-LSWM116H                   OBJECT IDENTIFIER ::= { ibevtModuleSwitchType 2223 }
ibevtModuleSw-LSWM1M4CD                  OBJECT IDENTIFIER ::= { ibevtModuleSwitchType 2224 }
ibevtModuleSw-LSXM1QGS36TE2              OBJECT IDENTIFIER ::= { ibevtModuleSwitchType 2225 }
ibevtModuleSw-LSXM1SFT16F2               OBJECT IDENTIFIER ::= { ibevtModuleSwitchType 2226 }
ibevtModuleSw-CSPEX-1812X-E              OBJECT IDENTIFIER ::= { ibevtModuleSwitchType 2227 }  -- Service Processing Unit(1812X-E)
ibevtModuleSw-MOD20-A3                   OBJECT IDENTIFIER ::= { ibevtModuleSwitchType 2228 }  -- R9900-S-G,SR0MZLF1DQM1,Service Processing Unit(MOD20-G),Domestic&Overseas Version
ibevtModuleSw-RP-S-G-A3                  OBJECT IDENTIFIER ::= { ibevtModuleSwitchType 2229 }  -- R9900-S-G,SR0MZSRP1A4,Main Processing Unit,Domestic Version
ibevtModuleSw-LSXM1SFT16EA1              OBJECT IDENTIFIER ::= { ibevtModuleSwitchType 2230 }  -- Switch Fabric Board
ibevtModuleSw-RP1-S-G                    OBJECT IDENTIFIER ::= { ibevtModuleSwitchType 2231 }  -- R9900-S-G,SR0MZSRP1A3A,Main Processing Unit(S Type),Domestic&Overseas Version
ibevtModuleSw-MOD21-G                    OBJECT IDENTIFIER ::= { ibevtModuleSwitchType 2232 }  -- R9900-S1-G,SR0MZLF1DQM1,Service Processing Unit(MOD21-G),Domestic&Overseas Version
ibevtModuleSw-LSXM1SUPKR1                OBJECT IDENTIFIER ::= { ibevtModuleSwitchType 2233 }  -- Supervisor Engine Module
ibevtModuleSw-LSXM1CDQ36KBR1             OBJECT IDENTIFIER ::= { ibevtModuleSwitchType 2234 }  -- 36-Port 400GBASE Ethernet Optical Interface Module(QSFP-DD)(KB)
ibevtModuleSw-LSXM1CMUR1                 OBJECT IDENTIFIER ::= { ibevtModuleSwitchType 2235 }  -- Board Monitor Unit
ibevtModuleSw-LSXM1SFK16GR1              OBJECT IDENTIFIER ::= { ibevtModuleSwitchType 2236 }  -- Switch Fabric Board,Type K(Class G)
ibevtModuleSw-CSR05SRP1R3                OBJECT IDENTIFIER ::= { ibevtModuleSwitchType 2237 }  -- CR16000-F,CSR05SRP1R3,Main Processing Unit(1R3)
ibevtModuleSw-MIC-TCP8L                  OBJECT IDENTIFIER ::= { ibevtModuleSwitchType 2238 }  -- SR8800-X, SR0MDTCP8LA1,8-port OC-3c/OC-12c POS Optical Interface Card(SFP,LC),Domestic&Overseas Version
ibevtModuleSw-MIC-PSP4L                  OBJECT IDENTIFIER ::= { ibevtModuleSwitchType 2239 }  -- SR8800-X , SR0MDPSP4LA1,4-port OC-48c/STM-16c POS Optical Interface Card(SFP,LC),Domestic&Overseas Version



ibevtModuleSw-LSUM1MPU06B8               OBJECT IDENTIFIER ::= { ibevtModuleSwitchType 2240 }  -- Supervisor Engine Board
ibevtModuleSw-LSUM1MPU10C8               OBJECT IDENTIFIER ::= { ibevtModuleSwitchType 2241 }  -- Supervisor Engine Board
ibevtModuleSw-LSUM1FAB06C8               OBJECT IDENTIFIER ::= { ibevtModuleSwitchType 2242 }  -- Switching Fabric Module
ibevtModuleSw-LSUM1FAB10C8               OBJECT IDENTIFIER ::= { ibevtModuleSwitchType 2243 }  -- Switching Fabric Module
ibevtModuleSw-LSUM1MPU10A8               OBJECT IDENTIFIER ::= { ibevtModuleSwitchType 2244 }  -- Supervisor Engine Board
ibevtModuleSw-LSUM1FAB10A8               OBJECT IDENTIFIER ::= { ibevtModuleSwitchType 2245 }  -- Switching Fabric Module
ibevtModuleSw-LSUM1TGS16FD8              OBJECT IDENTIFIER ::= { ibevtModuleSwitchType 2246 }  -- 16-Port 10GBASE-R Ethernet SFP+ Optical Interface Board(FD)
ibevtModuleSw-LSUM1GP48FD8               OBJECT IDENTIFIER ::= { ibevtModuleSwitchType 2247 }  -- 48-Port 1000BASE-X Optical Interface Board(SFP,LC)
ibevtModuleSw-LSUM1GT48FD8               OBJECT IDENTIFIER ::= { ibevtModuleSwitchType 2248 }  -- 48-Port 10/100/1000BASE-T Electrical Interface Board(RJ45)
ibevtModuleSw-LSUM1GP40TS8FD8            OBJECT IDENTIFIER ::= { ibevtModuleSwitchType 2249 }  -- 40-Port 1000BASE-X Optical Interface(SFP,LC)+8-Port 10GBASE-R Ethernet Optical Interface Board(SFP+,LC)
ibevtModuleSw-LSUM1TGS48RSH8             OBJECT IDENTIFIER ::= { ibevtModuleSwitchType 2250 }  -- 48-Port 10GBASE-R Ethernet Optical Interface Module(SFP+,LC)(SH)
ibevtModuleSw-LSDM1GP48SE0-Z             OBJECT IDENTIFIER ::= { ibevtModuleSwitchType 2251 }  -- 48-Port 1000BASE-X Ethernet Optical Interface Board(SFP,LC)
ibevtModuleSw-LSDM1GT48SE0-Z             OBJECT IDENTIFIER ::= { ibevtModuleSwitchType 2252 }  -- 48-Port 10/100/1000BASE-T Ethernet Interface Board(RJ45)(SE)
ibevtModuleSw-LSDM1CGS8SE0-Z             OBJECT IDENTIFIER ::= { ibevtModuleSwitchType 2253 }  -- 8-Port 100GBASE-R Ethernet Optical Interface Board(QSFP28,LC)
ibevtModuleSw-LSXM1SUP04T2               OBJECT IDENTIFIER ::= { ibevtModuleSwitchType 2254 }  -- Supervisor Engine Board
ibevtModuleSw-LSXM1SFT04F2               OBJECT IDENTIFIER ::= { ibevtModuleSwitchType 2255 }  -- Switch Fabric Board
ibevtModuleSw-LSXM1SFT08F2               OBJECT IDENTIFIER ::= { ibevtModuleSwitchType 2256 }  -- Switch Fabric Board
ibevtModuleSw-RX-NIC-CQ2LF-E             OBJECT IDENTIFIER ::= { ibevtModuleSwitchType 2257 }  -- 2-port 100G Flexible Ethernet Optical Interface Card(QSFP28,LC)(RX-NIC)
ibevtModuleSw-LSUM1TGS24FD8              OBJECT IDENTIFIER ::= { ibevtModuleSwitchType 2258 }  -- 24-Port 10GBASE-R Ethernet Optical Interface Board(SFP+,LC)
ibevtModuleSw-RX-SPE400-E                OBJECT IDENTIFIER ::= { ibevtModuleSwitchType 2259 }  -- Service Processing Unit(SPE400-E)
ibevtModuleSw-LSXM1SFK08GR1              OBJECT IDENTIFIER ::= { ibevtModuleSwitchType 2260 }  -- Switch Fabric Board,Type K(Class G)
ibevtModuleSw-RX-SFC-16T1                OBJECT IDENTIFIER ::= { ibevtModuleSwitchType 2261 }  -- 1Tbps Fabric Module(16)
ibevtModuleSw-LSCM3SUP03A0-Z             OBJECT IDENTIFIER ::= { ibevtModuleSwitchType 2262 }  -- Supervisor Engine Board
ibevtModuleSw-LSCM3MPUS06A0-Z            OBJECT IDENTIFIER ::= { ibevtModuleSwitchType 2263 }  -- Supervisor Engine Board
ibevtModuleSw-LSCM3GT48SC0-Z             OBJECT IDENTIFIER ::= { ibevtModuleSwitchType 2264 }  -- 48-Port 10/100/1000BASE-T Electrical Interface Board(RJ45)(SC)
ibevtModuleSw-LSCM3TGS48SE0-Z            OBJECT IDENTIFIER ::= { ibevtModuleSwitchType 2265 }  -- 48-Port 10GBASE-R Ethernet SFP+ Optical Interface Board(SE)
ibevtModuleSw-LSCM3QGS8CSSE0-Z           OBJECT IDENTIFIER ::= { ibevtModuleSwitchType 2266 }  -- 8-Port 40GBASE-R QSFP+ + 4-Port 100GBASE-R QSFP28 Optical Interface Board(SE)
ibevtModuleSw-LSDM3QGS12SE0-Z            OBJECT IDENTIFIER ::= { ibevtModuleSwitchType 2267 }  -- 12-Port 40GBASE-R Ethernet QSFP+ Optical Interface Board(SE)
ibevtModuleSw-LSDM3TGS48SE0-Z            OBJECT IDENTIFIER ::= { ibevtModuleSwitchType 2268 }  -- 48-Port 10GBASE-R Ethernet SFP+ Optical Interface Board(SE)
ibevtModuleSw-LSDM3SUPA0-Z               OBJECT IDENTIFIER ::= { ibevtModuleSwitchType 2269 }  -- Supervisor Engine Board
ibevtModuleSw-LSDM3FAB08D0-Z             OBJECT IDENTIFIER ::= { ibevtModuleSwitchType 2270 }  -- Switch Fabric Board
ibevtModuleSw-LSDM3GT24GPSE0-Z           OBJECT IDENTIFIER ::= { ibevtModuleSwitchType 2271 }  -- 24-Port 10/100/1000BASE-T Electrical Interface(RJ45)+24-Port 1000BASE-X Ethernet Optical Interface Board(SFP,LC)(SE)
ibevtModuleSw-LSDM3GP48SE0-Z             OBJECT IDENTIFIER ::= { ibevtModuleSwitchType 2272 }  -- 48-Port 1000BASE-X Ethernet Optical Interface Board(SFP,LC)
ibevtModuleSw-LSDM3GT48SE0-Z             OBJECT IDENTIFIER ::= { ibevtModuleSwitchType 2273 }  -- 48-Port 10/100/1000BASE-T Ethernet Interface Board(RJ45)(SE)
ibevtModuleSw-LSDM3CGS8SE0-Z             OBJECT IDENTIFIER ::= { ibevtModuleSwitchType 2274 }  -- 8-Port 100GBASE-R Ethernet Optical Interface Board(QSFP28,LC)
ibevtModuleSw-RX-CEPC-CQ8LF              OBJECT IDENTIFIER ::= { ibevtModuleSwitchType 2275 }  -- 8-port 100G Flexible Ethernet Optical Interface Line Processing Unit(QSFP28,LC)
ibevtModuleSw-RX-SPE200-E                OBJECT IDENTIFIER ::= { ibevtModuleSwitchType 2276 }  -- Service Processing Unit(SPE200-E)

ibevtModuleSw-DSH7503-MP                 OBJECT IDENTIFIER ::= { ibevtModuleSwitchType 2277 }  -- Supervisor Engine Board
ibevtModuleSw-DSH7506-MP                 OBJECT IDENTIFIER ::= { ibevtModuleSwitchType 2278 }  -- Supervisor Engine Board
ibevtModuleSw-DSH7510-MP                 OBJECT IDENTIFIER ::= { ibevtModuleSwitchType 2279 }  -- Supervisor Engine Board
ibevtModuleSw-DSH7500-48T-P              OBJECT IDENTIFIER ::= { ibevtModuleSwitchType 2280 }  -- 48-Port 1000Base-T Gigabit Ethernet Interface Board(RJ45)-POE
ibevtModuleSw-DSH7500-16X                OBJECT IDENTIFIER ::= { ibevtModuleSwitchType 2281 }  -- 16-Port 10GBASE-R Ethernet SFP+ Optical Interface Board
ibevtModuleSw-DSH7500-48F                OBJECT IDENTIFIER ::= { ibevtModuleSwitchType 2282 }  -- 48-Port 1000BASE-X Optical Interface Board(SFP,LC)
ibevtModuleSw-DSH7500-12QX4Q28           OBJECT IDENTIFIER ::= { ibevtModuleSwitchType 2283 }  -- 12-Port 40GBASE-R QSFP+ or 4-Port 100GBASE-R QSFP28 Optical Interface Board
ibevtModuleSw-DSH7500-24F4X              OBJECT IDENTIFIER ::= { ibevtModuleSwitchType 2284 }  -- 24-Port GE Optical Interface(SFP,LC)+4-Port 10GE Optical Interface Board(SFP+,LC)
ibevtModuleSw-DSH7500-24QX               OBJECT IDENTIFIER ::= { ibevtModuleSwitchType 2285 }  -- 24-Port 40GBASE-R Ethernet QSFP+ Optical Interface Board
ibevtModuleSw-DSH7500-24T4X              OBJECT IDENTIFIER ::= { ibevtModuleSwitchType 2286 }  -- 24-Port 1000Base-T Gigabit Ethernet Interface Board(RJ45)+4-Port 10GE Optical Interface Board(SFP+,LC)
ibevtModuleSw-DSH7500-24X2QX1Q28         OBJECT IDENTIFIER ::= { ibevtModuleSwitchType 2287 }  -- 24-Port 10GBASE-R Optical Interface(SFP+,LC)+2-Port 40GBASE-R Optical Interface Board(QSFP+) or 1-Port 100GBASE-R Optical Interface Board(QSFP28)
ibevtModuleSw-DSH7500-2Q28               OBJECT IDENTIFIER ::= { ibevtModuleSwitchType 2288 }  -- 2-Port 100GBASE-R Ethernet QSFP28 Optical Interface Board
ibevtModuleSw-DSH7500-44F4X              OBJECT IDENTIFIER ::= { ibevtModuleSwitchType 2289 }  -- 44-Port GE Optical Interface(SFP,LC)+4-Port 10GE Optical Interface Board(SFP+,LC)
ibevtModuleSw-DSH7500-48T                OBJECT IDENTIFIER ::= { ibevtModuleSwitchType 2290 }  -- 48-Port 10/100/1000BASE-T Electrical Interface Board(RJ45)
ibevtModuleSw-DSH7500-48X                OBJECT IDENTIFIER ::= { ibevtModuleSwitchType 2291 }  -- 48-Port 10GBASE-R Ethernet SFP+ Optical Interface Board
ibevtModuleSw-LSWM2-iMC                  OBJECT IDENTIFIER ::= { ibevtModuleSwitchType 2292 }  -- Intelligent Network Management Module
ibevtModuleSw-LSWM2ZQP2P-Z               OBJECT IDENTIFIER ::= { ibevtModuleSwitchType 2293 }  -- 2-Port QSFP28 Interface Module
ibevtModuleSw-LSWM2ZSP4P-Z               OBJECT IDENTIFIER ::= { ibevtModuleSwitchType 2294 }  -- 4-Port SFP28 Interface Module
ibevtModuleSw-LSWM2ZSP8P-Z               OBJECT IDENTIFIER ::= { ibevtModuleSwitchType 2295 }  -- 8-Port SFP28 Interface Module
ibevtModuleSw-LSDM3SUP04A0-Z             OBJECT IDENTIFIER ::= { ibevtModuleSwitchType 2296 }  -- Supervisor Engine Board
ibevtModuleSw-LSDM3FAB04E0-Z             OBJECT IDENTIFIER ::= { ibevtModuleSwitchType 2297 }  -- Switching Fabric Module
ibevtModuleSw-LSDM3FAB08E0-Z             OBJECT IDENTIFIER ::= { ibevtModuleSwitchType 2298 }  -- Switching Fabric Module
ibevtModuleSw-LSDM3QGS36SE0-Z            OBJECT IDENTIFIER ::= { ibevtModuleSwitchType 2299 }  -- 36-Port 40GBASE-R Ethernet QSFP+ Optical Interface Board
ibevtModuleSw-LSDM3CGS12SE0-Z            OBJECT IDENTIFIER ::= { ibevtModuleSwitchType 2300 }  -- 12-Port 100GBASE-R Ethernet QSFP28 Optical Interface Board
ibevtModuleSw-LSQM2XPT12TSFD0            OBJECT IDENTIFIER ::= { ibevtModuleSwitchType 2301 }  -- 12-Port 10/1GBASE-PR/PRX Ethernet Optical(SFP+,LC) and 8-Port 10GBASE-R SFP+ Optical Interface Board
ibevtModuleSw-CSPEX-1702X                OBJECT IDENTIFIER ::= { ibevtModuleSwitchType 2302 }  -- Service Processing Unit(1702X)
ibevtModuleSw-CSR05SRP1P1                OBJECT IDENTIFIER ::= { ibevtModuleSwitchType 2303 }  -- CR16000-F CSR05SRP1P1 Main Processing Unit(1P1)
ibevtModuleSw-NIC-GP24L1                 OBJECT IDENTIFIER ::= { ibevtModuleSwitchType 2304 }  -- 24-port 1000BASE-X Ethernet Optical Interface Card(SFP,LC)(NIC)
ibevtModuleSw-NIC-GP24LA                 OBJECT IDENTIFIER ::= { ibevtModuleSwitchType 2305 }  -- 24-port 1000BASE-X Ethernet Optical Interface Card A(SFP,LC)(NIC)
ibevtModuleSw-NIC-XP20L1                 OBJECT IDENTIFIER ::= { ibevtModuleSwitchType 2306 }  -- 20-port 10GBASE-R/W Ethernet Optical Interface Card(SFP+,LC)(NIC)
ibevtModuleSw-NIC-XP20LA                 OBJECT IDENTIFIER ::= { ibevtModuleSwitchType 2307 }  -- 20-port 10GBASE-R/W Ethernet Optical Interface Card A(SFP+,LC)(NIC)
ibevtModuleSw-RX-NIC-LGQ4LF              OBJECT IDENTIFIER ::= { ibevtModuleSwitchType 2308 }  -- 4-port 50G Flexible Ethernet Optical Interface Card(QSFP28,LC)(RX-NIC)
ibevtModuleSw-CSR05SRP1R3A               OBJECT IDENTIFIER ::= { ibevtModuleSwitchType 2309 }  -- CR16000-FA Main Processing Unit(1R3A)
ibevtModuleSw-CEPC-CQ8L                  OBJECT IDENTIFIER ::= { ibevtModuleSwitchType 2310 }  -- 8-port 100G Ethernet Optical Interface Line Processing Unit(QSFP28,LC)
ibevtModuleSw-CEPC-CQ8LA                 OBJECT IDENTIFIER ::= { ibevtModuleSwitchType 2311 }  -- 8-port 100G Ethernet Optical Interface Line Processing Unit A(QSFP28,LC)
ibevtModuleSw-CSPEX-1802XA               OBJECT IDENTIFIER ::= { ibevtModuleSwitchType 2312 }  -- Service Processing Unit(1802XA)
ibevtModuleSw-CSPEX-1802XB               OBJECT IDENTIFIER ::= { ibevtModuleSwitchType 2313 }  -- Service Processing Unit(1802XB)
ibevtModuleSw-CSPEX-1502XA               OBJECT IDENTIFIER ::= { ibevtModuleSwitchType 2314 }  -- Service Processing Unit(1502XA)
ibevtModuleSw-CSPEX-1512XB               OBJECT IDENTIFIER ::= { ibevtModuleSwitchType 2315 }  -- Service Processing Unit(1512XB)

ibevtModuleSw-NIC-XP20L1A                OBJECT IDENTIFIER ::= { ibevtModuleSwitchType 2317 }  -- 20-port 10GBASE-R/W Ethernet Optical Interface Card A(SFP+,LC)(NIC)
ibevtModuleSw-NIC-XP20L1B                OBJECT IDENTIFIER ::= { ibevtModuleSwitchType 2318 }  -- 20-port 10GBASE-R/W Ethernet Optical Interface Card B(SFP+,LC)(NIC)

ibevtModuleSw-NIC-GP24L1A                OBJECT IDENTIFIER ::= { ibevtModuleSwitchType 2320 }  -- 24-port 1000BASE-X Ethernet Optical Interface Card A(SFP,LC)(NIC)
ibevtModuleSw-NIC-GP24L1B                OBJECT IDENTIFIER ::= { ibevtModuleSwitchType 2321 }  -- 24-port 1000BASE-X Ethernet Optical Interface Card B(SFP,LC)(NIC)
ibevtModuleSw-NIC-CQ2LA                  OBJECT IDENTIFIER ::= { ibevtModuleSwitchType 2322 }  -- 2-port 100G Ethernet Optical Interface Card A(QSFP28)(NIC)
ibevtModuleSw-NIC-CQ2LB                  OBJECT IDENTIFIER ::= { ibevtModuleSwitchType 2323 }  -- 2-port 100G Ethernet Optical Interface Card B(QSFP28)(NIC)
ibevtModuleSw-NIC-XP5LA                  OBJECT IDENTIFIER ::= { ibevtModuleSwitchType 2324 }  -- 5-port 10GBASE-R/W Ethernet Optical Interface Card A(SFP+,LC)(NIC)
ibevtModuleSw-NIC-XP5LB                  OBJECT IDENTIFIER ::= { ibevtModuleSwitchType 2325 }  -- 5-port 10GBASE-R/W Ethernet Optical Interface Card B(SFP+,LC)(NIC)
ibevtModuleSw-CSFC-16T1                  OBJECT IDENTIFIER ::= { ibevtModuleSwitchType 2326 }  -- CR16018-F Fabric Module(T Type)
ibevtModuleSw-LSUM1MPUS10XEC0            OBJECT IDENTIFIER ::= { ibevtModuleSwitchType 2327 }  -- Supervisor Engine Board
ibevtModuleSw-LSUM1MPUS10XEC3            OBJECT IDENTIFIER ::= { ibevtModuleSwitchType 2328 }  -- Supervisor Engine Board
ibevtModuleSw-LSUM1MPUS06XEC3            OBJECT IDENTIFIER ::= { ibevtModuleSwitchType 2329 }  -- Supervisor Engine Board
ibevtModuleSw-LSUM1FAB10XEC0             OBJECT IDENTIFIER ::= { ibevtModuleSwitchType 2330 }  -- Switching Fabric Module
ibevtModuleSw-LSCM2MPUS06AS0-Z           OBJECT IDENTIFIER ::= { ibevtModuleSwitchType 2331 }  -- Supervisor Engine Board
ibevtModuleSw-LSCM2CGT24TSSC0-Z          OBJECT IDENTIFIER ::= { ibevtModuleSwitchType 2332 }  -- Supervisor Engine Board With 24-Port 10/100/1000BASE-T Ethernet Interface+4-Port 10GBASE-R Ethernet SFP+ Optical Interfaces
ibevtModuleSw-LSCM2CGP24TSSC0-Z          OBJECT IDENTIFIER ::= { ibevtModuleSwitchType 2333 }  -- Supervisor Engine Board With 24-Port 1000BASE-X Ethernet SFP Optical Interface+4-Port 10GBASE-R Ethernet SFP+ Optical Interfaces
ibevtModuleSw-LSCM2CTGS12GTSC0-Z         OBJECT IDENTIFIER ::= { ibevtModuleSwitchType 2334 }  -- Supervisor Engine Board With 16-Port 10/100/1000BASE-T Ethernet Interface+12-Port 10GBASE-R Ethernet SFP+ Optical Interfaces
ibevtModuleSw-LSCM2CTGS12GPSC0-Z         OBJECT IDENTIFIER ::= { ibevtModuleSwitchType 2335 }  -- Supervisor Engine Board With 16-Port 1000BASE-X Ethernet SFP Optical Interface+12-Port 10GBASE-R Ethernet SFP+ Optical Interfaces
ibevtModuleSw-LSCM2GT24GPTSSC0-Z         OBJECT IDENTIFIER ::= { ibevtModuleSwitchType 2336 }  -- 24-Port 10/100/1000BASE-T Ethernet Interface Board(RJ45)+20-Port 1000BASE-X Ethernet SFP Optical Interface(SFP,LC)+4-Port 10GBASE-R Optical Interface Board(SFP+,LC)(SC)
ibevtModuleSw-LSCM2GT24GPSC0-Z           OBJECT IDENTIFIER ::= { ibevtModuleSwitchType 2337 }  -- 24-Port 10/100/1000BASE-T Ethernet Interface Board(RJ45)+8-Port 1000BASE-X Ethernet SFP Optical Interface(SFP,LC)(SC)
ibevtModuleSw-LSCM2GP24GTSC0-Z           OBJECT IDENTIFIER ::= { ibevtModuleSwitchType 2338 }  -- 8-Port 10/100/1000BASE-T Ethernet Interface Board(RJ45)+24-Port 1000BASE-X Ethernet SFP Optical Interface(SFP,LC)(SC)
ibevtModuleSw-LSCM2GT48SC0-Z             OBJECT IDENTIFIER ::= { ibevtModuleSwitchType 2339 }  -- 48-Port 10/100/1000BASE-T Ethernet Interface Board(RJ45)(SC)
ibevtModuleSw-LSCM2GP48SC0-Z             OBJECT IDENTIFIER ::= { ibevtModuleSwitchType 2340 }  -- 48-Port 1000BASE-X Ethernet Optical Interface Board(SFP,LC)
ibevtModuleSw-LSCM2TGS16GPSC0-Z          OBJECT IDENTIFIER ::= { ibevtModuleSwitchType 2341 }  -- 24-Port 1000BASE-R Ethernet Optical Interface(SFP,LC)+16-Port 10GBASE-R Ethernet Optical Interface Board(SFP+,LC)
ibevtModuleSw-LSWM2SP2PM-Z               OBJECT IDENTIFIER ::= { ibevtModuleSwitchType 2342 }  -- 2-Port SFP+ Interface Module with MACsec
ibevtModuleSw-LSWM2QP2P-Z                OBJECT IDENTIFIER ::= { ibevtModuleSwitchType 2343 }  -- 2-Port QSFP+ Interface Module
ibevtModuleSw-LSWM2SP8P-Z                OBJECT IDENTIFIER ::= { ibevtModuleSwitchType 2344 }  -- 8-Port SFP+ Interface Module
ibevtModuleSw-LSCM2MPUS06AS0             OBJECT IDENTIFIER ::= { ibevtModuleSwitchType 2345 }  -- Supervisor Engine Board
ibevtModuleSw-LSCM2CGT24TSSC0            OBJECT IDENTIFIER ::= { ibevtModuleSwitchType 2346 }  -- Supervisor Engine Board With 24-Port 10/100/1000BASE-T Ethernet Interface+4-Port 10GBASE-R Ethernet SFP+ Optical Interfaces
ibevtModuleSw-LSCM2CGP24TSSC0            OBJECT IDENTIFIER ::= { ibevtModuleSwitchType 2347 }  -- Supervisor Engine Board With 24-Port 1000BASE-X Ethernet SFP Optical Interface+4-Port 10GBASE-R Ethernet SFP+ Optical Interfaces
ibevtModuleSw-LSCM2CTGS12GTSC0           OBJECT IDENTIFIER ::= { ibevtModuleSwitchType 2348 }  -- Supervisor Engine Board With 16-Port 10/100/1000BASE-T Ethernet Interface+12-Port 10GBASE-R Ethernet SFP+ Optical Interfaces
ibevtModuleSw-LSCM2CTGS12GPSC0           OBJECT IDENTIFIER ::= { ibevtModuleSwitchType 2349 }  -- Supervisor Engine Board With 16-Port 1000BASE-X Ethernet SFP Optical Interface+12-Port 10GBASE-R Ethernet SFP+ Optical Interfaces
ibevtModuleSw-LSCM2GT24GPTSSC0           OBJECT IDENTIFIER ::= { ibevtModuleSwitchType 2350 }  -- 24-Port 10/100/1000BASE-T Ethernet Interface Board(RJ45)+20-Port 1000BASE-X Ethernet SFP Optical Interface(SFP,LC)+4-Port 10GBASE-R Optical Interface Board(SFP+,LC)(SC)
ibevtModuleSw-LSCM2GT24GPSC0             OBJECT IDENTIFIER ::= { ibevtModuleSwitchType 2351 }  -- 24-Port 10/100/1000BASE-T Ethernet Interface Board(RJ45)+8-Port 1000BASE-X Ethernet SFP Optical Interface(SFP,LC)(SC)
ibevtModuleSw-LSCM2GP24GTSC0             OBJECT IDENTIFIER ::= { ibevtModuleSwitchType 2352 }  -- 8-Port 10/100/1000BASE-T Ethernet Interface Board(RJ45)+24-Port 1000BASE-X Ethernet SFP Optical Interface(SFP,LC)(SC)
ibevtModuleSw-LSCM2GT48SC0               OBJECT IDENTIFIER ::= { ibevtModuleSwitchType 2353 }  -- 48-Port 10/100/1000BASE-T Ethernet Interface Board(RJ45)(SC)
ibevtModuleSw-LSCM2GP48SC0               OBJECT IDENTIFIER ::= { ibevtModuleSwitchType 2354 }  -- 48-Port 1000BASE-X Ethernet Optical Interface Board(SFP,LC)
ibevtModuleSw-LSCM2TGS16GPSC0            OBJECT IDENTIFIER ::= { ibevtModuleSwitchType 2355 }  -- 24-Port 1000BASE-R Ethernet Optical Interface(SFP,LC)+16-Port 10GBASE-R Ethernet Optical Interface Board(SFP+,LC)
ibevtModuleSw-LSXM1SFK04FR1              OBJECT IDENTIFIER ::= { ibevtModuleSwitchType 2356 }  -- S12504R Fabric Module
ibevtModuleSw-LSXM1SFK08ER1              OBJECT IDENTIFIER ::= { ibevtModuleSwitchType 2357 }  -- S12508CR Fabric Module
ibevtModuleSw-LSXM1SFK16ER1              OBJECT IDENTIFIER ::= { ibevtModuleSwitchType 2358 }  -- S12516CR Fabric Module
ibevtModuleSw-LSXM1CCQ48KBR1             OBJECT IDENTIFIER ::= { ibevtModuleSwitchType 2359 }  --  48-Port 200GBASE Ethernet Optical Interface Module (QSFP56)(KB)
ibevtModuleSw-LSQM3SUPA0                 OBJECT IDENTIFIER ::= { ibevtModuleSwitchType 2360 }  -- Supervisor Engine Board
ibevtModuleSw-LSQM3SUPA3                 OBJECT IDENTIFIER ::= { ibevtModuleSwitchType 2361 }  -- Supervisor Engine Board
ibevtModuleSw-LSXM1YGS24CGMODTE2         OBJECT IDENTIFIER ::= { ibevtModuleSwitchType 2362 }  -- 24-Port 25G Ethernet Optical Interface(SFP28)+4-Port 100G Ethernet Optical Interface Module (QSFP28),With 1 Expansion Slot
ibevtModuleSw-LSXM1SUPE1                 OBJECT IDENTIFIER ::= { ibevtModuleSwitchType 2363 }  -- Supervisor Engine Unit

ibevtModuleSw-LSUM2TGS48SH0              OBJECT IDENTIFIER ::= { ibevtModuleSwitchType 2364 } -- 48-Port 10G Ethernet Optical Interface Module(SFP+,LC)(SH)
ibevtModuleSw-LSCM3SUP03A0               OBJECT IDENTIFIER ::= { ibevtModuleSwitchType 2365 } -- Supervisor Engine Board
ibevtModuleSw-LSCM3MPUS06A0              OBJECT IDENTIFIER ::= { ibevtModuleSwitchType 2366 } -- Supervisor Engine Board
ibevtModuleSw-LSCM3TGS48SE0              OBJECT IDENTIFIER ::= { ibevtModuleSwitchType 2367 } -- 48-Port 10GBASE-R Ethernet SFP+ Optical Interface Board(SE)
ibevtModuleSw-LSCM3QGS8CSSE0             OBJECT IDENTIFIER ::= { ibevtModuleSwitchType 2368 } -- 8-Port 40GBASE-R QSFP+ + 4-Port 100GBASE-R QSFP28 Optical Interface Board(SE)
ibevtModuleSw-LSCM3SUP03A0-ZE            OBJECT IDENTIFIER ::= { ibevtModuleSwitchType 2369 } -- Supervisor Engine Board
ibevtModuleSw-LSCM3GT48SC0-ZE            OBJECT IDENTIFIER ::= { ibevtModuleSwitchType 2370 } -- 48-Port 10/100/1000BASE-T Electrical Interface Board(RJ45)(SC)
ibevtModuleSw-LSCM3TGS48SE0-ZE           OBJECT IDENTIFIER ::= { ibevtModuleSwitchType 2371 } -- 48-Port 10GBASE-R Ethernet SFP+ Optical Interface Board(SE)
ibevtModuleSw-LSCM3QGS8CSSE0-ZE          OBJECT IDENTIFIER ::= { ibevtModuleSwitchType 2372 } -- 8-Port 40GBASE-R QSFP+ + 4-Port 100GBASE-R QSFP28 Optical Interface Board(SE)
ibevtModuleSw-LSDM3FAB04G0-Z             OBJECT IDENTIFIER ::= { ibevtModuleSwitchType 2373 } -- Switch Fabric Board
ibevtModuleSw-LSDM3FAB08G0-Z             OBJECT IDENTIFIER ::= { ibevtModuleSwitchType 2374 } -- Switch Fabric Board
ibevtModuleSw-LSDM3FAB16G0-Z             OBJECT IDENTIFIER ::= { ibevtModuleSwitchType 2375 } -- Switch Fabric Board
ibevtModuleSw-LSDM3CGS36SF0-Z            OBJECT IDENTIFIER ::= { ibevtModuleSwitchType 2376 } -- 36-Port 100GBASE-R Ethernet Optical Interface Board(QSFP28,LC)
ibevtModuleSw-LSDM3YGS48SF0-Z            OBJECT IDENTIFIER ::= { ibevtModuleSwitchType 2377 } -- 48-Port 25GBASE-R Ethernet Optical Interface Board(SFP28,LC)
ibevtModuleSw-LSCM3MPUS10B0              OBJECT IDENTIFIER ::= { ibevtModuleSwitchType 2378 } -- Supervisor Engine Board
ibevtModuleSw-LSCM3MPUS10B0-Z            OBJECT IDENTIFIER ::= { ibevtModuleSwitchType 2379 } -- Supervisor Engine Board
ibevtModuleSw-LSUM1CGS8QSSH8             OBJECT IDENTIFIER ::= { ibevtModuleSwitchType 2380 } -- 8-Port 100G Ethernet Optical Interface Module(QSFP28) +8-port 40G/4-Port 100G Ethernet Optical Interface Module(QSFP28)(SH)
ibevtModuleSw-LSDM3TGS48SF0-Z            OBJECT IDENTIFIER ::= { ibevtModuleSwitchType 2381 } -- 48-Port 10GBASE-R Ethernet SFP+ Optical Interface Board(SF)
ibevtModuleSw-LSDM1SUPA0                 OBJECT IDENTIFIER ::= { ibevtModuleSwitchType 2382 } -- Supervisor Engine Board
ibevtModuleSw-LSDM1FAB08D0               OBJECT IDENTIFIER ::= { ibevtModuleSwitchType 2383 } -- Switch Fabric Board
ibevtModuleSw-LSDM1TGS48SE0              OBJECT IDENTIFIER ::= { ibevtModuleSwitchType 2384 } -- 48-Port 10GBASE-R Ethernet SFP+ Optical Interface Board(SE)
ibevtModuleSw-LSDM1GT24GPSE0             OBJECT IDENTIFIER ::= { ibevtModuleSwitchType 2385 } -- 24-Port 10/100/1000BASE-T Electrical Interface(RJ45)+24-Port 1000BASE-X Ethernet Optical Interface Board(SFP,LC)(SE)
ibevtModuleSw-LSDM1GT48SE0               OBJECT IDENTIFIER ::= { ibevtModuleSwitchType 2386 } -- 48-Port 10/100/1000BASE-T Ethernet Interface Board(RJ45)(SE)
ibevtModuleSw-LSDM1GP48SE0               OBJECT IDENTIFIER ::= { ibevtModuleSwitchType 2387 } -- 48-Port 1000BASE-X Ethernet Optical Interface Board(SFP,LC)
ibevtModuleSw-LSDM3SUPA0                 OBJECT IDENTIFIER ::= { ibevtModuleSwitchType 2388 } -- Supervisor Engine Board
ibevtModuleSw-LSDM3FAB08D0               OBJECT IDENTIFIER ::= { ibevtModuleSwitchType 2389 } -- Switch Fabric Board
ibevtModuleSw-LSDM3TGS48SE0              OBJECT IDENTIFIER ::= { ibevtModuleSwitchType 2390 } -- 48-Port 10GBASE-R Ethernet SFP+ Optical Interface Board(SE)
ibevtModuleSw-LSDM3GT24GPSE0             OBJECT IDENTIFIER ::= { ibevtModuleSwitchType 2391 } -- 24-Port 10/100/1000BASE-T Electrical Interface(RJ45)+24-Port 1000BASE-X Ethernet Optical Interface Board(SFP,LC)(SE)
ibevtModuleSw-LSDM3GT48SE0               OBJECT IDENTIFIER ::= { ibevtModuleSwitchType 2392 } -- 48-Port 10/100/1000BASE-T Ethernet Interface Board(RJ45)(SE)
ibevtModuleSw-LSDM3GP48SE0               OBJECT IDENTIFIER ::= { ibevtModuleSwitchType 2393 } -- 48-Port 1000BASE-X Ethernet Optical Interface Board(SFP,LC)
ibevtModuleSw-SR07MPUA3-M                OBJECT IDENTIFIER ::= { ibevtModuleSwitchType 2394 } -- CR16000-M Management and Route Process Board(UA3-M)
ibevtModuleSw-SFE-A                      OBJECT IDENTIFIER ::= { ibevtModuleSwitchType 2395 } -- Network Processing Unit(A)
ibevtModuleSw-MIC-CQ1L-M                 OBJECT IDENTIFIER ::= { ibevtModuleSwitchType 2396 } -- 1-Port 100G Ethernet Optical Interface Card(QSFP28,LC)
ibevtModuleSw-MIC-CQ2L-M                 OBJECT IDENTIFIER ::= { ibevtModuleSwitchType 2397 } -- 2-Port 100G Ethernet Optical Interface Card(QSFP28,LC)


ibevtModuleSw-LSXM1CGQ18C1               OBJECT IDENTIFIER ::= { ibevtModuleSwitchType 2398 } -- 18-Port 100GBASE Ethernet Optical Interface Module (QSFP28)
ibevtModuleSw-LSXM1CGQMS18B1             OBJECT IDENTIFIER ::= { ibevtModuleSwitchType 2399 } -- 18-Port 100GBASE MACsec Ethernet Optical Interface Module(QSFP28)
ibevtModuleSw-LSXM1MOD48KBR1             OBJECT IDENTIFIER ::= { ibevtModuleSwitchType 2400 } -- 48KBR Flexible Line Processing Platform Module
ibevtModuleSw-LSXM1CDQ36KB1              OBJECT IDENTIFIER ::= { ibevtModuleSwitchType 2401 } -- 36-Port 400GBASE Ethernet Optical Interface Module(QSFP-DD)(KB)
ibevtModuleSw-LSXM1SUP02TR1              OBJECT IDENTIFIER ::= { ibevtModuleSwitchType 2402 } -- Supervisor Engine Unit
ibevtModuleSw-LSCM2SUP03B0               OBJECT IDENTIFIER ::= { ibevtModuleSwitchType 2407 } -- Supervisor Engine Board
ibevtModuleSw-LSCM2SUP03B0-Z             OBJECT IDENTIFIER ::= { ibevtModuleSwitchType 2408 } -- Supervisor Engine Board
ibevtModuleSw-LSWM2QP4P                  OBJECT IDENTIFIER ::= { ibevtModuleSwitchType 2409 } -- 4-Port QSFP+ Interface Module
ibevtModuleSw-LSXM1SUPS2                 OBJECT IDENTIFIER ::= { ibevtModuleSwitchType 2410 } -- Supervisor Engine Board
ibevtModuleSw-LSXM1SFS08D2               OBJECT IDENTIFIER ::= { ibevtModuleSwitchType 2411 } -- Switch Fabric Board
ibevtModuleSw-LSXM1TGS48SE2              OBJECT IDENTIFIER ::= { ibevtModuleSwitchType 2412 } -- 48-Port 10GBASE-R Ethernet SFP+ Optical Interface Board(SE)
ibevtModuleSw-LSXM1GT24GPSE2             OBJECT IDENTIFIER ::= { ibevtModuleSwitchType 2413 } -- 24-Port 10/100/1000BASE-T Electrical Interface(RJ45)+24-Port 1000BASE-X Ethernet Optical Interface Board(SFP,LC)(SE)
ibevtModuleSw-LSXM1GT48SE2               OBJECT IDENTIFIER ::= { ibevtModuleSwitchType 2414 } -- 48-Port 10/100/1000BASE-T Ethernet Interface Board(RJ45)(SE)
ibevtModuleSw-LSXM1GP48SE2               OBJECT IDENTIFIER ::= { ibevtModuleSwitchType 2415 } -- 48-Port 1000BASE-X Ethernet Optical Interface Board(SFP,LC)
ibevtModuleSw-LSXM3SUPS2                 OBJECT IDENTIFIER ::= { ibevtModuleSwitchType 2416 } -- Supervisor Engine Board
ibevtModuleSw-LSXM3SFS08D2               OBJECT IDENTIFIER ::= { ibevtModuleSwitchType 2417 } -- Switch Fabric Board
ibevtModuleSw-LSXM3TGS48SE2              OBJECT IDENTIFIER ::= { ibevtModuleSwitchType 2418 } -- 48-Port 10GBASE-R Ethernet SFP+ Optical Interface Board(SE)
ibevtModuleSw-LSXM3GT24GPSE2             OBJECT IDENTIFIER ::= { ibevtModuleSwitchType 2419 } -- 24-Port 10/100/1000BASE-T Electrical Interface(RJ45)+24-Port 1000BASE-X Ethernet Optical Interface Board(SFP,LC)(SE)
ibevtModuleSw-LSXM3GT48SE2               OBJECT IDENTIFIER ::= { ibevtModuleSwitchType 2420 } -- 48-Port 10/100/1000BASE-T Ethernet Interface Board(RJ45)(SE)
ibevtModuleSw-LSXM3GP48SE2               OBJECT IDENTIFIER ::= { ibevtModuleSwitchType 2421 } -- 48-Port 1000BASE-X Ethernet Optical Interface Board(SFP,LC)
ibevtModuleSw-LSXM3SUP04S2               OBJECT IDENTIFIER ::= { ibevtModuleSwitchType 2422 } -- Supervisor Engine Board
ibevtModuleSw-LSXM3SFS04G2               OBJECT IDENTIFIER ::= { ibevtModuleSwitchType 2423 } -- Switch Fabric Board
ibevtModuleSw-LSXM3SFS08G2               OBJECT IDENTIFIER ::= { ibevtModuleSwitchType 2424 } -- Switch Fabric Board
ibevtModuleSw-LSXM3SFS16G2               OBJECT IDENTIFIER ::= { ibevtModuleSwitchType 2425 } -- Switch Fabric Board
ibevtModuleSw-LSXM3CGQ36SF2              OBJECT IDENTIFIER ::= { ibevtModuleSwitchType 2426 } -- 36-Port 100GBASE-R Ethernet Optical Interface Board(QSFP28,LC)
ibevtModuleSw-LSXM3YGS48SF2              OBJECT IDENTIFIER ::= { ibevtModuleSwitchType 2427 } -- 48-Port 25GBASE-R Ethernet Optical Interface Board(SFP28,LC)
ibevtModuleSw-LSXM3TGS48SF2              OBJECT IDENTIFIER ::= { ibevtModuleSwitchType 2428 } -- 48-Port 10GBASE-R Ethernet SFP+ Optical Interface Board(SF)
ibevtModuleSw-MIC-GP12L-M                OBJECT IDENTIFIER ::= { ibevtModuleSwitchType 2429 } -- 12-port 1000BASE-X Optical Interface Card(SFP,LC)
ibevtModuleSw-MIC-CQ1LF-M                OBJECT IDENTIFIER ::= { ibevtModuleSwitchType 2430 } -- 1-port 100G Flexible Ethernet Optical Interface Card(QSFP28,LC)
ibevtModuleSw-MIC-XP10L-M                OBJECT IDENTIFIER ::= { ibevtModuleSwitchType 2431 } -- 10-port 10GBASE-R/W Ethernet Optical Interface Card Module(SFP+,LC)
ibevtModuleSw-MIC-CLP4L-M                OBJECT IDENTIFIER ::= { ibevtModuleSwitchType 2432 } -- 4-port OC-3/STM-1 Channelized POS Optical Interface Card(SFP,LC)
ibevtModuleSw-MIC-ET16L-M                OBJECT IDENTIFIER ::= { ibevtModuleSwitchType 2433 } -- 16-port E1 Copper Interface Card(HM96 Male Connector)
ibevtModuleSw-MIC-PSP4L-M                OBJECT IDENTIFIER ::= { ibevtModuleSwitchType 2434 } -- 4-Port OC-48c/STM-16c POS Optical Interface Card,(SFP,LC)
ibevtModuleSw-MIC-TCP8L-M                OBJECT IDENTIFIER ::= { ibevtModuleSwitchType 2435 } -- 8-Port OC-3c/OC-12c POS Optical Interface Card,(SFP,LC)
ibevtModuleSw-MIC-SP4L-M                 OBJECT IDENTIFIER ::= { ibevtModuleSwitchType 2436 } -- 4-port OC-3c/STM-1c POS/ATM or 1-port OC-12c/STM-4c POS/ATM Fiber Interface Card(SFP,LC)
ibevtModuleSw-LSCM2GV48SC0               OBJECT IDENTIFIER ::= { ibevtModuleSwitchType 2437 } -- 48-Port 10/100/1000BASE-T Ethernet Interface Board(RJ45)(SC)-POE
ibevtModuleSw-LSQM1FAB06XEB0             OBJECT IDENTIFIER ::= { ibevtModuleSwitchType 2438 } -- Switch Fabric Board
ibevtModuleSw-LSQM1FAB10XEA0             OBJECT IDENTIFIER ::= { ibevtModuleSwitchType 2439 } -- Switch Fabric Board
ibevtModuleSw-LSQM1MPUS06XEB0            OBJECT IDENTIFIER ::= { ibevtModuleSwitchType 2440 } -- Supervisor Engine Board
ibevtModuleSw-LSQM1MPUS10XEA0            OBJECT IDENTIFIER ::= { ibevtModuleSwitchType 2441 } -- Supervisor Engine Board
ibevtModuleSw-LSQM2TGS48XSH0             OBJECT IDENTIFIER ::= { ibevtModuleSwitchType 2442 } -- 48-Port 10G Ethernet Optical Interface Module(SFP+,LC)(SH)
ibevtModuleSw-LSQM1TGS48RXSH0            OBJECT IDENTIFIER ::= { ibevtModuleSwitchType 2443 } -- 48-Port 10GBASE-R Ethernet Optical Interface Module(SFP+,LC)(SH)
ibevtModuleSw-LSQM1CGS8XSH0              OBJECT IDENTIFIER ::= { ibevtModuleSwitchType 2444 } -- 8-Port 100G Ethernet Optical Interface Module(QSFP28)(SH)
ibevtModuleSw-LSQM1YGS24CSXSH0           OBJECT IDENTIFIER ::= { ibevtModuleSwitchType 2445 } -- 24-Port 25G Ethernet Optical Interface(SFP28,LC)+4-Port 100G Ethernet Optical Interface Module(QSFP28)(SH)
ibevtModuleSw-LSQM1CGS8QSXSH0            OBJECT IDENTIFIER ::= { ibevtModuleSwitchType 2446 } -- 8-Port 100G Ethernet Optical Interface Module(QSFP28) +8-port 40G/4-Port 100G Ethernet Optical Interface Module(QSFP28)(SH)
ibevtModuleSw-LSQM2GP24TSXSA0            OBJECT IDENTIFIER ::= { ibevtModuleSwitchType 2447 } -- 24-Port GE Optical Interface(SFP,LC)+4-Port 10GE Optical Interface Board(SFP+,LC)(SA)
ibevtModuleSw-LSQM2GT48XSA0              OBJECT IDENTIFIER ::= { ibevtModuleSwitchType 2448 } -- 48-Port 1000Base-T Gigabit Ethernet Interface Board(RJ45)(SA)
ibevtModuleSw-LSQM2GP48XSA0              OBJECT IDENTIFIER ::= { ibevtModuleSwitchType 2449 } -- 48-Port 1000BASE-X Ethernet Optical Interface Board(SFP,LC)(SA)
ibevtModuleSw-LSQM2GP44TSXSE0            OBJECT IDENTIFIER ::= { ibevtModuleSwitchType 2450 } -- 44-Port GE Optical Interface(SFP,LC)+4-Port 10GE Optical Interface Board(SFP+,LC)(SE)
ibevtModuleSw-LSQM2GT24PTSXSE0           OBJECT IDENTIFIER ::= { ibevtModuleSwitchType 2451 } -- 24-Port 1000Base-T Gigabit Ethernet Interface Board(RJ45)+20-Port GE Optical Interface(SFP,LC)+4-Port 10GE Optical Interface Board(SFP+,LC)(SE)
ibevtModuleSw-LSQM2GT24TSXSE0            OBJECT IDENTIFIER ::= { ibevtModuleSwitchType 2452 } -- 24-Port 1000Base-T Gigabit Ethernet Interface Board(RJ45)+4-Port 10GE Optical Interface Board(SFP+,LC)(SE)
ibevtModuleSw-LSQM1GT48XFD0              OBJECT IDENTIFIER ::= { ibevtModuleSwitchType 2453 } -- 48-Port 1000BASE-X Optical Interface Board(SFP,LC)
ibevtModuleSw-LSQM2GP40TS8XFD0           OBJECT IDENTIFIER ::= { ibevtModuleSwitchType 2454 } -- 40-Port 1000BASE-X Optical Interface(SFP,LC)+8-Port 10GBASE-R Ethernet Optical Interface Board(SFP+,LC)
ibevtModuleSw-LSQM1TGT24XFD0             OBJECT IDENTIFIER ::= { ibevtModuleSwitchType 2455 } -- 24-Port 10GBASE-T Ethernet Copper Interface Module(RJ45)(FD)
ibevtModuleSw-LSEM1SUPA0                 OBJECT IDENTIFIER ::= { ibevtModuleSwitchType 2456 } -- Supervisor Engine Board
ibevtModuleSw-LSEM1SF06D0                OBJECT IDENTIFIER ::= { ibevtModuleSwitchType 2457 } -- Switch Fabric Board
ibevtModuleSw-LSEM1GT48TSSD0             OBJECT IDENTIFIER ::= { ibevtModuleSwitchType 2458 } -- 48-Port 10/100/1000BASE-T Electrical Interface(RJ45)+4-Port 10GBASE-R Ethernet Optical Interface Board(SFP+,LC)(SD)
ibevtModuleSw-LSEM1TGS24SD0              OBJECT IDENTIFIER ::= { ibevtModuleSwitchType 2459 } -- 24-Port 10GBASE-R Ethernet SFP+ Optical Interface Board(SD)
ibevtModuleSw-LSEM1TGS48SD0              OBJECT IDENTIFIER ::= { ibevtModuleSwitchType 2460 } -- 48-Port 10GBASE-R Ethernet SFP+ Optical Interface Board(SD)
ibevtModuleSw-LSDM3FAB08F0-Z             OBJECT IDENTIFIER ::= { ibevtModuleSwitchType 2461 } -- Switching Fabric Module
ibevtModuleSw-LSDM3FAB16F0-Z             OBJECT IDENTIFIER ::= { ibevtModuleSwitchType 2462 } -- Switching Fabric Module
ibevtModuleSw-LSDM3QGS36SF0-Z            OBJECT IDENTIFIER ::= { ibevtModuleSwitchType 2463 } -- 36-Port 40G Ethernet Optical Interface Module (QSFP+)
ibevtModuleSw-LSDM3CGS18SF0-Z            OBJECT IDENTIFIER ::= { ibevtModuleSwitchType 2464 } -- 18-Port 100G Ethernet Optical Interface Module (QSFP28)
ibevtModuleSw-LSDM3CDQ16SF0-Z            OBJECT IDENTIFIER ::= { ibevtModuleSwitchType 2465 } -- 16-Port 400G Ethernet Optical Interface Module (QSFP-DD)
ibevtModuleSw-LSDM3CDQ8SF0-Z             OBJECT IDENTIFIER ::= { ibevtModuleSwitchType 2466 } -- 8-Port 400G Ethernet Optical Interface Module (QSFP-DD)
ibevtModuleSw-LSXM3SFS08F2               OBJECT IDENTIFIER ::= { ibevtModuleSwitchType 2467 } -- Switching Fabric Module
ibevtModuleSw-LSXM3SFS16F2               OBJECT IDENTIFIER ::= { ibevtModuleSwitchType 2468 } -- Switching Fabric Module
ibevtModuleSw-LSXM3QGS36SF2              OBJECT IDENTIFIER ::= { ibevtModuleSwitchType 2469 } -- 36-Port 40G Ethernet Optical Interface Module (QSFP+)
ibevtModuleSw-LSXM3CGQ18SF2              OBJECT IDENTIFIER ::= { ibevtModuleSwitchType 2470 } -- 18-Port 100G Ethernet Optical Interface Module (QSFP28)
ibevtModuleSw-LSXM3CDQ16SF2              OBJECT IDENTIFIER ::= { ibevtModuleSwitchType 2471 } -- 16-Port 400G Ethernet Optical Interface Module (QSFP-DD)
ibevtModuleSw-LSXM3CDQ8SF2               OBJECT IDENTIFIER ::= { ibevtModuleSwitchType 2472 } -- 8-Port 400G Ethernet Optical Interface Module (QSFP-DD)
ibevtModuleSw-MIC-XP4L-M                 OBJECT IDENTIFIER ::= { ibevtModuleSwitchType 2473 } -- 4-Port 10GBASE-R/W Ethernet Optical Interface Card (SFP+,LC)
ibevtModuleSw-LSDM3SUP04A0               OBJECT IDENTIFIER ::= { ibevtModuleSwitchType 2474 } -- Supervisor Engine Board
ibevtModuleSw-LSDM3FAB04E0               OBJECT IDENTIFIER ::= { ibevtModuleSwitchType 2475 } -- Switching Fabric Module
ibevtModuleSw-LSDM3QGS36SE0              OBJECT IDENTIFIER ::= { ibevtModuleSwitchType 2476 } -- 36-Port 40GBASE-R Ethernet QSFP+ Optical Interface Board
ibevtModuleSw-CSR05SRP1P3-G              OBJECT IDENTIFIER ::= { ibevtModuleSwitchType 2477 } -- CR16000-F Management and Route Process Board(1P3-G)
ibevtModuleSw-CSPEX-2304X-G              OBJECT IDENTIFIER ::= { ibevtModuleSwitchType 2478 } -- Network Processing Unit(2304X-G)
ibevtModuleSw-CSFC-08T-G                 OBJECT IDENTIFIER ::= { ibevtModuleSwitchType 2479 } -- CR16000-F Fabric Module(T Type-G)
ibevtModuleSw-S66-8VGT                   OBJECT IDENTIFIER ::= { ibevtModuleSwitchType 2480 } -- 8-Port SmartGE (5/2.5/1G) Interface Module
ibevtModuleSw-LSXM1MOD24KBR1             OBJECT IDENTIFIER ::= { ibevtModuleSwitchType 2481 } -- 24KBR Flexible Line Processing Platform Module
ibevtModuleSw-LSXM1TGS24C1               OBJECT IDENTIFIER ::= { ibevtModuleSwitchType 2482 } -- 24-Port 10GBASE Ethernet Optical Interface Module (SFP+,LC)
ibevtModuleSw-LSXM1CGQ8C1                OBJECT IDENTIFIER ::= { ibevtModuleSwitchType 2483 } -- 8-Port 100GBASE Ethernet Optical Interface Module (QSFP28)
ibevtModuleSw-LSXM1CGQ72KCR1             OBJECT IDENTIFIER ::= { ibevtModuleSwitchType 2484 } -- 36-Port 200GBASE Ethernet Optical Interface (QSFP56)/72-Port 100GBASE Ethernet Optical Interface Module (QSFP28)(KC)
ibevtModuleSw-CSR05SRP1P3-GZ             OBJECT IDENTIFIER ::= { ibevtModuleSwitchType 2485 } -- R9900, CSR05SRP1R3,Main Processing Unit(1P3-GZ)
ibevtModuleSw-CSPEX-2304X-GZ             OBJECT IDENTIFIER ::= { ibevtModuleSwitchType 2486 } -- Service Processing Unit(2304X-GZ)
ibevtModuleSw-CSFC-08T-GZ                OBJECT IDENTIFIER ::= { ibevtModuleSwitchType 2487 } -- R9900, Fabric Module(T Type-GZ)
ibevtModuleSw-MIC-CQ1L2                  OBJECT IDENTIFIER ::= { ibevtModuleSwitchType 2488 } -- 1-port 100G  Ethernet Optical Interface Card A(QSFP28)
ibevtModuleSw-MIC-GT12L-M                OBJECT IDENTIFIER ::= { ibevtModuleSwitchType 2489 } -- 12-Port 1000BASE-X Ethernet Copper Interface Card (RJ45)
ibevtModuleSw-MIC-GP24L-M                OBJECT IDENTIFIER ::= { ibevtModuleSwitchType 2490 } -- 24-Port 1000BASE-X Ethernet Optical Interface Card (SFP,LC)
ibevtModuleSw-LSQM1MPUS06S8              OBJECT IDENTIFIER ::= { ibevtModuleSwitchType 2491 } -- Supervisor Engine Board
ibevtModuleSw-LSQM3SUPA8                 OBJECT IDENTIFIER ::= { ibevtModuleSwitchType 2492 } -- Supervisor Engine Board
ibevtModuleSw-LSQM1PT24TSSC8             OBJECT IDENTIFIER ::= { ibevtModuleSwitchType 2493 } -- 24-Port 1G EPON OLT Optical Interface(SFP,SC)+2-Port 10GE Optical Interface Board(SFP+,LC)(SC)
ibevtModuleSw-LSQM2XPT12TSFD8            OBJECT IDENTIFIER ::= { ibevtModuleSwitchType 2494 } -- 12-Port 10/1GBASE-PR/PRX Ethernet Optical(SFP+,LC) and 8-Port 10GBASE-R SFP+ Optical Interface Board
ibevtModuleSw-LSQM2GP24SA8               OBJECT IDENTIFIER ::= { ibevtModuleSwitchType 2495 } -- 24-Port GE Optical Interface(SFP,LC)(SA)
ibevtModuleSw-LSQM1TGS16GPSA8            OBJECT IDENTIFIER ::= { ibevtModuleSwitchType 2496 } -- 24-Port 1000BASE-R Ethernet Optical Interface(SFP,LC)+16-Port 10GBASE-R Ethernet Optical Interface Board(SFP+,LC)
ibevtModuleSw-LSEM1SUPB0                 OBJECT IDENTIFIER ::= { ibevtModuleSwitchType 2500 } -- Supervisor Engine Board
ibevtModuleSw-LSEM1SF12B0                OBJECT IDENTIFIER ::= { ibevtModuleSwitchType 2501 } -- Switching Fabric Module
ibevtModuleSw-LSEM1YGS48CQSF0            OBJECT IDENTIFIER ::= { ibevtModuleSwitchType 2502 } -- 48-Port 25G Ethernet Optical Interface(SFP28,LC)+4-Port 100G Ethernet Optical Interface Module(QSFP28)
ibevtModuleSw-LSEM1CGQ16SF0              OBJECT IDENTIFIER ::= { ibevtModuleSwitchType 2503 } -- 16-Port 100G Ethernet Optical Interface Module(QSFP28)
ibevtModuleSw-LSXM1SUPF1                 OBJECT IDENTIFIER ::= { ibevtModuleSwitchType 2504 } -- S12500G-EF Supervisor Engine Unit
ibevtModuleSw-LSXM1SUPFA1                OBJECT IDENTIFIER ::= { ibevtModuleSwitchType 2505 } -- S12500G-EF AI Supervisor Engine Unit
ibevtModuleSw-LSXM1SFP16F1               OBJECT IDENTIFIER ::= { ibevtModuleSwitchType 2506 } -- S12516G-EF Fabric Module,Type P(Class F)
ibevtModuleSw-LSXM1TGS48PB1              OBJECT IDENTIFIER ::= { ibevtModuleSwitchType 2507 } -- S12500G-EF 48-Port 10GBASE Ethernet Optical Interface Module(SFP+,LC)(PB)
ibevtModuleSw-LSXM1CGQ36PB1              OBJECT IDENTIFIER ::= { ibevtModuleSwitchType 2508 } -- S12500G-EF 36-Port 100GBASE Ethernet Optical Interface Module(QSFP28)(PB)
ibevtModuleSw-SR07MPUA3-M-Z              OBJECT IDENTIFIER ::= { ibevtModuleSwitchType 2509 } -- R9900-M Management and Route Process Board(UA3-M)
ibevtModuleSw-SFE-A-Z                    OBJECT IDENTIFIER ::= { ibevtModuleSwitchType 2510 } -- Network Processing Unit(A)
ibevtModuleSw-MIC-CQ1L-M-Z               OBJECT IDENTIFIER ::= { ibevtModuleSwitchType 2511 } -- 1-Port 100G Ethernet Optical Interface Card(QSFP28,LC)
ibevtModuleSw-MIC-CQ2L-M-Z               OBJECT IDENTIFIER ::= { ibevtModuleSwitchType 2512 } -- 2-Port 100G Ethernet Optical Interface Card(QSFP28,LC)
ibevtModuleSw-MIC-XP4L-M-Z               OBJECT IDENTIFIER ::= { ibevtModuleSwitchType 2513 } -- 4-Port 10GBASE-R/W Ethernet Optical Interface Card (SFP+,LC)
ibevtModuleSw-MIC-GP12L-M-Z              OBJECT IDENTIFIER ::= { ibevtModuleSwitchType 2514 } -- 12-port 1000BASE-X Optical Interface Card(SFP,LC)
ibevtModuleSw-MIC-XP10L-M-Z              OBJECT IDENTIFIER ::= { ibevtModuleSwitchType 2515 } -- 10-port 10GBASE-R/W Ethernet Optical Interface Card Module(SFP+,LC)
ibevtModuleSw-MIC-CLP4L-M-Z              OBJECT IDENTIFIER ::= { ibevtModuleSwitchType 2516 } -- 4-port OC-3/STM-1 Channelized POS Optical Interface Card(SFP,LC)
ibevtModuleSw-MIC-ET16L-M-Z              OBJECT IDENTIFIER ::= { ibevtModuleSwitchType 2517 } -- 16-port E1 Copper Interface Card(HM96 Male Connector)
ibevtModuleSw-MIC-PSP4L-M-Z              OBJECT IDENTIFIER ::= { ibevtModuleSwitchType 2518 } -- 4-Port OC-48c/STM-16c POS Optical Interface Card,(SFP,LC)
ibevtModuleSw-MIC-TCP8L-M-Z              OBJECT IDENTIFIER ::= { ibevtModuleSwitchType 2519 } -- 8-Port OC-3c/OC-12c POS Optical Interface Card,(SFP,LC)
ibevtModuleSw-MIC-SP4L-M-Z               OBJECT IDENTIFIER ::= { ibevtModuleSwitchType 2520 } -- 4-port OC-3c/STM-1c POS/ATM or 1-port OC-12c/STM-4c POS/ATM Fiber Interface Card(SFP,LC)
ibevtModuleSw-MIC-GT12L-M-Z              OBJECT IDENTIFIER ::= { ibevtModuleSwitchType 2521 } -- 12-Port 1000BASE-X Ethernet Copper Interface Card (RJ45)
ibevtModuleSw-MIC-GP24L-M-Z              OBJECT IDENTIFIER ::= { ibevtModuleSwitchType 2522 } -- 24-Port 1000BASE-X Ethernet Optical Interface Card (SFP,LC)
ibevtModuleSw-DS-3E7803-MPU              OBJECT IDENTIFIER ::= { ibevtModuleSwitchType 2523 } -- Supervisor Engine Board
ibevtModuleSw-DS-3E7800-16X24F-SC        OBJECT IDENTIFIER ::= { ibevtModuleSwitchType 2524 } -- 24-Port 1000BASE-R Ethernet Optical Interface(SFP,LC)+16-Port 10GBASE-R Ethernet Optical Interface Board(SFP+,LC)
ibevtModuleSw-DS-3E7800-48F-SC           OBJECT IDENTIFIER ::= { ibevtModuleSwitchType 2525 } -- 48-Port 1000BASE-X Ethernet Optical Interface Board(SFP,LC)
ibevtModuleSw-DS-3E7800-24F8T-SC         OBJECT IDENTIFIER ::= { ibevtModuleSwitchType 2526 } -- 8-Port 10/100/1000BASE-T Ethernet Interface Board(RJ45)+24-Port 1000BASE-X Ethernet SFP Optical Interface(SFP,LC)(SC)
ibevtModuleSw-DS-3E7806-MPU              OBJECT IDENTIFIER ::= { ibevtModuleSwitchType 2527 } -- Supervisor Engine Board
ibevtModuleSw-DS-3E7800-24T20F4X-SC      OBJECT IDENTIFIER ::= { ibevtModuleSwitchType 2528 } -- 24-Port 10/100/1000BASE-T Ethernet Interface Board(RJ45)+20-Port 1000BASE-X Ethernet SFP Optical Interface(SFP,LC)+4-Port 10GBASE-R Optical Interface Board(SFP+,LC)(SC)
ibevtModuleSw-DS-3E7800-24T8F-SC         OBJECT IDENTIFIER ::= { ibevtModuleSwitchType 2529 } -- 24-Port 10/100/1000BASE-T Ethernet Interface Board(RJ45)+8-Port 1000BASE-X Ethernet SFP Optical Interface(SFP,LC)(SC)
ibevtModuleSw-DS-3E7800-48T-SC           OBJECT IDENTIFIER ::= { ibevtModuleSwitchType 2530 } -- 48-Port 10/100/1000BASE-T Ethernet Interface Board(RJ45)(SC)
ibevtModuleSw-RX-SRP1R3                  OBJECT IDENTIFIER ::= { ibevtModuleSwitchType 2531 } -- CR16000-F,RX-SRP1R3,Main Processing Unit(1R3)
ibevtModuleSw-CSFC-16T-G                 OBJECT IDENTIFIER ::= { ibevtModuleSwitchType 2532 } -- CR16000-F Fabric Module(T Type-G)
ibevtModuleSw-NIC-XP20L-E                OBJECT IDENTIFIER ::= { ibevtModuleSwitchType 2533 } -- 20-port 10GBASE-R/W Ethernet Optical Interface Card A(SFP+,LC)(NIC)
ibevtModuleSw-S7803-MPU                  OBJECT IDENTIFIER ::= { ibevtModuleSwitchType 2534 } -- Supervisor Engine Board
ibevtModuleSw-S7806-MPU                  OBJECT IDENTIFIER ::= { ibevtModuleSwitchType 2535 } -- Supervisor Engine Board
ibevtModuleSw-S78-16XF24GF               OBJECT IDENTIFIER ::= { ibevtModuleSwitchType 2536 } -- 24-Port 1000BASE-R Ethernet Optical Interface(SFP,LC)+16-Port 10GBASE-R Ethernet Optical Interface Board(SFP+,LC)
ibevtModuleSw-S78-24GF8GT                OBJECT IDENTIFIER ::= { ibevtModuleSwitchType 2537 } -- 8-Port 10/100/1000BASE-T Ethernet Interface Board(RJ45)+24-Port 1000BASE-X Ethernet SFP Optical Interface(SFP,LC)
ibevtModuleSw-S78-24GT20GF4XF            OBJECT IDENTIFIER ::= { ibevtModuleSwitchType 2538 } -- 24-Port 10/100/1000BASE-T Ethernet Interface Board(RJ45)+20-Port 1000BASE-X Ethernet SFP Optical Interface(SFP,LC)+4-Port 10GBASE-R Optical Interface Board(SFP+,LC)
ibevtModuleSw-S78-24GT8GF                OBJECT IDENTIFIER ::= { ibevtModuleSwitchType 2539 } -- 24-Port 10/100/1000BASE-T Ethernet Interface Board(RJ45)+8-Port 1000BASE-X Ethernet SFP Optical Interface(SFP,LC)
ibevtModuleSw-S78-48GF                   OBJECT IDENTIFIER ::= { ibevtModuleSwitchType 2540 } -- 48-Port 1000BASE-X Ethernet Optical Interface Board(SFP,LC)
ibevtModuleSw-S78-48GT                   OBJECT IDENTIFIER ::= { ibevtModuleSwitchType 2541 } -- 48-Port 10/100/1000BASE-T Ethernet Interface Board(RJ45)
ibevtModuleSw-LSWM124SFPP                OBJECT IDENTIFIER ::= { ibevtModuleSwitchType 2542 } -- 24-Port SFP+ Interface Module
ibevtModuleSw-LSWM124MUPWR               OBJECT IDENTIFIER ::= { ibevtModuleSwitchType 2543 } -- 24-Port 10G PoE++ multi-speed Interface Module
ibevtModuleSwLSWM2XMGT2PM                OBJECT IDENTIFIER ::= { ibevtModuleSwitchType 2544 } -- 2*1G/2.5G/5G/10G BASE-T Ethernet Interface Board(RJ45)
ibevtModuleSw-LSCM2GV48SC0-Z             OBJECT IDENTIFIER ::= { ibevtModuleSwitchType 2545 } -- 48-Port 10/100/1000BASE-T Ethernet Interface Board(RJ45)(SC)-POE
ibevtModuleSw-LSCM2GT24GPTSSD0           OBJECT IDENTIFIER ::= { ibevtModuleSwitchType 2546 } -- 24-Port 10/100/1000BASE-T Ethernet Interface Board(RJ45)+20-Port 1000BASE-X Ethernet SFP Optical Interface(SFP,LC)+4-Port 10GBASE-R Optical Interface Board(SFP+,LC)(SD)
ibevtModuleSw-LSCM2GT24GPSD0             OBJECT IDENTIFIER ::= { ibevtModuleSwitchType 2547 } -- 24-Port 10/100/1000BASE-T Ethernet Interface Board(RJ45)+8-Port 1000BASE-X Ethernet SFP Optical Interface(SFP,LC)(SD)
ibevtModuleSw-LSCM2GP24GTSD0             OBJECT IDENTIFIER ::= { ibevtModuleSwitchType 2548 } -- 8-Port 10/100/1000BASE-T Ethernet Interface Board(RJ45)+24-Port 1000BASE-X Ethernet SFP Optical Interface(SFP,LC)(SD)
ibevtModuleSw-LSCM2GT48SD0               OBJECT IDENTIFIER ::= { ibevtModuleSwitchType 2549 } -- 48-Port 10/100/1000BASE-T Ethernet Interface Board(RJ45)(SD)
ibevtModuleSw-LSCM2GP48SD0               OBJECT IDENTIFIER ::= { ibevtModuleSwitchType 2550 } -- 48-Port 1000BASE-X Ethernet Optical Interface Board(SFP,LC)
ibevtModuleSw-LSCM2TGS16GPSD0            OBJECT IDENTIFIER ::= { ibevtModuleSwitchType 2551 } -- 24-Port 1000BASE-R Ethernet Optical Interface(SFP,LC)+16-Port 10GBASE-R Ethernet Optical Interface Board(SFP+,LC)
ibevtModuleSw-LSCM2GV48SD0               OBJECT IDENTIFIER ::= { ibevtModuleSwitchType 2552 } -- 48-Port 10/100/1000BASE-T Ethernet Interface Board(RJ45)(SD)-POE
ibevtModuleSw-LSCM2GT24GPTSSD0-Z         OBJECT IDENTIFIER ::= { ibevtModuleSwitchType 2553 } -- 24-Port 10/100/1000BASE-T Ethernet Interface Board(RJ45)+20-Port 1000BASE-X Ethernet SFP Optical Interface(SFP,LC)+4-Port 10GBASE-R Optical Interface Board(SFP+,LC)(SD)
ibevtModuleSw-LSCM2GT24GPSD0-Z           OBJECT IDENTIFIER ::= { ibevtModuleSwitchType 2554 } -- 24-Port 10/100/1000BASE-T Ethernet Interface Board(RJ45)+8-Port 1000BASE-X Ethernet SFP Optical Interface(SFP,LC)(SD)
ibevtModuleSw-LSCM2GP24GTSD0-Z           OBJECT IDENTIFIER ::= { ibevtModuleSwitchType 2555 } -- 8-Port 10/100/1000BASE-T Ethernet Interface Board(RJ45)+24-Port 1000BASE-X Ethernet SFP Optical Interface(SFP,LC)(SD)
ibevtModuleSw-LSCM2GT48SD0-Z             OBJECT IDENTIFIER ::= { ibevtModuleSwitchType 2556 } -- 48-Port 10/100/1000BASE-T Ethernet Interface Board(RJ45)(SD)
ibevtModuleSw-LSCM2GP48SD0-Z             OBJECT IDENTIFIER ::= { ibevtModuleSwitchType 2557 } -- 48-Port 1000BASE-X Ethernet Optical Interface Board(SFP,LC)
ibevtModuleSw-LSCM2TGS16GPSD0-Z          OBJECT IDENTIFIER ::= { ibevtModuleSwitchType 2558 } -- 24-Port 1000BASE-R Ethernet Optical Interface(SFP,LC)+16-Port 10GBASE-R Ethernet Optical Interface Board(SFP+,LC)
ibevtModuleSw-LSCM2GV48SD0-Z             OBJECT IDENTIFIER ::= { ibevtModuleSwitchType 2559 } -- 48-Port 10/100/1000BASE-T Ethernet Interface Board(RJ45)(SD)-POE
ibevtModuleSw-LSUM1TGT24FD0-Z            OBJECT IDENTIFIER ::= { ibevtModuleSwitchType 2560 } -- 24-Port 10GBASE-T Ethernet Copper Interface Module(RJ45)(FD)
ibevtModuleSw-LSXM1TGS24XT24C4Q2TE2      OBJECT IDENTIFIER ::= { ibevtModuleSwitchType 2561 } -- 24-Port 10G Ethernet Optical Interface(SFP+)+4-Port 100G Ethernet Optical Interface(QSFP28)+24-Port 10G/1000BASE-T Ethernet Copper Interface(RJ45)+2-Port 40G Ethernet Optical Interface Module(QSFP+)
ibevtModuleSw-CSFC-16T-GZ                OBJECT IDENTIFIER ::= { ibevtModuleSwitchType 2562 } -- CR16000-F Fabric Module(T Type-GZ)
ibevtModuleSw-CSPEX-2612X                OBJECT IDENTIFIER ::= { ibevtModuleSwitchType 2563 } -- Service Processing Unit(2612X)
ibevtModuleSw-CSPEX-2612XA               OBJECT IDENTIFIER ::= { ibevtModuleSwitchType 2564 } -- Service Processing Unit(2612XA)
ibevtModuleSw-CEPC-CQ8L1A                OBJECT IDENTIFIER ::= { ibevtModuleSwitchType 2565 } -- 8-port 100G Ethernet Optical Interface Line Processing Unit A(QSFP28,LC)
ibevtModuleSw-CEPC-CQ8L1                 OBJECT IDENTIFIER ::= { ibevtModuleSwitchType 2566 } -- 8-port 100G Ethernet Optical Interface Line Processing Unit(QSFP28,LC)
ibevtModuleSw-CEPC-CQ12L                 OBJECT IDENTIFIER ::= { ibevtModuleSwitchType 2567 } -- 12-port 100G Ethernet Optical Interface Line Processing Unit(QSFP28,LC)
ibevtModuleSw-CEPC-CQ16L                 OBJECT IDENTIFIER ::= { ibevtModuleSwitchType 2568 } -- 16-port 100G Ethernet Optical Interface Line Processing Unit(QSFP28,LC)
ibevtModuleSw-CEPC-CQ16L1                OBJECT IDENTIFIER ::= { ibevtModuleSwitchType 2569 } -- 16-port 100G Ethernet Optical Interface Line Processing Unit(QSFP28,LC)
ibevtModuleSw-ZD-S7803M-MPU-24T4X        OBJECT IDENTIFIER ::= { ibevtModuleSwitchType 2570 }  -- Supervisor Engine Board With 24-Port 10/100/1000BASE-T Ethernet Interface+4-Port 10GBASE-R Ethernet SFP+ Optical Interfaces
ibevtModuleSw-ZD-S7803M-MPU-24F4X        OBJECT IDENTIFIER ::= { ibevtModuleSwitchType 2571 }  -- Supervisor Engine Board With 24-Port 1000BASE-X Ethernet SFP Optical Interface+4-Port 10GBASE-R Ethernet SFP+ Optical Interfaces
ibevtModuleSw-ZD-S7800-24T8F-SC          OBJECT IDENTIFIER ::= { ibevtModuleSwitchType 2572 }  -- 24-Port 10/100/1000BASE-T Ethernet Interface Board(RJ45)+8-Port 1000BASE-X Ethernet SFP Optical Interface(SFP,LC)(SC)
ibevtModuleSw-ZD-S7800-48T-SC            OBJECT IDENTIFIER ::= { ibevtModuleSwitchType 2573 }  -- 48-Port 10/100/1000BASE-T Ethernet Interface Board(RJ45)(SC)
ibevtModuleSw-ZD-S7800-48F-SC            OBJECT IDENTIFIER ::= { ibevtModuleSwitchType 2574 }  -- 48-Port 1000BASE-X Ethernet Optical Interface Board(SFP,LC)
ibevtModuleSw-DS-3E7803M-MPU-24T4X       OBJECT IDENTIFIER ::= { ibevtModuleSwitchType 2575 }  -- Supervisor Engine Board With 24-Port 10/100/1000BASE-T Ethernet Interface+4-Port 10GBASE-R Ethernet SFP+ Optical Interfaces
ibevtModuleSw-DS-3E7803M-MPU-24F4X       OBJECT IDENTIFIER ::= { ibevtModuleSwitchType 2576 }  -- Supervisor Engine Board With 24-Port 1000BASE-X Ethernet SFP Optical Interface+4-Port 10GBASE-R Ethernet SFP+ Optical Interfaces
ibevtModuleSw-LSXM1SUPFH1                OBJECT IDENTIFIER ::= { ibevtModuleSwitchType 2577 }  -- S12500G-EF Supervisor Engine Unit,Half-Width
ibevtModuleSw-LSXM1SFP08F1               OBJECT IDENTIFIER ::= { ibevtModuleSwitchType 2578 }  -- S12508G-EF Fabric Module,Type P(Class F)
ibevtModuleSw-LSXM1CGQ18PB1              OBJECT IDENTIFIER ::= { ibevtModuleSwitchType 2579 }  -- S12500G-EF 18-Port 100GBASE Ethernet Optical Interface Module(QSFP28)(PB)
ibevtModuleSw-LSXM1QGS36PB1              OBJECT IDENTIFIER ::= { ibevtModuleSwitchType 2580 }  -- S12500G-EF 36-Port 40GBASE Ethernet Optical Interface Module(QSFP+)(PB)
ibevtModuleSw-LSXM1SUPFHA1               OBJECT IDENTIFIER ::= { ibevtModuleSwitchType 2581 }  -- S12500G-EF AI Supervisor Engine Unit,Half-Width
ibevtModuleSw-LSXM1SEERBA2               OBJECT IDENTIFIER ::= { ibevtModuleSwitchType 2582 }  -- High Performance Compute Engine Module
ibevtModuleSw-LSEM1SF08C0                OBJECT IDENTIFIER ::= { ibevtModuleSwitchType 2583 }  -- Switch Fabric Board
ibevtModuleSw-LSEM1TGS48QSSF0            OBJECT IDENTIFIER ::= { ibevtModuleSwitchType 2584 }  -- 48-Port 10G Ethernet Optical Interface(SFP+)+4-Port 40G Ethernet Optical Interface Module (QSFP+)(SF)
ibevtModuleSw-LSEM1QGS16SF0              OBJECT IDENTIFIER ::= { ibevtModuleSwitchType 2585 }  -- 16-Port 40G Ethernet Optical Interface Ethernet Optical Interface Module (QSFP+)(SF)
ibevtModuleSw-LSEM1TGS16GP32SD0          OBJECT IDENTIFIER ::= { ibevtModuleSwitchType 2586 }  -- 16-Port 10G Ethernet Optical Interface (SFP+)+32-Port 1000BASE Ethernet Optical Interface Module (SFP)(SD)
ibevtModuleSw-LSEM1SF08C0-Z              OBJECT IDENTIFIER ::= { ibevtModuleSwitchType 2587 }  -- Switch Fabric Board
ibevtModuleSw-LSEM1TGS48QSSF0-Z          OBJECT IDENTIFIER ::= { ibevtModuleSwitchType 2588 }  -- 48-Port 10G Ethernet Optical Interface(SFP+)+4-Port 40G Ethernet Optical Interface Module (QSFP+)(SF)
ibevtModuleSw-LSEM1QGS16SF0-Z            OBJECT IDENTIFIER ::= { ibevtModuleSwitchType 2589 }  -- 16-Port 40G Ethernet Optical Interface Ethernet Optical Interface Module (QSFP+)(SF)
ibevtModuleSw-LSEM1TGS16GP32SD0-Z        OBJECT IDENTIFIER ::= { ibevtModuleSwitchType 2590 }  -- 16-Port 10G Ethernet Optical Interface (SFP+)+32-Port 1000BASE Ethernet Optical Interface Module (SFP)(SD)
ibevtModuleSw-LSEM1SUPA0-Z               OBJECT IDENTIFIER ::= { ibevtModuleSwitchType 2591 }  -- Supervisor Engine Board
ibevtModuleSw-LSEM1SF06D0-Z              OBJECT IDENTIFIER ::= { ibevtModuleSwitchType 2592 }  -- Switch Fabric Board
ibevtModuleSw-LSEM1GT48TSSD0-Z           OBJECT IDENTIFIER ::= { ibevtModuleSwitchType 2593 }  -- 48-Port 10/100/1000BASE-T Electrical Interface(RJ45)+4-Port 10GBASE-R Ethernet Optical Interface Board(SFP+,LC)(SD)
ibevtModuleSw-LSEM1TGS24SD0-Z            OBJECT IDENTIFIER ::= { ibevtModuleSwitchType 2594 }  -- 24-Port 10GBASE-R Ethernet SFP+ Optical Interface Board(SD)
ibevtModuleSw-LSEM1TGS48SD0-Z            OBJECT IDENTIFIER ::= { ibevtModuleSwitchType 2595 }  -- 48-Port 10GBASE-R Ethernet SFP+ Optical Interface Board(SD)
ibevtModuleSw-LSEM1SUPB0-Z               OBJECT IDENTIFIER ::= { ibevtModuleSwitchType 2596 }  -- Supervisor Engine Board
ibevtModuleSw-LSEM1SF12B0-Z              OBJECT IDENTIFIER ::= { ibevtModuleSwitchType 2597 }  -- Switching Fabric Module
ibevtModuleSw-LSEM1YGS48CQSF0-Z          OBJECT IDENTIFIER ::= { ibevtModuleSwitchType 2598 }  -- 48-Port 25G Ethernet Optical Interface(SFP28,LC)+4-Port 100G Ethernet Optical Interface Module(QSFP28)
ibevtModuleSw-LSEM1CGQ16SF0-Z            OBJECT IDENTIFIER ::= { ibevtModuleSwitchType 2599 }  -- 16-Port 100G Ethernet Optical Interface Module(QSFP28)
ibevtModuleSw-LSEM1RCGQ2TSSF0            OBJECT IDENTIFIER ::= { ibevtModuleSwitchType 2600 }  -- 2-Port 100G RPR Optical Interface(QSFP28)+16-Port 10G Ethernet Optical Interface Module(SFP+)(SF)
ibevtModuleSw-LSEM1RCGQ2TSSF0-Z          OBJECT IDENTIFIER ::= { ibevtModuleSwitchType 2601 }  -- 2-Port 100G RPR Optical Interface(QSFP28)+16-Port 10G Ethernet Optical Interface Module(SFP+)(SF)
ibevtModuleSw-LSEM3RCGQ2TSSF0            OBJECT IDENTIFIER ::= { ibevtModuleSwitchType 2602 }  -- 2-Port 100G RPR Optical Interface(QSFP28)+16-Port 10G Ethernet Optical Interface Module(SFP+)(SF)
ibevtModuleSw-LSEM3SF08C0                OBJECT IDENTIFIER ::= { ibevtModuleSwitchType 2603 }  -- Switch Fabric Board
ibevtModuleSw-LSEM3TGS48QSSF0            OBJECT IDENTIFIER ::= { ibevtModuleSwitchType 2604 }  -- 48-Port 10G Ethernet Optical Interface(SFP+)+4-Port 40G Ethernet Optical Interface Module (QSFP+)(SF)
ibevtModuleSw-LSEM3QGS16SF0              OBJECT IDENTIFIER ::= { ibevtModuleSwitchType 2605 }  -- 16-Port 40G Ethernet Optical Interface Ethernet Optical Interface Module (QSFP+)(SF)
ibevtModuleSw-LSEM3TGS16GP32SD0          OBJECT IDENTIFIER ::= { ibevtModuleSwitchType 2606 }  -- 16-Port 10G Ethernet Optical Interface (SFP+)+32-Port 1000BASE Ethernet Optical Interface Module (SFP)(SD)
ibevtModuleSw-LSEM3SUPA0                 OBJECT IDENTIFIER ::= { ibevtModuleSwitchType 2607 }  -- Supervisor Engine Board
ibevtModuleSw-LSEM3SF06D0                OBJECT IDENTIFIER ::= { ibevtModuleSwitchType 2608 }  -- Switch Fabric Board
ibevtModuleSw-LSEM3GT48TSSD0             OBJECT IDENTIFIER ::= { ibevtModuleSwitchType 2609 }  -- 48-Port 10/100/1000BASE-T Electrical Interface(RJ45)+4-Port 10GBASE-R Ethernet Optical Interface Board(SFP+,LC)(SD)
ibevtModuleSw-LSEM3TGS24SD0              OBJECT IDENTIFIER ::= { ibevtModuleSwitchType 2610 }  -- 24-Port 10GBASE-R Ethernet SFP+ Optical Interface Board(SD)
ibevtModuleSw-LSEM3TGS48SD0              OBJECT IDENTIFIER ::= { ibevtModuleSwitchType 2611 }  -- 48-Port 10GBASE-R Ethernet SFP+ Optical Interface Board(SD)
ibevtModuleSw-LSEM3SUPB0                 OBJECT IDENTIFIER ::= { ibevtModuleSwitchType 2612 }  -- Supervisor Engine Board
ibevtModuleSw-LSEM3SF12B0                OBJECT IDENTIFIER ::= { ibevtModuleSwitchType 2613 }  -- Switching Fabric Module
ibevtModuleSw-LSEM3YGS48CQSF0            OBJECT IDENTIFIER ::= { ibevtModuleSwitchType 2614 }  -- 48-Port 25G Ethernet Optical Interface(SFP28,LC)+4-Port 100G Ethernet Optical Interface Module(QSFP28)
ibevtModuleSw-LSEM3CGQ16SF0              OBJECT IDENTIFIER ::= { ibevtModuleSwitchType 2615 }  -- 16-Port 100G Ethernet Optical Interface Module(QSFP28)
ibevtModuleSw-MIC-CQ1L2-Z                OBJECT IDENTIFIER ::= { ibevtModuleSwitchType 2616 } -- 1-port 100G  Ethernet Optical Interface Card A(QSFP28)
ibevtModuleSw-MIC-GP10L2                 OBJECT IDENTIFIER ::= { ibevtModuleSwitchType 2617 }  -- 10-Port 1000BASE-X Ethernet Optical Interface Card(SFP,LC)
ibevtModuleSw-LSCM1FWDSD0                OBJECT IDENTIFIER ::= { ibevtModuleSwitchType 2618 } -- SecBlade IV Next Generation Firewall
ibevtModuleSw-LSCM2FWDSD0                OBJECT IDENTIFIER ::= { ibevtModuleSwitchType 2619 } -- SecBlade IV Next Generation Firewall
ibevtModuleSw-LSCM2CGS8QS8SF0            OBJECT IDENTIFIER ::= { ibevtModuleSwitchType 2620 } -- 8-Port 40G Ethernet Optical Interface(QSFP+)+8-Port 100G Ethernet Optical Interface Module(QSFP28)(SF)
ibevtModuleSw-LSCM2TGS16GP32SD0          OBJECT IDENTIFIER ::= { ibevtModuleSwitchType 2621 } -- 32-Port 1000BASE Ethernet Optical Interface(SFP)+16-Port 10G Ethernet Optical Interface Module(SFP+)(SD)
ibevtModuleSw-LSCM2TGS48SF0              OBJECT IDENTIFIER ::= { ibevtModuleSwitchType 2622 } -- 48-Port 10G Ethernet Optical Interface Module(SFP+)(SF)
ibevtModuleSw-LSCM2YGS16TS8SF0           OBJECT IDENTIFIER ::= { ibevtModuleSwitchType 2623 } -- 16-Port 25G Ethernet Optical Interface(SFP28)+8-Port 10G Ethernet Optical Interface Module(SFP+)(SF)
ibevtModuleSw-LSCM2YGS32TS16SF0          OBJECT IDENTIFIER ::= { ibevtModuleSwitchType 2624 } -- 32-Port 25G Ethernet Optical Interface(SFP28)+16-Port 10G Ethernet Optical Interface Module(SFP+)(SF)
ibevtModuleSw-LSCM2SRP6C4Y06A0           OBJECT IDENTIFIER ::= { ibevtModuleSwitchType 2625 } -- Main Processing Unit with Switching and Routing With 4-Port 25G Ethernet Optical Interface(SFP28)+6-Port 100G Ethernet Optical Interfaces(QSFP28)
ibevtModuleSw-LSXM1SUPRS2                OBJECT IDENTIFIER ::= { ibevtModuleSwitchType 2626 } -- Supervisor Engine Unit
ibevtModuleSw-LSXM1CMURS2                OBJECT IDENTIFIER ::= { ibevtModuleSwitchType 2627 } -- Switch Environment Management Module
ibevtModuleSw-LSCM1FWDSD0-Z              OBJECT IDENTIFIER ::= { ibevtModuleSwitchType 2628 } -- SecBlade IV Next Generation Firewall
ibevtModuleSw-LSCM2FWDSD0-Z              OBJECT IDENTIFIER ::= { ibevtModuleSwitchType 2629 } -- SecBlade IV Next Generation Firewall
ibevtModuleSw-LSCM2CGS8QS8SF0-Z          OBJECT IDENTIFIER ::= { ibevtModuleSwitchType 2630 } -- 8-Port 40G Ethernet Optical Interface(QSFP+)+8-Port 100G Ethernet Optical Interface Module(QSFP28)(SF)
ibevtModuleSw-LSCM2TGS16GP32SD0-Z        OBJECT IDENTIFIER ::= { ibevtModuleSwitchType 2631 } -- 32-Port 1000BASE Ethernet Optical Interface(SFP)+16-Port 10G Ethernet Optical Interface Module(SFP+)(SD)
ibevtModuleSw-LSCM2TGS48SF0-Z            OBJECT IDENTIFIER ::= { ibevtModuleSwitchType 2632 } -- 48-Port 10G Ethernet Optical Interface Module(SFP+)(SF)
ibevtModuleSw-LSCM2YGS16TS8SF0-Z         OBJECT IDENTIFIER ::= { ibevtModuleSwitchType 2633 } -- 16-Port 25G Ethernet Optical Interface(SFP28)+8-Port 10G Ethernet Optical Interface Module(SFP+)(SF)
ibevtModuleSw-LSCM2YGS32TS16SF0-Z        OBJECT IDENTIFIER ::= { ibevtModuleSwitchType 2634 } -- 32-Port 25G Ethernet Optical Interface(SFP28)+16-Port 10G Ethernet Optical Interface Module(SFP+)(SF)
ibevtModuleSw-LSCM2SRP6C4Y06A0-Z         OBJECT IDENTIFIER ::= { ibevtModuleSwitchType 2635 } -- Main Processing Unit with Switching and Routing With 4-Port 25G Ethernet Optical Interface(SFP28)+6-Port 100G Ethernet Optical Interfaces(QSFP28)
ibevtModuleSw-LSXM1CGQFX16KBR1           OBJECT IDENTIFIER ::= { ibevtModuleSwitchType 2636 } -- 16-Port 100GBASE FlexE Ethernet Optical Interface Module(QSFP28)
ibevtModuleSw-LSXM1CGMS48KBR1            OBJECT IDENTIFIER ::= { ibevtModuleSwitchType 2637 } -- 48-Port 100GBASE MACsec Ethernet Optical Interface Module (QSFP28)
ibevtModuleSw-LSXM1CDMS36KCR1            OBJECT IDENTIFIER ::= { ibevtModuleSwitchType 2638 } -- 36-Port 400GBASE MACsec Ethernet Optical Interface Module (QSFP-DD)(KC)
ibevtModuleSw-LSXM1SUPEAR1               OBJECT IDENTIFIER ::= { ibevtModuleSwitchType 2639 } -- AI Supervisor Engine Unit
ibevtModuleSw-LSXM1SUPKAR1               OBJECT IDENTIFIER ::= { ibevtModuleSwitchType 2640 } -- AI Supervisor Engine Unit
ibevtModuleSw-MIC-GP10L2-Z               OBJECT IDENTIFIER ::= { ibevtModuleSwitchType 2641 } -- 10-Port 1000BASE-X Ethernet Optical Interface Card(SFP,LC)
ibevtModuleSw-IE-Module-8G               OBJECT IDENTIFIER ::= { ibevtModuleSwitchType 2642 } -- 8*SFP
ibevtModuleSw-IE-Module-8P               OBJECT IDENTIFIER ::= { ibevtModuleSwitchType 2643 } -- 8*GE
ibevtModuleSw-IE-Module-4G4P             OBJECT IDENTIFIER ::= { ibevtModuleSwitchType 2644 } -- 4*GE+4*SFP
ibevtModuleSw-LSXM1CDQ12PB1              OBJECT IDENTIFIER ::= { ibevtModuleSwitchType 2645 } -- S12500G-EF 12-Port 400GBASE Ethernet Optical Interface Module(QSFP-DD)(PB)
ibevtModuleSw-MIC-GT20L1                 OBJECT IDENTIFIER ::= { ibevtModuleSwitchType 2646 } -- 20-port 1000BASE-X Ethernet Copper Interface Card(RJ45)
ibevtModuleSw-MIC-XP10L-LAN              OBJECT IDENTIFIER ::= { ibevtModuleSwitchType 2647 } -- 10-port 10GBASE-R/W Ethernet Optical Interface Card Module(SFP+,LC)-LAN
ibevtModuleSw-MIC-SEC-M                  OBJECT IDENTIFIER ::= { ibevtModuleSwitchType 2648 } -- Network Data Encryption Interface Card(MIC-SEC-M)
ibevtModuleSw-MIC-GT20L1-Z               OBJECT IDENTIFIER ::= { ibevtModuleSwitchType 2649 } -- 20-port 1000BASE-X Ethernet Copper Interface Card Z(RJ45)
ibevtModuleSw-MIC-XP10L-LAN-Z            OBJECT IDENTIFIER ::= { ibevtModuleSwitchType 2650 } -- 10-port 10GBASE-R/W Ethernet Optical Interface Card Module(SFP+,LC)-LAN-Z
ibevtModuleSw-MIC-SEC-M-Z                OBJECT IDENTIFIER ::= { ibevtModuleSwitchType 2651 } -- Network Data Encryption Interface Card(MIC-SEC-M-Z)
ibevtModuleSw-LSXM3TGT48CQSF2            OBJECT IDENTIFIER ::= { ibevtModuleSwitchType 2652 } -- 48-Port 10GBASE-T Ethernet Copper Interface(RJ45)+2-Port 100G Ethernet Optical Interface Module(QSFP28)
ibevtModuleSw-LSDM3TGT48CQSF0-Z          OBJECT IDENTIFIER ::= { ibevtModuleSwitchType 2653 } -- 48-Port 10GBASE-T Ethernet Copper Interface(RJ45)+2-Port 100G Ethernet Optical Interface Module(QSFP28)
ibevtModuleSw-LSEM1GV48TSSD0             OBJECT IDENTIFIER ::= { ibevtModuleSwitchType 2654 } -- 48-Port 10/100/1000BASE-T Ethernet Copper Interface(RJ45)+4-Port 10G Ethernet Optical Interface Module(SFP+),PoE Plus
ibevtModuleSw-LSEM1GV48TSSD0-Z           OBJECT IDENTIFIER ::= { ibevtModuleSwitchType 2655 } -- 48-Port 10/100/1000BASE-T Ethernet Copper Interface(RJ45)+4-Port 10G Ethernet Optical Interface Module(SFP+),PoE Plus
ibevtModuleSw-LSEM1GT24GP16TSSD0         OBJECT IDENTIFIER ::= { ibevtModuleSwitchType 2656 } -- 24-Port 10/100/1000BASE-T Ethernet Copper Interface(RJ45)+16-Port 1000BASE Ethernet Optical Interface(SFP)+12-Port 10G Ethernet Optical Interface Module(SFP+)
ibevtModuleSw-LSEM1TGT48SD0              OBJECT IDENTIFIER ::= { ibevtModuleSwitchType 2657 } -- 48-Port 10GBASE-T Ethernet Copper Interface(RJ45)
ibevtModuleSw-LSEM1CGQ36SF0              OBJECT IDENTIFIER ::= { ibevtModuleSwitchType 2658 } -- 36-Port 100G Ethernet Optical Interface Module(QSFP28)
ibevtModuleSw-LSEM1CDQ2SF0               OBJECT IDENTIFIER ::= { ibevtModuleSwitchType 2659 } -- 2-Port 400G Ethernet Optical Interface Module(QSFP-DD)
ibevtModuleSw-LSEM1GT48TS24QSSD0         OBJECT IDENTIFIER ::= { ibevtModuleSwitchType 2660 } -- 48-Port 10/100/1000BASE-T Ethernet Copper Interface(RJ45)+24-Port 10G Ethernet Optical Interface(SFP+)+2-Port 40G Ethernet Optical Interface Module(QSFP+)
ibevtModuleSw-CSPEX-2612X-E              OBJECT IDENTIFIER ::= { ibevtModuleSwitchType 2661 } -- Service Processing Unit(2612X-E)
ibevtModuleSw-SR05SRP1P3-DZEC            OBJECT IDENTIFIER ::= { ibevtModuleSwitchType 2662 } -- DZEC Main Processing Unit(1P3)
ibevtModuleSw-RT-FIP-680-G               OBJECT IDENTIFIER ::= { ibevtModuleSwitchType 2663 } -- Network Processing Unit(G)
ibevtModuleSw-LSCM3YGS32TS16SF0          OBJECT IDENTIFIER ::= { ibevtModuleSwitchType 2664 } -- 32-Port 25G Ethernet Optical Interface(SFP28)+16-Port 10G Ethernet Optical Interface Module(SFP+)(SF)
ibevtModuleSw-LSCM3TGS48SF0              OBJECT IDENTIFIER ::= { ibevtModuleSwitchType 2665 } -- 48-Port 10G Ethernet Optical Interface Module(SFP+)(SF)
ibevtModuleSw-LSCM3YGS16TS8SF0           OBJECT IDENTIFIER ::= { ibevtModuleSwitchType 2666 } -- 16-Port 25G Ethernet Optical Interface(SFP28)+8-Port 10G Ethernet Optical Interface Module(SFP+)(SF)
ibevtModuleSw-LSCM3CGS8QS8SF0            OBJECT IDENTIFIER ::= { ibevtModuleSwitchType 2667 } -- 8-Port 40G Ethernet Optical Interface(QSFP+)+8-Port 100G Ethernet Optical Interface Module(QSFP28)(SF)
ibevtModuleSw-LSCM3SRP6C4Y06A0           OBJECT IDENTIFIER ::= { ibevtModuleSwitchType 2668 } -- Main Processing Unit with Switching and Routing With 4-Port 25G Ethernet Optical Interface(SFP28)+6-Port 100G Ethernet Optical Interfaces(QSFP28)
ibevtModuleSw-LSCM3YGS32TS16SF0-Z        OBJECT IDENTIFIER ::= { ibevtModuleSwitchType 2669 } -- 32-Port 25G Ethernet Optical Interface(SFP28)+16-Port 10G Ethernet Optical Interface Module(SFP+)(SF)
ibevtModuleSw-LSCM3TGS48SF0-Z            OBJECT IDENTIFIER ::= { ibevtModuleSwitchType 2670 } -- 48-Port 10G Ethernet Optical Interface Module(SFP+)(SF)
ibevtModuleSw-LSCM3YGS16TS8SF0-Z         OBJECT IDENTIFIER ::= { ibevtModuleSwitchType 2671 } -- 16-Port 25G Ethernet Optical Interface(SFP28)+8-Port 10G Ethernet Optical Interface Module(SFP+)(SF)
ibevtModuleSw-LSCM3CGS8QS8SF0-Z          OBJECT IDENTIFIER ::= { ibevtModuleSwitchType 2672 } -- 8-Port 40G Ethernet Optical Interface(QSFP+)+8-Port 100G Ethernet Optical Interface Module(QSFP28)(SF)
ibevtModuleSw-LSCM2TGS16GP32SC0-Z        OBJECT IDENTIFIER ::= { ibevtModuleSwitchType 2673 } -- 32-Port 1000BASE Ethernet Optical Interface(SFP)+16-Port 10G Ethernet Optical Interface Module(SFP+)(SC)
ibevtModuleSw-LSCM3SRP6C4Y06A0-Z         OBJECT IDENTIFIER ::= { ibevtModuleSwitchType 2674 } -- Main Processing Unit with Switching and Routing With 4-Port 25G Ethernet Optical Interface(SFP28)+6-Port 100G Ethernet Optical Interfaces(QSFP28)
ibevtModuleSw-LSXM1SUPCH1                OBJECT IDENTIFIER ::= { ibevtModuleSwitchType 2675 } -- Supervisor Engine Board
ibevtModuleSw-LSXM1SFC08C1               OBJECT IDENTIFIER ::= { ibevtModuleSwitchType 2676 } -- Switch Fabric Board
ibevtModuleSw-LSXM1TGS48CA1              OBJECT IDENTIFIER ::= { ibevtModuleSwitchType 2677 } -- 48-Port 10G Ethernet Optical Interface Module(SFP+)
ibevtModuleSw-LSXM1CGQ18CA1              OBJECT IDENTIFIER ::= { ibevtModuleSwitchType 2678 } -- 18-Port 100G Ethernet Optical Interface Module(QSFP28)
ibevtModuleSw-LSXM1QGS36CA1              OBJECT IDENTIFIER ::= { ibevtModuleSwitchType 2679 } -- 36-Port 40G Ethernet Optical Interface Module(QSFP+)
ibevtModuleSw-LSXM3SUPCH1                OBJECT IDENTIFIER ::= { ibevtModuleSwitchType 2680 } -- Supervisor Engine Board
ibevtModuleSw-LSXM3TGS48CA1              OBJECT IDENTIFIER ::= { ibevtModuleSwitchType 2681 } -- 48-Port 10G Ethernet Optical Interface Module(SFP+)
ibevtModuleSw-LSXM3CGQ18CA1              OBJECT IDENTIFIER ::= { ibevtModuleSwitchType 2682 } -- 18-Port 100G Ethernet Optical Interface Module(QSFP28)
ibevtModuleSw-LSXM3QGS36CA1              OBJECT IDENTIFIER ::= { ibevtModuleSwitchType 2683 } -- 36-Port 40G Ethernet Optical Interface Module(QSFP+)
ibevtModuleSw-MIC-SEC                    OBJECT IDENTIFIER ::= { ibevtModuleSwitchType 2684 } -- Network Data Encryption Interface Card(MIC-SEC)
ibevtModuleSw-MIC-SEC-Z                  OBJECT IDENTIFIER ::= { ibevtModuleSwitchType 2685 } -- Network Data Encryption Interface Card(MIC-SEC-Z)
ibevtModuleSw-MIC-XP12LF                 OBJECT IDENTIFIER ::= { ibevtModuleSwitchType 2686 } -- 12-port 10GBASE-R/W Ethernet Optical Interface Card Module(SFP+,LC)
ibevtModuleSw-MIC-XP12LF-Z               OBJECT IDENTIFIER ::= { ibevtModuleSwitchType 2687 } -- 12-port 10GBASE-R/W Ethernet Optical Interface Card Module(SFP+,LC)
ibevtModuleSw-MIC-CQ1LF                  OBJECT IDENTIFIER ::= { ibevtModuleSwitchType 2688 } -- 2-port 100G Flexible Ethernet Optical Interface Card(QSFP28,LC)
ibevtModuleSw-MIC-CQ1LF-Z                OBJECT IDENTIFIER ::= { ibevtModuleSwitchType 2689 } -- 2-port 100G Flexible Ethernet Optical Interface Card(QSFP28,LC)
ibevtModuleSw-SR07IPUA3-M                OBJECT IDENTIFIER ::= { ibevtModuleSwitchType 2690 } -- CR16000-M Management and Route Process Board(UA3-M)
ibevtModuleSw-LSXM1SUPS1                 OBJECT IDENTIFIER ::= { ibevtModuleSwitchType 2691 } -- Supervisor Engine Board
ibevtModuleSw-LSXM1CGQ36S1               OBJECT IDENTIFIER ::= { ibevtModuleSwitchType 2692 } -- 36-Port 100GBASE-R Ethernet Optical Interface Board(QSFP28,LC)
ibevtModuleSw-LSEM3SUPA3                 OBJECT IDENTIFIER ::= { ibevtModuleSwitchType 2693 } -- Supervisor Engine Board
ibevtModuleSw-LSEM1SF06D3                OBJECT IDENTIFIER ::= { ibevtModuleSwitchType 2694 } -- Switch Fabric Board
ibevtModuleSw-LSEM1SF08C3                OBJECT IDENTIFIER ::= { ibevtModuleSwitchType 2695 } -- Switch Fabric Board
ibevtModuleSw-LSEM3CGQ8SF3               OBJECT IDENTIFIER ::= { ibevtModuleSwitchType 2696 } -- 8-Port 100G Ethernet Optical Interface Module(QSFP28)
ibevtModuleSw-LSEM3TGS48SF3              OBJECT IDENTIFIER ::= { ibevtModuleSwitchType 2697 } -- 48-Port 10GBASE-R Ethernet SFP+ Optical Interface Board(SF)
ibevtModuleSw-LSEM1GT48SD3               OBJECT IDENTIFIER ::= { ibevtModuleSwitchType 2698 } -- 48-Port 10/100/1000BASE-T Electrical Interface Board(RJ45)(SD)
ibevtModuleSw-LSEM2GP48SD3               OBJECT IDENTIFIER ::= { ibevtModuleSwitchType 2699 } -- 48-Port 1000BASE-X Optical Interface Board(SFP,LC)
ibevtModuleSw-MIC-XP10LF                 OBJECT IDENTIFIER ::= { ibevtModuleSwitchType 2700 } -- 10-port 10GBASE-R/W Ethernet Optical Interface Card Module(SFP+,LC)
ibevtModuleSw-MIC-XP10LF-Z               OBJECT IDENTIFIER ::= { ibevtModuleSwitchType 2701 } -- 10-port 10GBASE-R/W Ethernet Optical Interface Card Module(SFP+,LC)
ibevtModuleSw-DS-3E12508X-MPU            OBJECT IDENTIFIER ::= { ibevtModuleSwitchType 2702 } -- Supervisor Engine Board
ibevtModuleSw-DS-3E12508X-CLOS           OBJECT IDENTIFIER ::= { ibevtModuleSwitchType 2703 } -- Switching Fabric Module
ibevtModuleSw-DS-3E12512X-MPU            OBJECT IDENTIFIER ::= { ibevtModuleSwitchType 2704 } -- Supervisor Engine Board
ibevtModuleSw-DS-3E12512X-CLOS           OBJECT IDENTIFIER ::= { ibevtModuleSwitchType 2705 } -- Switching Fabric Module
ibevtModuleSw-DS-3E12500X-48T4X-SD       OBJECT IDENTIFIER ::= { ibevtModuleSwitchType 2706 } -- 48-Port 10/100/1000BASE-T Electrical Interface(RJ45)+4-Port 10GBASE-R Ethernet Optical Interface Board(SFP+,LC)(SD)
ibevtModuleSw-DS-3E12500X-48X-SD         OBJECT IDENTIFIER ::= { ibevtModuleSwitchType 2707 } -- 48-Port 10GBASE-R Ethernet SFP+ Optical Interface Board(SD)
ibevtModuleSw-DS-3E12500X-48Y4C-SF       OBJECT IDENTIFIER ::= { ibevtModuleSwitchType 2708 } -- 48-Port 25G Ethernet Optical Interface(SFP28,LC)+4-Port 100G Ethernet Optical Interface Module(QSFP28)
ibevtModuleSw-DS-3E12500X-16C-SF         OBJECT IDENTIFIER ::= { ibevtModuleSwitchType 2709 } -- 16-Port 100G Ethernet Optical Interface Module(QSFP28)
ibevtModuleSw-DS-3E12500X-16Q-SF         OBJECT IDENTIFIER ::= { ibevtModuleSwitchType 2710 } -- 16-Port 40G Ethernet Optical Interface Ethernet Optical Interface Module (QSFP+)(SF)
ibevtModuleSw-DS-3E12500X-32F16X-SD      OBJECT IDENTIFIER ::= { ibevtModuleSwitchType 2711 } -- 16-Port 10G Ethernet Optical Interface (SFP+)+32-Port 1000BASE Ethernet Optical Interface Module (SFP)(SD)
ibevtModuleSw-LSWM1M4CDC                 OBJECT IDENTIFIER ::= { ibevtModuleSwitchType 2712 } -- 4-Port 400GBASE Ethernet Optical Interface Module(QSFP-DD)
ibevtModuleSw-LSEM2TGS48SD0              OBJECT IDENTIFIER ::= { ibevtModuleSwitchType 2713 } -- 48-Port 10GBASE-R Ethernet SFP+ Optical Interface Board(SD)
ibevtModuleSw-LSEM1SF06B0                OBJECT IDENTIFIER ::= { ibevtModuleSwitchType 2714 } -- Switch Fabric Board
ibevtModuleSw-LSXM3SFS08H2               OBJECT IDENTIFIER ::= { ibevtModuleSwitchType 2715 } -- Switch Fabric Board
ibevtModuleSw-LSXM3SFS16H2               OBJECT IDENTIFIER ::= { ibevtModuleSwitchType 2716 } -- Switch Fabric Board
ibevtModuleSw-LSXM4CGQ36SF2              OBJECT IDENTIFIER ::= { ibevtModuleSwitchType 2717 } -- 36-Port 100GBASE-R Ethernet Optical Interface Board(QSFP28,LC)
ibevtModuleSw-LSEM2TGS48SD0-Z            OBJECT IDENTIFIER ::= { ibevtModuleSwitchType 2718 } -- 48-Port 10GBASE-R Ethernet SFP+ Optical Interface Board(SD)
ibevtModuleSw-LSEM1SF06B0-Z              OBJECT IDENTIFIER ::= { ibevtModuleSwitchType 2719 } -- Switch Fabric Board
ibevtModuleSw-LSDM3SFS08H2-Z             OBJECT IDENTIFIER ::= { ibevtModuleSwitchType 2720 } -- Switch Fabric Board
ibevtModuleSw-LSDM3SFS16H2-Z             OBJECT IDENTIFIER ::= { ibevtModuleSwitchType 2721 } -- Switch Fabric Board
ibevtModuleSw-LSDM4CGQ36SF2-Z            OBJECT IDENTIFIER ::= { ibevtModuleSwitchType 2722 } -- 36-Port 100GBASE-R Ethernet Optical Interface Board(QSFP28,LC)
ibevtModuleSw-LSUM1MPUS06XEB8            OBJECT IDENTIFIER ::= { ibevtModuleSwitchType 2723 } -- Supervisor Engine Board
ibevtModuleSw-LSUM1MPUS10XEA8            OBJECT IDENTIFIER ::= { ibevtModuleSwitchType 2724 } -- Supervisor Engine Board
ibevtModuleSw-LSUM1CGS8SH8               OBJECT IDENTIFIER ::= { ibevtModuleSwitchType 2725 } -- 8-Port 100G Ethernet Optical Interface Module(QSFP28)(SH)
ibevtModuleSw-LSUM2GT48SE8               OBJECT IDENTIFIER ::= { ibevtModuleSwitchType 2726 } -- 48-Port 1000Base-T Gigabit Ethernet Interface Board(RJ45)(SE)
ibevtModuleSw-LSUM2GT24PTSSE8            OBJECT IDENTIFIER ::= { ibevtModuleSwitchType 2727 } -- 24-Port 1000Base-T Gigabit Ethernet Interface Board(RJ45)+20-Port GE Optical Interface(SFP,LC)+4-Port 10GE Optical Interface Board(SFP+,LC)(SE)
ibevtModuleSw-LSUM2GP44TSSE8             OBJECT IDENTIFIER ::= { ibevtModuleSwitchType 2728 } -- 44-Port GE Optical Interface(SFP,LC)+4-Port 10GE Optical Interface Board(SFP+,LC)(SE)
ibevtModuleSw-CSPEX-2304X-LG             OBJECT IDENTIFIER ::= { ibevtModuleSwitchType 2729 } -- Network Processing Unit(2304X-LG)
ibevtModuleSw-CEPC-DQ2L1-G               OBJECT IDENTIFIER ::= { ibevtModuleSwitchType 2730 } -- 2-port 400G Ethernet Optical Interface Line Processing Unit(QSFP28,LC)
ibevtModuleSw-SRFP-A3                    OBJECT IDENTIFIER ::= { ibevtModuleSwitchType 2731 } -- CR16000-M Management and Route Process Board(A3)
ibevtModuleSw-LSXM2SUP02LR1              OBJECT IDENTIFIER ::= { ibevtModuleSwitchType 2732 } -- Supervisor Engine Unit
ibevtModuleSw-LSXM2CGQ48KBR1             OBJECT IDENTIFIER ::= { ibevtModuleSwitchType 2733 } -- 48-Port 100GBASE Ethernet Optical Interface Module(QSFP28)(KB)
ibevtModuleSw-LSXM3QGS36SF1              OBJECT IDENTIFIER ::= { ibevtModuleSwitchType 2734 } -- 36-Port 40G Ethernet Optical Interface Module (QSFP+)
ibevtModuleSw-LSXM3TGS48SF1              OBJECT IDENTIFIER ::= { ibevtModuleSwitchType 2735 } -- 48-Port 10GBASE-R Ethernet SFP+ Optical Interface Board(SF)
ibevtModuleSw-CSPEX-2502X                OBJECT IDENTIFIER ::= { ibevtModuleSwitchType 2736 } -- Network Processing Unit(2502X)
ibevtModuleSw-LSWM2QP2PB                 OBJECT IDENTIFIER ::= { ibevtModuleSwitchType 2737 } -- 2-Port QSFP+ Interface Module
ibevtModuleSw-MPUC-1P3                   OBJECT IDENTIFIER ::= { ibevtModuleSwitchType 2738 } -- DNR20008C-DN Main Processing Unit(1P3)
ibevtModuleSw-FSUC-1802X                 OBJECT IDENTIFIER ::= { ibevtModuleSwitchType 2739 } -- Service Processing Unit(1802X)
ibevtModuleSw-SFUC-08E1                  OBJECT IDENTIFIER ::= { ibevtModuleSwitchType 2740 } -- DNR20008C-DN Fabric Module(E Type)
ibevtModuleSw-ICC-CQ2LF                  OBJECT IDENTIFIER ::= { ibevtModuleSwitchType 2741 } -- 2-port 100G Flexible Ethernet Optical Interface Card(QSFP28,LC)
ibevtModuleSw-ICC-XP20L1                 OBJECT IDENTIFIER ::= { ibevtModuleSwitchType 2742 } -- 20-port 10GBASE-R/W Ethernet Optical Interface Card(SFP+,LC)(NIC)
ibevtModuleSw-MPUM-A3                    OBJECT IDENTIFIER ::= { ibevtModuleSwitchType 2743 } -- DNR20008M-DN Management and Route Process Board(UA3-M)
ibevtModuleSw-SFUM-A                     OBJECT IDENTIFIER ::= { ibevtModuleSwitchType 2744 } -- Network Processing Unit(A)
ibevtModuleSw-ICM-CQ1LF                  OBJECT IDENTIFIER ::= { ibevtModuleSwitchType 2745 } -- 1-port 100G Flexible Ethernet Optical Interface Card(QSFP28,LC)
ibevtModuleSw-ICM-XP10L1                 OBJECT IDENTIFIER ::= { ibevtModuleSwitchType 2746 } -- 10-port 10GBASE-R/W Ethernet Optical Interface Card Module(SFP+,LC)
ibevtModuleSw-LSCM2XPT24SF0              OBJECT IDENTIFIER ::= { ibevtModuleSwitchType 2747 } -- 24-Port 10G EPON OLT Optical Interface Board(SFP+,SC)
ibevtModuleSw-LSCM2XPG24SF0              OBJECT IDENTIFIER ::= { ibevtModuleSwitchType 2748 } -- 24-Port XGS-PON OLT Optical Interface Board(SFP+,SC)
ibevtModuleSw-MIC-XP2L-M                 OBJECT IDENTIFIER ::= { ibevtModuleSwitchType 2749 } -- 2-Port 10GBASE-R/W Ethernet Optical Interface Card (SFP+,LC)
ibevtModuleSw-MIC-XP2L-M-Z               OBJECT IDENTIFIER ::= { ibevtModuleSwitchType 2750 } -- 2-Port 10GBASE-R/W Ethernet Optical Interface Card (SFP+,LC)
ibevtModuleSwLS5M1IEXG4                  OBJECT IDENTIFIER ::= { ibevtModuleSwitchType 2751 } -- IE-Module-4X 4-Port 1G/10G BASE-X Interface Module
ibevtModuleSw-MIC-XP5L2                  OBJECT IDENTIFIER ::= { ibevtModuleSwitchType 2752 } -- 5-Port 10GBASE-R/W Ethernet Optical Interface Card,(SFP+,LC)
ibevtModuleSw-CSR05SRP051E3-G            OBJECT IDENTIFIER ::= { ibevtModuleSwitchType 2753 } -- CR16000-F Management and Route Process Board(1E3-G)
ibevtModuleSw-CSR05SRP101E3-G            OBJECT IDENTIFIER ::= { ibevtModuleSwitchType 2754 } -- CR16000-F Management and Route Process Board(1E3-G)
ibevtModuleSw-CSFC-10T-G                 OBJECT IDENTIFIER ::= { ibevtModuleSwitchType 2755 } -- CR16000-F Fabric Module(T Type-G)
ibevtModuleSw-LSUM1FAB06XEB3             OBJECT IDENTIFIER ::= { ibevtModuleSwitchType 2756 } -- Switch Fabric Board
ibevtModuleSw-LSUM2GP40TS8FD3            OBJECT IDENTIFIER ::= { ibevtModuleSwitchType 2757 } -- 40-Port 1000BASE-X Optical Interface(SFP,LC)+8-Port 10GBASE-R Ethernet Optical Interface Board(SFP+,LC)
ibevtModuleSw-LSEM1GT48TS24QSSD0-Z       OBJECT IDENTIFIER ::= { ibevtModuleSwitchType 2758 } -- 48-Port 10/100/1000BASE-T Ethernet Copper Interface(RJ45)+24-Port 10G Ethernet Optical Interface(SFP+)+2-Port 40G Ethernet Optical Interface Module(QSFP+)
ibevtModuleSw-LSEM1CGQ36SF0-Z            OBJECT IDENTIFIER ::= { ibevtModuleSwitchType 2759 } -- 36-Port 100G Ethernet Optical Interface Module(QSFP28)
ibevtModuleSw-LSEM1TGT48SD0-Z            OBJECT IDENTIFIER ::= { ibevtModuleSwitchType 2760 } -- 48-Port 10GBASE-T Ethernet Copper Interface(RJ45)
ibevtModuleSw-LSEM3CDQ2SF0               OBJECT IDENTIFIER ::= { ibevtModuleSwitchType 2761 } -- 2-Port 400G Ethernet Optical Interface Module(QSFP-DD)
ibevtModuleSw-LSEM3CGQ36SF0              OBJECT IDENTIFIER ::= { ibevtModuleSwitchType 2762 } -- 36-Port 100G Ethernet Optical Interface Module(QSFP28)
ibevtModuleSw-LSEM3QGS36SF0              OBJECT IDENTIFIER ::= { ibevtModuleSwitchType 2763 } -- 36-Port 40G Ethernet Optical Interface Module(QSFP+)
ibevtModuleSw-LSEM1QGS36SF0              OBJECT IDENTIFIER ::= { ibevtModuleSwitchType 2764 } -- 36-Port 40G Ethernet Optical Interface Module(QSFP+)
ibevtModuleSw-S16700X-G-MPU              OBJECT IDENTIFIER ::= { ibevtModuleSwitchType 2765 } -- Supervisor Engine Board
ibevtModuleSw-S16706X-G-NET              OBJECT IDENTIFIER ::= { ibevtModuleSwitchType 2766 } -- Switch Fabric Board
ibevtModuleSw-S16708X-G-NET              OBJECT IDENTIFIER ::= { ibevtModuleSwitchType 2767 } -- Switch Fabric Board
ibevtModuleSw-S16700-48GT4XFSD           OBJECT IDENTIFIER ::= { ibevtModuleSwitchType 2768 } -- 48-Port 10/100/1000BASE-T Electrical Interface(RJ45)+4-Port 10GBASE-R Ethernet Optical Interface Board(SFP+,LC)(SD)
ibevtModuleSw-S16700-48XFSD              OBJECT IDENTIFIER ::= { ibevtModuleSwitchType 2769 } -- 48-Port 10GBASE-R Ethernet SFP+ Optical Interface Board(SD)
ibevtModuleSw-S16700-16QFSF              OBJECT IDENTIFIER ::= { ibevtModuleSwitchType 2770 } -- 16-Port 40G Ethernet Optical Interface Ethernet Optical Interface Module (QSFP+)(SF)
ibevtModuleSw-S16700-32GF16XFSD          OBJECT IDENTIFIER ::= { ibevtModuleSwitchType 2771 } -- 16-Port 10G Ethernet Optical Interface (SFP+)+32-Port 1000BASE Ethernet Optical Interface Module (SFP)(SD)
ibevtModuleSw-LSCM3MPUS10C0              OBJECT IDENTIFIER ::= { ibevtModuleSwitchType 2772 } -- Supervisor Engine Board
ibevtModuleSw-LSCM3MPUS10C0-Z            OBJECT IDENTIFIER ::= { ibevtModuleSwitchType 2773 } -- Supervisor Engine Board
ibevtModuleSw-LSXM2TGS48TD2              OBJECT IDENTIFIER ::= { ibevtModuleSwitchType 2774 } -- 48-Port 10G Ethernet Optical Interface Module(SFP+)
ibevtModuleSw-LSCM2YSV16TSV32SD0         OBJECT IDENTIFIER ::= { ibevtModuleSwitchType 2775 } -- 32-Port 10G Ethernet Optical Interface(SFP+)+16-Port 25G Ethernet Optical Interface Module(SFP28)(SD)
ibevtModuleSw-LSCM2GP40TS8SD0            OBJECT IDENTIFIER ::= { ibevtModuleSwitchType 2776 } -- 40-Port 1000BASE Ethernet Optical Interface(SFP)+8-Port 10G Ethernet Optical Interface Module(SFP+)(SD)
ibevtModuleSw-LSCM2GT24TSSD0             OBJECT IDENTIFIER ::= { ibevtModuleSwitchType 2777 } -- 24-Port 10/100/1000BASE-T Ethernet Interface Board(RJ45)+4-Port 10GBASE-R Optical Interface Board(SFP+,LC)(SD)
ibevtModuleSw-LSCM3TGS32GP16SF0          OBJECT IDENTIFIER ::= { ibevtModuleSwitchType 2778 } -- 16-Port 1000BASE Ethernet Optical Interface(SFP)+32-Port 10G Ethernet Optical Interface Module(SFP+)(SF)
ibevtModuleSw-LSEM2TGS16GP32SD0          OBJECT IDENTIFIER ::= { ibevtModuleSwitchType 2779 } -- 32-Port 1000BASE Ethernet Optical Interface(SFP)+16-Port 10G Ethernet Optical Interface Module(SFP+)(SD)
ibevtModuleSw-DS-3E12500X-24T16F12X-SD   OBJECT IDENTIFIER ::= { ibevtModuleSwitchType 2780 } -- 24-Port 10/100/1000BASE-T Ethernet Copper Interface(RJ45)+16-Port 1000BASE Ethernet Optical Interface(SFP)+12-Port 10G Ethernet Optical Interface Module(SFP+)
ibevtModuleSw-DS-3E7800-48X-SE           OBJECT IDENTIFIER ::= { ibevtModuleSwitchType 2781 } -- 48-Port 10GBASE-R Ethernet SFP+ Optical Interface Board(SE)
ibevtModuleSw-CSR05SRP1R3-G              OBJECT IDENTIFIER ::= { ibevtModuleSwitchType 2782 } -- CR16000-F Management and Route Process Board(1R3-G)
ibevtModuleSw-NIC-QP3L                   OBJECT IDENTIFIER ::= { ibevtModuleSwitchType 2783 } -- 3-port 40G Ethernet Optical Interface Card(QSFP+,LC)
ibevtModuleSwLS5M1IERS4C2-G              OBJECT IDENTIFIER ::= { ibevtModuleSwitchType 2787 } -- 4-RS485 Interface+2-CAN Interface Module
ibevtModuleSwLS5M1IEGT4GP4-G             OBJECT IDENTIFIER ::= { ibevtModuleSwitchType 2788 } -- 4-Port 10/100/1000BASE-T Ethernet Interface+4-Port 1000BASE-X Optical Interface(SFP,LC) Module
ibevtModuleSwLS5M1IEGT8-G                OBJECT IDENTIFIER ::= { ibevtModuleSwitchType 2789 } -- 8-Port 10/100/1000BASE-T Ethernet Interface Module
ibevtModuleSwLS5M1IEGP8-G                OBJECT IDENTIFIER ::= { ibevtModuleSwitchType 2790 } -- 8-Port 1000BASE-X Optical Interface(SFP,LC) Module
ibevtModuleSw-LSEM1TGV48SD0              OBJECT IDENTIFIER ::= { ibevtModuleSwitchType 2791 } -- 48-Port 10GBASE-T Ethernet Copper Interface(RJ45)
ibevtModuleSw-LSXM3YGS24XT24C6SF2        OBJECT IDENTIFIER ::= { ibevtModuleSwitchType 2792 } -- 24-Port 10GBASE-T Ethernet Copper Interface(RJ45)+24-Port 25G Ethernet Optical Interface(SFP28)+6-Port 100G Ethernet Optical Interface Module(QSFP28)(SF)
ibevtModuleSw-LSDM3YGS24XT24C6SF0-Z      OBJECT IDENTIFIER ::= { ibevtModuleSwitchType 2793 } -- 24-Port 10GBASE-T Ethernet Copper Interface(RJ45)+24-Port 25G Ethernet Optical Interface(SFP28)+6-Port 100G Ethernet Optical Interface Module(QSFP28)(SF)
ibevtModuleSw-LSXM3CGQ48SG2              OBJECT IDENTIFIER ::= { ibevtModuleSwitchType 2794 } -- 48-Port 100G Ethernet Optical Interface Module(QSFP28)
ibevtModuleSw-LSDM3CGQ48SG0-Z            OBJECT IDENTIFIER ::= { ibevtModuleSwitchType 2795 } -- 48-Port 100G Ethernet Optical Interface Module(QSFP28)
ibevtModuleSw-LSEM5TGS48QSSF0            OBJECT IDENTIFIER ::= { ibevtModuleSwitchType 2796 } -- 48-Port 10G Ethernet Optical Interface(SFP+)+4-Port 40G Ethernet Optical Interface Module (QSFP+)(SF)
ibevtModuleSw-LSEM5TGS48QSSF0-Z          OBJECT IDENTIFIER ::= { ibevtModuleSwitchType 2797 } -- 48-Port 10G Ethernet Optical Interface(SFP+)+4-Port 40G Ethernet Optical Interface Module (QSFP+)(SF)
ibevtModuleSw-LSCM5TGS48SF0              OBJECT IDENTIFIER ::= { ibevtModuleSwitchType 2798 } -- 48-Port 10G Ethernet Optical Interface Module(SFP+)(SF)
ibevtModuleSw-LSCM5TGS48SF0-Z            OBJECT IDENTIFIER ::= { ibevtModuleSwitchType 2799 } -- 48-Port 10G Ethernet Optical Interface Module(SFP+)(SF)
ibevtModuleSw-SRFP-A1                    OBJECT IDENTIFIER ::= { ibevtModuleSwitchType 2800 } -- CR16000-M Management and Route Process Board(A1)
ibevtModuleSw-MIC-ET16L-G                OBJECT IDENTIFIER ::= { ibevtModuleSwitchType 2801 } -- 16-Port E1/T1 Electrical Interface Card
ibevtModuleSw-MIC-CQ1L-G                 OBJECT IDENTIFIER ::= { ibevtModuleSwitchType 2802 } -- 1-port 100G Ethernet Optical Interface Card Module(QSFP28,LC)
ibevtModuleSw-MIC-TCP8L-G                OBJECT IDENTIFIER ::= { ibevtModuleSwitchType 2803 } -- SR8800-X, SR0MDTCP8LA1,8-port OC-3c/OC-12c POS Optical Interface Card(SFP,LC),Domestic&Overseas Version
ibevtModuleSw-MIC-CLP2L-G                OBJECT IDENTIFIER ::= { ibevtModuleSwitchType 2804 } -- 2-Port OC-3/STM-1 CPOS/POS Optical Interface Card,(SFP,LC)
ibevtModuleSw-CSPEX-2314X-G              OBJECT IDENTIFIER ::= { ibevtModuleSwitchType 2805 } -- Network Processing Unit(2314X-G)
ibevtModuleSw-CSFC-08E2A                 OBJECT IDENTIFIER ::= { ibevtModuleSwitchType 2806 } -- CR16000-F Fabric Module(E2A Type)
ibevtModuleSw-CSFC-16E2A                 OBJECT IDENTIFIER ::= { ibevtModuleSwitchType 2807 } -- CR16018-F Fabric Module(E2A Type)
ibevtModuleSw-MIC-XP12L-G                OBJECT IDENTIFIER ::= { ibevtModuleSwitchType 2808 } -- 12-Port 10GBASE-R/W Ethernet Optical Interface Card,(SFP+,LC)
ibevtModuleSw-MIC-XP6L-G                 OBJECT IDENTIFIER ::= { ibevtModuleSwitchType 2809 } -- 6-Port 10GBASE-R/W Ethernet Optical Interface Card,(SFP+,LC)
ibevtModuleSw-MIC-XP4L-G                 OBJECT IDENTIFIER ::= { ibevtModuleSwitchType 2810 } -- 4-Port 10GBASE-R/W Ethernet Optical Interface Card,(SFP+,LC)
ibevtModuleSw-MIC-GP12L-G                OBJECT IDENTIFIER ::= { ibevtModuleSwitchType 2811 } -- 12-Port 1000BASE-X Ethernet Optical Interface Card(SFP,LC)
ibevtModuleSw-RX-NIC-YGS8L               OBJECT IDENTIFIER ::= { ibevtModuleSwitchType 2812 } -- 8-port 25G Ethernet Optical Interface Card(SFP28,LC)
ibevtModuleSw-CSPEX-2104X-G              OBJECT IDENTIFIER ::= { ibevtModuleSwitchType 2883 } -- Network Processing Unit(2104X-G)
ibevtModuleSw-CEPC-CQ8L3A                OBJECT IDENTIFIER ::= { ibevtModuleSwitchType 2884 } -- 8-port 100G Ethernet Optical Interface Line Processing Unit A(QSFP28,LC)
ibevtModuleSw-CSPEX-2612X3A              OBJECT IDENTIFIER ::= { ibevtModuleSwitchType 2885 } -- Service Processing Unit(2612X3A)
ibevtModuleSw-CSFC-10E-G                 OBJECT IDENTIFIER ::= { ibevtModuleSwitchType 2886 } -- CR16000-F Fabric Module(T Type-G)
-- Here define submodule for routers
ibevtSubModuleRouter       OBJECT IDENTIFIER ::= { ibevtModule 5 }


-- Here define submodule for switches
ibevtSubModuleSwitch       OBJECT IDENTIFIER ::= { ibevtModule 6 }
-- Here define Compact Flash
ibevtModuleCFCard          OBJECT IDENTIFIER ::= { ibevtModule 7 }

-- Here define Secure Digital Memory Card
ibevtModuleSDCard          OBJECT IDENTIFIER ::= { ibevtModule 8 }

--
-- ibevtPort section:
--
ibevtPort          OBJECT IDENTIFIER ::= { ibEntityVendortypeObjects 10 }

ibevtPortUnknownPorts      OBJECT IDENTIFIER ::= { ibevtPort 1 }
ibevtPortCommonPorts       OBJECT IDENTIFIER ::= { ibevtPort 2 }
ibevtPortRouterType        OBJECT IDENTIFIER ::= { ibevtPort 3 }
ibevtPortSwitchType        OBJECT IDENTIFIER ::= { ibevtPort 4 }


-- Below are ports used to router
ibevtPortRt-Async          OBJECT IDENTIFIER ::= { ibevtPortRouterType 1 }    -- Async interface
ibevtPortRt-Analogmodem    OBJECT IDENTIFIER ::= { ibevtPortRouterType 2 }    -- Analog modem interface
ibevtPortRt-Atm            OBJECT IDENTIFIER ::= { ibevtPortRouterType 3 }
ibevtPortRt-AtmAdsl        OBJECT IDENTIFIER ::= { ibevtPortRouterType 4 }
ibevtPortRt-AtmShdsl       OBJECT IDENTIFIER ::= { ibevtPortRouterType 5 }
ibevtPortRt-AtmE1          OBJECT IDENTIFIER ::= { ibevtPortRouterType 6 }
ibevtPortRt-AtmT1          OBJECT IDENTIFIER ::= { ibevtPortRouterType 7 }
ibevtPortRt-AtmE3          OBJECT IDENTIFIER ::= { ibevtPortRouterType 8 }
ibevtPortRt-AtmT3          OBJECT IDENTIFIER ::= { ibevtPortRouterType 9 }
ibevtPortRt-Atm622M        OBJECT IDENTIFIER ::= { ibevtPortRouterType 10 }
ibevtPortRt-AtmImaE1       OBJECT IDENTIFIER ::= { ibevtPortRouterType 11 }
ibevtPortRt-AtmImaT1       OBJECT IDENTIFIER ::= { ibevtPortRouterType 12 }
ibevtPortRt-Atm25M         OBJECT IDENTIFIER ::= { ibevtPortRouterType 13 }
ibevtPortRt-Bri            OBJECT IDENTIFIER ::= { ibevtPortRouterType 14 }
ibevtPortRt-Console        OBJECT IDENTIFIER ::= { ibevtPortRouterType 15 }
ibevtPortRt-E1             OBJECT IDENTIFIER ::= { ibevtPortRouterType 16 }
ibevtPortRt-E3             OBJECT IDENTIFIER ::= { ibevtPortRouterType 17 }
ibevtPortRt-T1             OBJECT IDENTIFIER ::= { ibevtPortRouterType 18 }
ibevtPortRt-T3             OBJECT IDENTIFIER ::= { ibevtPortRouterType 19 }
ibevtPortRt-Cpos           OBJECT IDENTIFIER ::= { ibevtPortRouterType 20 }
ibevtPortRt-Ethernet       OBJECT IDENTIFIER ::= { ibevtPortRouterType 21 }
ibevtPortRt-Serial         OBJECT IDENTIFIER ::= { ibevtPortRouterType 22 }
ibevtPortRt-E1f            OBJECT IDENTIFIER ::= { ibevtPortRouterType 23 }
ibevtPortRt-T1f            OBJECT IDENTIFIER ::= { ibevtPortRouterType 24 }
ibevtPortRt-Pos            OBJECT IDENTIFIER ::= { ibevtPortRouterType 25 }
ibevtPortRt-Ge             OBJECT IDENTIFIER ::= { ibevtPortRouterType 26 }
ibevtPortRt-Aux            OBJECT IDENTIFIER ::= { ibevtPortRouterType 27 }
-- ibevtPortRt-Null         OBJECT IDENTIFIER ::= { ibevtPortRouterType 28 }   reserved
-- ibevtPortRt-Max          OBJECT IDENTIFIER ::= { ibevtPortRouterType 29 }   reserved
ibevtPortRt-VG-Fxs         OBJECT IDENTIFIER ::= { ibevtPortRouterType 30 }
ibevtPortRt-VG-Fxo         OBJECT IDENTIFIER ::= { ibevtPortRouterType 31 }
ibevtPortRt-VG-E1vi        OBJECT IDENTIFIER ::= { ibevtPortRouterType 32 }
ibevtPortRt-VG-T1vi        OBJECT IDENTIFIER ::= { ibevtPortRouterType 33 }
ibevtPortRt-Usb            OBJECT IDENTIFIER ::= { ibevtPortRouterType 34 }
ibevtPortRt-Ndec           OBJECT IDENTIFIER ::= { ibevtPortRouterType 35 }   -- NDEC port, Encrypt card version 1.0
ibevtPortRt-Cavium         OBJECT IDENTIFIER ::= { ibevtPortRouterType 36 }   -- NDEC port, Encrypt card version 2.0
ibevtPortRt-Fcm            OBJECT IDENTIFIER ::= { ibevtPortRouterType 37 }   -- POS/Fast connect module port
ibevtPortRt-E1vi           OBJECT IDENTIFIER ::= { ibevtPortRouterType 38 }   -- E1VI port
ibevtPortRt-T1vi           OBJECT IDENTIFIER ::= { ibevtPortRouterType 39 }   -- T1VI port
ibevtPortRt-Vi             OBJECT IDENTIFIER ::= { ibevtPortRouterType 40 }   -- Voice port
ibevtPortRt-Adls2Plus      OBJECT IDENTIFIER ::= { ibevtPortRouterType 41 }   -- ADSL2Plus port
ibevtPortRt-RADIO-AG       OBJECT IDENTIFIER ::= { ibevtPortRouterType 42 }   -- 802.11ag Radio port
ibevtPortRt-1exp           OBJECT IDENTIFIER ::= { ibevtPortRouterType 43 }   -- 10GBASE-R/W Ethernet port
ibevtPortRt-G-SHDSL-BIS    OBJECT IDENTIFIER ::= { ibevtPortRouterType 44 }   -- 4 wire G.SHDSL.BIS interface
ibevtPortRt-ONU-1000BASE-BX-SFF-SC    OBJECT IDENTIFIER ::= { ibevtPortRouterType 45 }   -- 1000 BASE-BX SFF SC ONU Interface
ibevtPortRt-CELLULAR       OBJECT IDENTIFIER ::= { ibevtPortRouterType 46 }   -- 3G Wireless WAN Interface
ibevtPortRt-CELLULAR-ETHERNET         OBJECT IDENTIFIER ::= { ibevtPortRouterType 47 }   -- 3G Wireless WAN Interface for Ethernet mode
ibevtPortRt-VGe            OBJECT IDENTIFIER ::= { ibevtPortRouterType 48 } -- virtual Ge port
ibevtPortRt-VXGe           OBJECT IDENTIFIER ::= { ibevtPortRouterType 49 } -- virtual XGe port
ibevtPortRt-Xpos           OBJECT IDENTIFIER ::= { ibevtPortRouterType 50 } -- 10G POS port
ibevtPortRt-Fge            OBJECT IDENTIFIER ::= { ibevtPortRouterType 51 } -- 40G Ethernet port
ibevtPortRt-XGe            OBJECT IDENTIFIER ::= { ibevtPortRouterType 52 } -- 10G Ethernet port
ibevtPortRt-HgeQsfp28Lc    OBJECT IDENTIFIER ::= { ibevtPortRouterType 53 } -- 100G Ethernet Port with QSFP28 Form Factor and LC Connector
ibevtPortRt-HgeCfp2Lc      OBJECT IDENTIFIER ::= { ibevtPortRouterType 54 } -- 100G Ethernet Port with CFP2 Form Factor and LC Connector
ibevtPortRt-HgeCfpLc       OBJECT IDENTIFIER ::= { ibevtPortRouterType 55 } -- 100G Ethernet Port with CFP Form Factor and LC Connector
ibevtPortRt-GeM12          OBJECT IDENTIFIER ::= { ibevtPortRouterType 56 } -- Gigabit Ethernet Port with M12 Form Connector
ibevtPortRt-VMEth          OBJECT IDENTIFIER ::= { ibevtPortRouterType 57 } -- Virtual Machine Ethernet Port
ibevtPortRt-FiberGe        OBJECT IDENTIFIER ::= { ibevtPortRouterType 58 } -- 1G Fiber Ethernet port
ibevtPortRt-GeOptic        OBJECT IDENTIFIER ::= { ibevtPortRouterType 59 }
ibevtPortRt-25Ge           OBJECT IDENTIFIER ::= { ibevtPortRouterType 60 } -- 25G Ethernet port with SFP28
ibevtPortRt-50Ge           OBJECT IDENTIFIER ::= { ibevtPortRouterType 61 } -- 50G Ethernet port with QSFP28
ibevtPortRt-FlexE-50-100G  OBJECT IDENTIFIER ::= { ibevtPortRouterType 62 } -- 50-100G FlexE port with QSFP28
ibevtPortRt-50-100Ge       OBJECT IDENTIFIER ::= { ibevtPortRouterType 63 } -- 50-100G Ethernet port with QSFP28
ibevtPortRt-FlexE          OBJECT IDENTIFIER ::= { ibevtPortRouterType 64 } -- FlexE port with QSFP28
ibevtPortRt-100Ge          OBJECT IDENTIFIER ::= { ibevtPortRouterType 65 } -- 100G Ethernet port with QSFP28
ibevtPortRt-FlexE-50G      OBJECT IDENTIFIER ::= { ibevtPortRouterType 66 } -- 50G FlexE port with QSFP28
ibevtPortRt-Async-Phoenix  OBJECT IDENTIFIER ::= { ibevtPortRouterType 67 } -- Async interface
ibevtPortRt-FlexE-100G     OBJECT IDENTIFIER ::= { ibevtPortRouterType 68 } -- 100G FlexE port with QSFP28
ibevtPortRt-QSFPDD-400GBASE-SR8    OBJECT IDENTIFIER ::= { ibevtPortRouterType 69 }  -- 400GBASE-SR8  QSFP-DD Optical Transceiver
ibevtPortRt-FiberGeCsfp    OBJECT IDENTIFIER ::= { ibevtPortRouterType 70 }  -- 1G Fiber Ethernet port

-- Below are ports used to switches
--ibevtPortSw-Unknown              OBJECT IDENTIFIER ::= { ibevtPortSwitchType 0 }
ibevtPortSw-10or100M               OBJECT IDENTIFIER ::= { ibevtPortSwitchType 1 }
ibevtPortSw-1000BaseLxSm           OBJECT IDENTIFIER ::= { ibevtPortSwitchType 2 }
ibevtPortSw-1000BaseSxMm           OBJECT IDENTIFIER ::= { ibevtPortSwitchType 3 }
ibevtPortSw-1000BaseTx             OBJECT IDENTIFIER ::= { ibevtPortSwitchType 4 }
ibevtPortSw-100MSinglemodeFx       OBJECT IDENTIFIER ::= { ibevtPortSwitchType 5 }
ibevtPortSw-100MMultimodeFx        OBJECT IDENTIFIER ::= { ibevtPortSwitchType 6 }
ibevtPortSw-100M100BaseTx          OBJECT IDENTIFIER ::= { ibevtPortSwitchType 7 }
ibevtPortSw-100MHub                OBJECT IDENTIFIER ::= { ibevtPortSwitchType 8 }
ibevtPortSw-Vdsl                   OBJECT IDENTIFIER ::= { ibevtPortSwitchType 9 }
ibevtPortSw-Stack                  OBJECT IDENTIFIER ::= { ibevtPortSwitchType 10 }
ibevtPortSw-1000BaseZenithFx       OBJECT IDENTIFIER ::= { ibevtPortSwitchType 11 }
ibevtPortSw-1000BaseLongFx         OBJECT IDENTIFIER ::= { ibevtPortSwitchType 12 }
ibevtPortSw-Adsl                   OBJECT IDENTIFIER ::= { ibevtPortSwitchType 13 }
ibevtPortSw-10or100MDb             OBJECT IDENTIFIER ::= { ibevtPortSwitchType 14 }
ibevtPortSw-10GBaseLrSm            OBJECT IDENTIFIER ::= { ibevtPortSwitchType 15 }
ibevtPortSw-10GBaseLx4Mm           OBJECT IDENTIFIER ::= { ibevtPortSwitchType 16 }
ibevtPortSw-10GBaseLx4Sm           OBJECT IDENTIFIER ::= { ibevtPortSwitchType 17 }
ibevtPortSw-100MLongFx             OBJECT IDENTIFIER ::= { ibevtPortSwitchType 18 }
ibevtPortSw-1000BaseCx             OBJECT IDENTIFIER ::= { ibevtPortSwitchType 19 }
ibevtPortSw-1000BaseZenithFxLc     OBJECT IDENTIFIER ::= { ibevtPortSwitchType 20 }
ibevtPortSw-1000BaseLongFxLc       OBJECT IDENTIFIER ::= { ibevtPortSwitchType 21 }
ibevtPortSw-100MSmFxSc             OBJECT IDENTIFIER ::= { ibevtPortSwitchType 22 }
ibevtPortSw-100MMmFxSc             OBJECT IDENTIFIER ::= { ibevtPortSwitchType 23 }
ibevtPortSw-100MSmFxLc             OBJECT IDENTIFIER ::= { ibevtPortSwitchType 24 }
ibevtPortSw-100MMmFxLc             OBJECT IDENTIFIER ::= { ibevtPortSwitchType 25 }
ibevtPortSw-GbicNoConnector        OBJECT IDENTIFIER ::= { ibevtPortSwitchType 26 }
ibevtPortSw-Gbic1000BaseT          OBJECT IDENTIFIER ::= { ibevtPortSwitchType 27 }
ibevtPortSw-Gbic1000BaseLx         OBJECT IDENTIFIER ::= { ibevtPortSwitchType 28 }
ibevtPortSw-Gbic1000BaseSx         OBJECT IDENTIFIER ::= { ibevtPortSwitchType 29 }
ibevtPortSw-Gbic1000BaseZx         OBJECT IDENTIFIER ::= { ibevtPortSwitchType 30 }
ibevtPortSw-ComboNoConnector       OBJECT IDENTIFIER ::= { ibevtPortSwitchType 31 }
ibevtPortSw-Combo1000BaseLx        OBJECT IDENTIFIER ::= { ibevtPortSwitchType 32 }
ibevtPortSw-Combo1000BaseLxFiber   OBJECT IDENTIFIER ::= { ibevtPortSwitchType 33 }
ibevtPortSw-Combo1000BaseLxCopper  OBJECT IDENTIFIER ::= { ibevtPortSwitchType 34 }
ibevtPortSw-Combo1000BaseSx        OBJECT IDENTIFIER ::= { ibevtPortSwitchType 35 }
ibevtPortSw-Combo1000BaseSxFiber   OBJECT IDENTIFIER ::= { ibevtPortSwitchType 36 }
ibevtPortSw-Combo1000BaseSxCopper  OBJECT IDENTIFIER ::= { ibevtPortSwitchType 37 }
ibevtPortSw-Combo1000BaseZx        OBJECT IDENTIFIER ::= { ibevtPortSwitchType 38 }
ibevtPortSw-Combo1000BaseZxFiber   OBJECT IDENTIFIER ::= { ibevtPortSwitchType 39 }
ibevtPortSw-Combo1000BaseZxCopper  OBJECT IDENTIFIER ::= { ibevtPortSwitchType 40 }
ibevtPortSw-155PosSxMmf            OBJECT IDENTIFIER ::= { ibevtPortSwitchType 41 }
ibevtPortSw-155PosLxSmf            OBJECT IDENTIFIER ::= { ibevtPortSwitchType 42 }

-- added by Garibaldi
ibevtPortSw-1000BASE-T             OBJECT IDENTIFIER ::= { ibevtPortSwitchType 43 }  -- 1000 Base-T Port
ibevtPortSw-1000BASE-SX-SFP        OBJECT IDENTIFIER ::= { ibevtPortSwitchType 44 }  -- 1000 Base-SX SFP Port
ibevtPortSw-1000BASE-LX-SFP        OBJECT IDENTIFIER ::= { ibevtPortSwitchType 45 }  -- 1000 Base-LX SFP Port
ibevtPortSw-1000BASE-T-AN-SFP      OBJECT IDENTIFIER ::= { ibevtPortSwitchType 46 }  -- 1000 Base-T AN SFP Port
ibevtPortSw-10GBASE-LX4-XENPAK     OBJECT IDENTIFIER ::= { ibevtPortSwitchType 47 }  -- 10G Base-LX4 XENPAK Port
ibevtPortSw-10GBASE-LR-XENPAK      OBJECT IDENTIFIER ::= { ibevtPortSwitchType 48 }  -- 10G Base-LR XENPAK Port
ibevtPortSw-10GBASE-CX4            OBJECT IDENTIFIER ::= { ibevtPortSwitchType 49 }  -- 10G Base-CX4 Port
ibevtPortSw-1000BASE-ZX-SFP        OBJECT IDENTIFIER ::= { ibevtPortSwitchType 50 }  -- 1000 Base-ZX SFP Port
ibevtPortSw-1000BASE-MM-SFP        OBJECT IDENTIFIER ::= { ibevtPortSwitchType 51 }  -- 1000 Base-MM SFP Port
ibevtPortSw-100BASE-SX-SFP         OBJECT IDENTIFIER ::= { ibevtPortSwitchType 52 }  -- 100 Base-SX SFP Port
ibevtPortSw-100BASE-LX-SFP         OBJECT IDENTIFIER ::= { ibevtPortSwitchType 53 }  -- 100 Base-LX SFP Port
ibevtPortSw-100BASE-T-AN-SFP       OBJECT IDENTIFIER ::= { ibevtPortSwitchType 54 }  -- 100 Base-T SFP Port
ibevtPortSw-100BASE-ZX-SFP         OBJECT IDENTIFIER ::= { ibevtPortSwitchType 55 }  -- 100 Base-ZX SFP Port
ibevtPortSw-100BASE-MM-SFP         OBJECT IDENTIFIER ::= { ibevtPortSwitchType 56 }  -- 100 Base-MM SFP Port
ibevtPortSw-SFP-NO-CONNECTOR       OBJECT IDENTIFIER ::= { ibevtPortSwitchType 57 }  -- No Connector SFP Port
ibevtPortSw-SFP-UNKNOWN-CONNECTOR  OBJECT IDENTIFIER ::= { ibevtPortSwitchType 58 }  -- Unknown SFP Port
ibevtPortSw-POS-NO-CONNECTOR       OBJECT IDENTIFIER ::= { ibevtPortSwitchType 59 }  -- POS no connector
ibevtPortSw-10G-BASE-SR            OBJECT IDENTIFIER ::= { ibevtPortSwitchType 60 }  -- 10GBASE-SR Fiber Optic Transceivers with SC Connector
ibevtPortSw-10G-BASE-ER            OBJECT IDENTIFIER ::= { ibevtPortSwitchType 61 }  -- 10GBASE-ER Fiber Optic Transceivers with SC Connector
ibevtPortSw-10G-BASE-LX4           OBJECT IDENTIFIER ::= { ibevtPortSwitchType 62 }  -- 10GBASE-LX4 Fiber Optic Transceivers with SC Connector
ibevtPortSw-10G-BASE-SW            OBJECT IDENTIFIER ::= { ibevtPortSwitchType 63 }  -- 10GBASE-SW Fiber Optic Transceivers with SC Connector
ibevtPortSw-10G-BASE-LW            OBJECT IDENTIFIER ::= { ibevtPortSwitchType 64 }  -- 10GBASE-LW Fiber Optic Transceivers with SC Connector
ibevtPortSw-10G-BASE-EW            OBJECT IDENTIFIER ::= { ibevtPortSwitchType 65 }  -- 10GBASE-EW Fiber Optic Transceivers with SC Connector
ibevtPortSw-10G-LR-SM-LC           OBJECT IDENTIFIER ::= { ibevtPortSwitchType 66 }  -- 10GBASE-LR Single Mode Fiber Optic Transceivers with LC Connector
ibevtPortSw-10G-SR-MM-LC           OBJECT IDENTIFIER ::= { ibevtPortSwitchType 67 }  -- 10GBASE-SR Multi Mode Fiber Optic Transceivers with LC Connector
ibevtPortSw-10G-ER-SM-LC           OBJECT IDENTIFIER ::= { ibevtPortSwitchType 68 }  -- 10GBASE-ER Single Mode Fiber Optic Transceivers with LC Connector
ibevtPortSw-10G-LW-SM-LC           OBJECT IDENTIFIER ::= { ibevtPortSwitchType 69 }  -- 10GBASE-LW Single Mode Fiber Optic Transceivers with LC Connector
ibevtPortSw-10G-SW-MM-LC           OBJECT IDENTIFIER ::= { ibevtPortSwitchType 70 }  -- 10GBASE-SW Multi Mode Fiber Optic Transceivers with LC Connector
ibevtPortSw-10G-EW-SM-LC           OBJECT IDENTIFIER ::= { ibevtPortSwitchType 71 }  -- 10GBASE-EW Single Mode Fiber Optic Transceivers with LC Connector
ibevtPortSw-100BASE-SM-MTRJ        OBJECT IDENTIFIER ::= { ibevtPortSwitchType 72 }  -- 100 Base-SM MTRJ Port
ibevtPortSw-100BASE-MM-MTRJ        OBJECT IDENTIFIER ::= { ibevtPortSwitchType 73 }  -- 100 Base-MM MTRJ Port
ibevtPortSw-XFP-NO-CONNECTOR       OBJECT IDENTIFIER ::= { ibevtPortSwitchType 74 }  -- XFP without Transceiver
ibevtPortSw-XFP-10GBASE-SR         OBJECT IDENTIFIER ::= { ibevtPortSwitchType 75 }  -- 10GBASE-SR XFP Transceiver
ibevtPortSw-XFP-10GBASE-LR         OBJECT IDENTIFIER ::= { ibevtPortSwitchType 76 }  -- 10GBASE-LR XFP Transceiver
ibevtPortSw-XFP-10GBASE-ER         OBJECT IDENTIFIER ::= { ibevtPortSwitchType 77 }  -- 10GBASE-ER XFP Transceiver
ibevtPortSw-XFP-10GBASE-SW         OBJECT IDENTIFIER ::= { ibevtPortSwitchType 78 }  -- 10GBASE-SW XFP Transceiver
ibevtPortSw-XFP-10GBASE-LW         OBJECT IDENTIFIER ::= { ibevtPortSwitchType 79 }  -- 10GBASE-LW XFP Transceiver
ibevtPortSw-XFP-10GBASE-EW         OBJECT IDENTIFIER ::= { ibevtPortSwitchType 80 }  -- 10GBASE-EW XFP Transceiver
ibevtPortSw-XFP-10GBASE-CX4        OBJECT IDENTIFIER ::= { ibevtPortSwitchType 81 }  -- 10GBASE-CX4 XFP Transceiver
ibevtPortSw-XFP-10GBASE-LX4        OBJECT IDENTIFIER ::= { ibevtPortSwitchType 82 }  -- 10GBASE-LX4 XFP Transceiver
ibevtPortSw-XFP-UNKNOWN            OBJECT IDENTIFIER ::= { ibevtPortSwitchType 83 }  -- Unknown  XFP Transceiver
ibevtPortSw-XPK-NOCONNECTOR        OBJECT IDENTIFIER ::= { ibevtPortSwitchType 84 }  -- Xenpak without Transceiver
ibevtPortSw-XPK-10GBASE-SR         OBJECT IDENTIFIER ::= { ibevtPortSwitchType 85 }  -- 10GBASE-SR Xenpak Transceiver
ibevtPortSw-XPK-10GBASE-LR         OBJECT IDENTIFIER ::= { ibevtPortSwitchType 86 }  -- 10GBASE-LR Xenpak Transceiver
ibevtPortSw-XPK-10GBASE-ER         OBJECT IDENTIFIER ::= { ibevtPortSwitchType 87 }  -- 10GBASE-ER Xenpak Transceiver
ibevtPortSw-XPK-10GBASE-SW         OBJECT IDENTIFIER ::= { ibevtPortSwitchType 88 }  -- 10GBASE-SW Xenpak Transceiver
ibevtPortSw-XPK-10GBASE-LW         OBJECT IDENTIFIER ::= { ibevtPortSwitchType 89 }  -- 10GBASE-LW Xenpak Transceiver
ibevtPortSw-XPK-10GBASE-EW         OBJECT IDENTIFIER ::= { ibevtPortSwitchType 90 }  -- 10GBASE-EW Xenpak Transceiver
ibevtPortSw-XPK-10GBASE-CX4        OBJECT IDENTIFIER ::= { ibevtPortSwitchType 91 }  -- 10GBASE-CX4 Xenpak Transceiver
ibevtPortSw-XPK-10GBASE-LX4        OBJECT IDENTIFIER ::= { ibevtPortSwitchType 92 }  -- 10GBASE-LX4 Xenpak Transceiver
ibevtPortSw-XPK-UNKNOWN            OBJECT IDENTIFIER ::= { ibevtPortSwitchType 93 }  -- Unknown Xenpak Transceiver
ibevtPortSw-POS-OC48-SR-SM-LC      OBJECT IDENTIFIER ::= { ibevtPortSwitchType 94 }  -- OC48-SR Single Mode Fiber Optic Transceivers with LC Connector
ibevtPortSw-POS-OC48-IR-SM-LC      OBJECT IDENTIFIER ::= { ibevtPortSwitchType 95 }  -- OC48-IR Single Mode Fiber Optic Transceivers with LC Connector
ibevtPortSw-POS-OC48-LR-SM-LC      OBJECT IDENTIFIER ::= { ibevtPortSwitchType 96 }  -- OC48-LR Single Mode Fiber Optic Transceivers with LC Connector
ibevtPortSw-10G-BASE-CX4           OBJECT IDENTIFIER ::= { ibevtPortSwitchType 97 }  -- 10G BASE-CX4 Electrical Interface
ibevtPortSw-OLT-1000BASE-BX-SFF-SC OBJECT IDENTIFIER ::= { ibevtPortSwitchType 98 }  -- 1000 BASE-BX SFF SC OLT Interface
ibevtPortSw-ONU-1000BASE-BX-SFF-SC OBJECT IDENTIFIER ::= { ibevtPortSwitchType 99 }  -- 1000 BASE-BX SFF SC ONU Interface
ibevtPortSw-24G-CASCADE            OBJECT IDENTIFIER ::= { ibevtPortSwitchType 100 }  -- 24G Cascade port
ibevtPortSw-POS-OC3-SR-MM          OBJECT IDENTIFIER ::= { ibevtPortSwitchType 101 }  -- STM1/OC3 Short Reach Multi Mode Fiber Optic Transceivers with LC Connector
ibevtPortSw-POS-OC3-IR-SM          OBJECT IDENTIFIER ::= { ibevtPortSwitchType 102 }  -- STM1/OC3 Intermediate Reach Single Mode Fiber Optic Transceivers with LC Connector
ibevtPortSw-POS-OC3-IR-1-SM        OBJECT IDENTIFIER ::= { ibevtPortSwitchType 103 }  -- STM1/OC3 Intermediate Reach Single Mode Fiber Optic Transceivers with LC Connector(variation 1)
ibevtPortSw-POS-OC3-IR-2-SM        OBJECT IDENTIFIER ::= { ibevtPortSwitchType 104 }  -- STM1/OC3 Intermediate Reach Single Mode Fiber Optic Transceivers with LC Connector(variation 2)
ibevtPortSw-POS-OC3-LR-SM          OBJECT IDENTIFIER ::= { ibevtPortSwitchType 105 }  -- STM1/OC3 Long Reach Single Mode Fiber Optic Transceivers with LC Connector
ibevtPortSw-POS-OC3-LR-1-SM        OBJECT IDENTIFIER ::= { ibevtPortSwitchType 106 }  -- STM1/OC3 Long Reach Single Mode Fiber Optic Transceivers with LC Connector(variation 1)
ibevtPortSw-POS-OC3-LR-2-SM        OBJECT IDENTIFIER ::= { ibevtPortSwitchType 107 }  -- STM1/OC3 Long Reach Single Mode Fiber Optic Transceivers with LC Connector(variation 2)
ibevtPortSw-POS-OC3-LR-3-SM        OBJECT IDENTIFIER ::= { ibevtPortSwitchType 108 }  -- STM1/OC3 Long Reach Single Mode Fiber Optic Transceivers with LC Connector(variation 3)
ibevtPortSw-POS-OC12-SR-MM         OBJECT IDENTIFIER ::= { ibevtPortSwitchType 109 }  -- STM4/OC12 Short Reach Multi Mode Fiber Optic Transceivers with LC Connector
ibevtPortSw-POS-OC12-IR-SM         OBJECT IDENTIFIER ::= { ibevtPortSwitchType 110 }  -- STM4/OC12 Intermediate Reach Single Mode Fiber Optic Transceivers with LC Connector
ibevtPortSw-POS-OC12-IR-1-SM       OBJECT IDENTIFIER ::= { ibevtPortSwitchType 111 }  -- STM4/OC12 Intermediate Reach Single Mode Fiber Optic Transceivers with LC Connector(variation 1)
ibevtPortSw-POS-OC12-IR-2-SM       OBJECT IDENTIFIER ::= { ibevtPortSwitchType 112 }  -- STM4/OC12 Intermediate Reach Single Mode Fiber Optic Transceivers with LC Connector(variation 2)
ibevtPortSw-POS-OC12-LR-SM         OBJECT IDENTIFIER ::= { ibevtPortSwitchType 113 }  -- STM4/OC12 Long Reach Single Mode Fiber Optic Transceivers with LC Connector
ibevtPortSw-POS-OC12-LR-1-SM       OBJECT IDENTIFIER ::= { ibevtPortSwitchType 114 }  -- STM4/OC12 Long Reach Single Mode Fiber Optic Transceivers with LC Connector(variation 1)
ibevtPortSw-POS-OC12-LR-2-SM       OBJECT IDENTIFIER ::= { ibevtPortSwitchType 115 }  -- STM4/OC12 Long Reach Single Mode Fiber Optic Transceivers with LC Connector(variation 2)
ibevtPortSw-POS-OC12-LR-3-SM       OBJECT IDENTIFIER ::= { ibevtPortSwitchType 116 }  -- STM4/OC12 Long Reach Single Mode Fiber Optic Transceivers with LC Connector(variation 3)
ibevtPortSw-POS-OC48-SR-SM         OBJECT IDENTIFIER ::= { ibevtPortSwitchType 117 }  -- STM16/OC48 Short Reach Single Mode Fiber Optic Transceivers with LC Connector
ibevtPortSw-POS-OC48-IR-SM         OBJECT IDENTIFIER ::= { ibevtPortSwitchType 118 }  -- STM16/OC48 Intermediate Reach Single Mode Fiber Optic Transceivers with LC Connector
ibevtPortSw-POS-OC48-IR-1-SM       OBJECT IDENTIFIER ::= { ibevtPortSwitchType 119 }  -- STM16/OC48 Intermediate Reach Single Mode Fiber Optic Transceivers with LC Connector(variation 1)
ibevtPortSw-POS-OC48-IR-2-SM       OBJECT IDENTIFIER ::= { ibevtPortSwitchType 120 }  -- STM16/OC48 Intermediate Reach Single Mode Fiber Optic Transceivers with LC Connector(variation 2)
ibevtPortSw-POS-OC48-LR-SM         OBJECT IDENTIFIER ::= { ibevtPortSwitchType 121 }  -- STM16/OC48 Long Reach Single Mode Fiber Optic Transceivers with LC Connector
ibevtPortSw-POS-OC48-LR-1-SM       OBJECT IDENTIFIER ::= { ibevtPortSwitchType 122 }  -- STM16/OC48 Long Reach Single Mode Fiber Optic Transceivers with LC Connector(variation 1)
ibevtPortSw-POS-OC48-LR-2-SM       OBJECT IDENTIFIER ::= { ibevtPortSwitchType 123 }  -- STM16/OC48 Long Reach Single Mode Fiber Optic Transceivers with LC Connector(variation 2)
ibevtPortSw-POS-OC48-LR-3-SM       OBJECT IDENTIFIER ::= { ibevtPortSwitchType 124 }  -- STM16/OC48 Long Reach Single Mode Fiber Optic Transceivers with LC Connector(variation 3)
ibevtPortSw-POS-I-64-1             OBJECT IDENTIFIER ::= { ibevtPortSwitchType 125 }  -- STM64/OC192 Interconnect Fiber Optic Transceivers with LC Connector(wavelength 1310nm G.652 fiber)
ibevtPortSw-POS-I-64-2             OBJECT IDENTIFIER ::= { ibevtPortSwitchType 126 }  -- STM64/OC192 Interconnect Fiber Optic Transceivers with LC Connector(wavelength 1550nm G.652 fiber)
ibevtPortSw-POS-I-64-3             OBJECT IDENTIFIER ::= { ibevtPortSwitchType 127 }  -- STM64/OC192 Interconnect Fiber Optic Transceivers with LC Connector(wavelength 1550nm G.653 fiber)
ibevtPortSw-POS-I-64-5             OBJECT IDENTIFIER ::= { ibevtPortSwitchType 128 }  -- STM64/OC192 Interconnect Fiber Optic Transceivers with LC Connector(wavelength 1550nm G.655 fiber)
ibevtPortSw-POS-S-64-1             OBJECT IDENTIFIER ::= { ibevtPortSwitchType 129 }  -- STM64/OC192 Short Haul Fiber Optic Transceivers with LC Connector(wavelength 1310nm G.652 fiber)
ibevtPortSw-POS-S-64-2             OBJECT IDENTIFIER ::= { ibevtPortSwitchType 130 }  -- STM64/OC192 Short Haul Fiber Optic Transceivers with LC Connector(wavelength 1550nm G.652 fiber)
ibevtPortSw-POS-S-64-3             OBJECT IDENTIFIER ::= { ibevtPortSwitchType 131 }  -- STM64/OC192 Short Haul Fiber Optic Transceivers with LC Connector(wavelength 1550nm G.653 fiber)
ibevtPortSw-POS-S-64-5             OBJECT IDENTIFIER ::= { ibevtPortSwitchType 132 }  -- STM64/OC192 Short Haul Fiber Optic Transceivers with LC Connector(wavelength 1550nm G.655 fiber)
ibevtPortSw-POS-L-64-1             OBJECT IDENTIFIER ::= { ibevtPortSwitchType 133 }  -- STM64/OC192 Long Haul Fiber Optic Transceivers with LC Connector(wavelength 1310nm G.652 fiber)
ibevtPortSw-POS-L-64-2             OBJECT IDENTIFIER ::= { ibevtPortSwitchType 134 }  -- STM64/OC192 Long Haul Fiber Optic Transceivers with LC Connector(wavelength 1550nm G.652 fiber)
ibevtPortSw-POS-L-64-3             OBJECT IDENTIFIER ::= { ibevtPortSwitchType 135 }  -- STM64/OC192 Long Haul Fiber Optic Transceivers with LC Connector(wavelength 1550nm G.653 fiber)
ibevtPortSw-POS-V-64-2             OBJECT IDENTIFIER ::= { ibevtPortSwitchType 136 }  -- STM64/OC192 Very Long Haul Fiber Optic Transceivers with LC Connector(wavelength 1550nm G.652 fiber)
ibevtPortSw-POS-V-64-3             OBJECT IDENTIFIER ::= { ibevtPortSwitchType 137 }  -- STM64/OC192 Very Long Haul Fiber Optic Transceivers with LC Connector(wavelength 1550nm G.653 fiber)
ibevtPortSw-100BASE-FX-BIDI        OBJECT IDENTIFIER ::= { ibevtPortSwitchType 138 }  -- 100 BASE-FX BIDI Port
ibevtPortSw-100BASE-BX10-U-SFP     OBJECT IDENTIFIER ::= { ibevtPortSwitchType 139 }  -- 100 BASE-BX10-U-SFP Port
ibevtPortSw-100BASE-BX10-D-SFP     OBJECT IDENTIFIER ::= { ibevtPortSwitchType 140 }  -- 100 BASE-BX10-D-SFP Port
ibevtPortSw-1000BASE-BX10-U-SFP    OBJECT IDENTIFIER ::= { ibevtPortSwitchType 141 }  -- 1000 BASE-BX10-U-SFP Port
ibevtPortSw-1000BASE-BX10-D-SFP    OBJECT IDENTIFIER ::= { ibevtPortSwitchType 142 }  -- 1000 BASE-BX10-D-SFP Port
ibevtPortSw-STK-1000BASE-T         OBJECT IDENTIFIER ::= { ibevtPortSwitchType 143 }  -- 1000 BASE-T Stack Port
ibevtPortSw-RPR-PHYPOS-CONNECTOR     OBJECT IDENTIFIER ::= { ibevtPortSwitchType 144 }  -- Resilient Packet Ring POS physical port
ibevtPortSw-RPR-PHY10GE-CONNECTOR    OBJECT IDENTIFIER ::= { ibevtPortSwitchType 145 }  -- 10G Resilient Packet Ring physical port
ibevtPortSw-RPR-LOGICPOS-CONNECTOR   OBJECT IDENTIFIER ::= { ibevtPortSwitchType 146 }  -- Resilient Packet Ring POS logical port
ibevtPortSw-RPR-LOGIC10GE-CONNECTOR  OBJECT IDENTIFIER ::= { ibevtPortSwitchType 147 }  -- 10G Resilient Packet Ring logical port
ibevtPortSw-10GBASE-ZR               OBJECT IDENTIFIER ::= { ibevtPortSwitchType 148 }  -- Fiber Optic Transceivers with SC Connector, XENPAK
ibevtPortSw-TYPE-ERROR-CONNECTOR     OBJECT IDENTIFIER ::= { ibevtPortSwitchType 149 }  -- Error Optic Transceivers type
ibevtPortSw-10G-STACK                OBJECT IDENTIFIER ::= { ibevtPortSwitchType 150 }  -- 10G Stack Port
ibevtPortSw-155-ATM-SX-MMF             OBJECT IDENTIFIER ::= { ibevtPortSwitchType 151 }  -- ATM OC-3 Multi-mode Short Reach Optical Transceiver
ibevtPortSw-155-ATM-LX-SMF             OBJECT IDENTIFIER ::= { ibevtPortSwitchType 152 }  -- ATM OC-3 Single Mode Long Reach Optical Transceiver
ibevtPortSw-622-ATM-SX-MMF             OBJECT IDENTIFIER ::= { ibevtPortSwitchType 153 }  -- ATM OC-12 Multi-mode Short Reach Optical Transceiver
ibevtPortSw-622-ATM-LX-SMF             OBJECT IDENTIFIER ::= { ibevtPortSwitchType 154 }  -- ATM OC-12 Single Mode Long Reach Optical Transceiver
ibevtPortSw-155-ATM-NO-CONNECTOR       OBJECT IDENTIFIER ::= { ibevtPortSwitchType 155 }  -- ATM OC-3 No Connector
ibevtPortSw-622-ATM-NO-CONNECTOR       OBJECT IDENTIFIER ::= { ibevtPortSwitchType 156 }  -- ATM OC-12 No Connector
ibevtPortSw-155-CPOS-E1-NO-CONNECTOR   OBJECT IDENTIFIER ::= { ibevtPortSwitchType 157 }  -- CPOS(E1) OC-3 No Connector
ibevtPortSw-155-CPOS-T1-NO-CONNECTOR   OBJECT IDENTIFIER ::= { ibevtPortSwitchType 158 }  -- CPOS(T1) OC-3 No Connector
ibevtPortSw-622-CPOS-E1-NO-CONNECTOR   OBJECT IDENTIFIER ::= { ibevtPortSwitchType 159 }  -- CPOS(E1) OC-12 No Connector
ibevtPortSw-622-CPOS-T1-NO-CONNECTOR   OBJECT IDENTIFIER ::= { ibevtPortSwitchType 160 }  -- CPOS(T1) OC-12 No Connector
ibevtPortSw-155-CPOS-E1-SX-MMF         OBJECT IDENTIFIER ::= { ibevtPortSwitchType 161 }  -- CPOS(E1) OC-3 Multi-mode Short Reach Optical Transceiver
ibevtPortSw-155-CPOS-T1-SX-MMF         OBJECT IDENTIFIER ::= { ibevtPortSwitchType 162 }  -- CPOS(T1) OC-3 Multi-mode Short Reach Optical Transceiver
ibevtPortSw-155-CPOS-E1-LX-SMF         OBJECT IDENTIFIER ::= { ibevtPortSwitchType 163 }  -- CPOS(E1) OC-3 Single Mode Long Reach Optical Transceiver
ibevtPortSw-155-CPOS-T1-LX-SMF         OBJECT IDENTIFIER ::= { ibevtPortSwitchType 164 }  -- CPOS(T1) OC-3 Single Mode Long Reach Optical Transceiver
ibevtPortSw-622-CPOS-E1-SX-MMF         OBJECT IDENTIFIER ::= { ibevtPortSwitchType 165 }  -- CPOS(E1) OC-12 Multi-mode Short Reach Optical Transceiver
ibevtPortSw-622-CPOS-T1-SX-MMF         OBJECT IDENTIFIER ::= { ibevtPortSwitchType 166 }  -- CPOS(T1) OC-12 Multi-mode Short Reach Optical Transceiver
ibevtPortSw-622-CPOS-E1-LX-SMF         OBJECT IDENTIFIER ::= { ibevtPortSwitchType 167 }  -- CPOS(E1) OC-12 Multi-mode Short Reach Optical Transceiver
ibevtPortSw-622-CPOS-T1-LX-SMF         OBJECT IDENTIFIER ::= { ibevtPortSwitchType 168 }  -- CPOS(T1) OC-12 Single Mode Long Reach Optical Transceiver
ibevtPortSw-E1-CONNECTOR               OBJECT IDENTIFIER ::= { ibevtPortSwitchType 169 }  -- E1 RJ45 Transceiver
ibevtPortSw-T1-CONNECTOR               OBJECT IDENTIFIER ::= { ibevtPortSwitchType 170 }  -- T1 RJ45 Transceiver
ibevtPortSw-1000BASE-STK-SFP           OBJECT IDENTIFIER ::= { ibevtPortSwitchType 171 }  -- 1-port 1000 Base-STK SFP Module
ibevtPortSw-1000BASE-BIDI-SFP          OBJECT IDENTIFIER ::= { ibevtPortSwitchType 172 }  -- 1-port 1000 Base-BIDI SFP Module
ibevtPortSw-1000BASE-CWDM-SFP          OBJECT IDENTIFIER ::= { ibevtPortSwitchType 173 }  -- 1-port 1000 Base-CWDM SFP Module
ibevtPortSw-100BASE-BIDI-SFP           OBJECT IDENTIFIER ::= { ibevtPortSwitchType 174 }  -- 1-port 100 Base-BIDI SFP Module
ibevtPortSw-OLT-1000BASE-PX-SFP        OBJECT IDENTIFIER ::= { ibevtPortSwitchType 175 }  -- 1000BASE-PX SFP OLT Interface
ibevtPortSw-OLT-1000BASE-NO-CONNECTOR  OBJECT IDENTIFIER ::= { ibevtPortSwitchType 176 }  -- 1000BASE OLT No Connector
ibevtPortSw-RPR-PHYGE-CONNECTOR        OBJECT IDENTIFIER ::= { ibevtPortSwitchType 177 }  -- Resilient Packet Ring GE physical port
ibevtPortSw-RPR-LOGICGE-CONNECTOR      OBJECT IDENTIFIER ::= { ibevtPortSwitchType 178 }  -- Resilient Packet Ring GE logical port
ibevtPortSw-100M-1550-BIDI             OBJECT IDENTIFIER ::= { ibevtPortSwitchType 179 }  -- Single Port 100M Ethernet Bi-direction Optical Interface Module(TX1550nm, RX1310nm, 15km, SC)
ibevtPortSw-100M-1310-BIDI             OBJECT IDENTIFIER ::= { ibevtPortSwitchType 180 }  -- Single Port 100M Ethernet Bi-direction Optical reverse Interface Module(TX1310nm, RX1550nm, 15km, SC)
ibevtPortSw-RPR-PHYOC48-CONNECTOR      OBJECT IDENTIFIER ::= { ibevtPortSwitchType 181 }  -- Resilient Packet Ring OC48 physical port
ibevtPortSw-RPR-LOGICOC48-CONNECTOR    OBJECT IDENTIFIER ::= { ibevtPortSwitchType 182 }  -- Resilient Packet Ring OC48 logical port
ibevtPortSw-100-1000-BASE-LX-SMF       OBJECT IDENTIFIER ::= { ibevtPortSwitchType 183 }  -- 100BASE-LX/1000BASE-LX Single Mode Fiber Optic Transceivers
ibevtPortSw-10G-ZW-SM-LC               OBJECT IDENTIFIER ::= { ibevtPortSwitchType 184 }  -- 10GBASE-ZW Single Mode Fiber Optic Transceivers with LC Connector
ibevtPortSw-10G-ZR-SM-LC               OBJECT IDENTIFIER ::= { ibevtPortSwitchType 185 }  -- 10GBASE-ZR Single Mode Fiber Optic Transceivers with LC Connector
ibevtPortSw-XPK-10GBASE-ZR             OBJECT IDENTIFIER ::= { ibevtPortSwitchType 186 }  -- 10GBASE-ZR Xenpak Transceiver:LH80,SM1550
ibevtPortSw-SGMII-100-BASE-LX-SFP      OBJECT IDENTIFIER ::= { ibevtPortSwitchType 187 }  -- SGMII-100-BASE-LX-SFP Transceiver
ibevtPortSw-SGMII-100-BASE-FX-SFP      OBJECT IDENTIFIER ::= { ibevtPortSwitchType 188 }  -- SGMII-100-BASE-FX-SFP Transceiver
ibevtPortSw-WLAN-RADIO                 OBJECT IDENTIFIER ::= { ibevtPortSwitchType 189 }  -- WLAN-RADIO Transceiver
ibevtPortSw-CABLE                      OBJECT IDENTIFIER ::= { ibevtPortSwitchType 190 }  -- Cable Port
ibevtPortSw-SFP-PLUS-NO-CONNECTOR      OBJECT IDENTIFIER ::= { ibevtPortSwitchType 191 }  -- SFP+ without Transceiver
ibevtPortSw-SFP-PLUS-10GBASE-SR        OBJECT IDENTIFIER ::= { ibevtPortSwitchType 192 }  -- 10GBASE-SR SFP+ Transceiver
ibevtPortSw-SFP-PLUS-10GBASE-LR        OBJECT IDENTIFIER ::= { ibevtPortSwitchType 193 }  -- 10GBASE-LR SFP+ Transceiver
ibevtPortSw-SFP-PLUS-10GBASE-LRM       OBJECT IDENTIFIER ::= { ibevtPortSwitchType 194 }  -- 10GBASE-LRM SFP+ Transceiver
ibevtPortSw-SFP-PLUS-10GBASE-Cu        OBJECT IDENTIFIER ::= { ibevtPortSwitchType 195 }  -- 10GBASE-Cu SFP+ Transceiver
ibevtPortSw-SFP-PLUS-UNKNOWN           OBJECT IDENTIFIER ::= { ibevtPortSwitchType 196 }  -- Unknown SFP+ Transceiver
ibevtPortSw-SFP-PLUS-STACK-CONNECTOR   OBJECT IDENTIFIER ::= { ibevtPortSwitchType 197 }  -- SFP+ STACK Transceiver
ibevtPortSw-POS-L-64-4                 OBJECT IDENTIFIER ::= { ibevtPortSwitchType 198 }  -- STM64/OC192 Long Haul Fiber Optic Transceivers with LC Connector(wavelength 1550nm G.653 fiber)
ibevtPortSw-MINISAS-HD-STACK-CONNECTOR OBJECT IDENTIFIER ::= { ibevtPortSwitchType 199 }  -- MiniSAS HD STACK Transceiver
ibevtPortSw-ONU-1000BASE-PX-SFF        OBJECT IDENTIFIER ::= { ibevtPortSwitchType 200 }  -- 1000BASE-PX SFF ONU Interface
ibevtPortSw-RS485                      OBJECT IDENTIFIER ::= { ibevtPortSwitchType 201 }  -- RS-485 Interface
ibevtPortSw-SFP-PLUS-10GBASE-ER        OBJECT IDENTIFIER ::= { ibevtPortSwitchType 202 }  -- 10GBASE-ER SFP+ Transceiver
ibevtPortSw-SFP-PLUS-10GBASE-ZR        OBJECT IDENTIFIER ::= { ibevtPortSwitchType 203 }  -- 10GBASE-ZR SFP+ Transceiver
ibevtPortSw-XFP-10GBASE-ZR             OBJECT IDENTIFIER ::= { ibevtPortSwitchType 204 }  -- 10GBASE-ZR XFP Transceiver
ibevtPortSw-QSFP-PLUS-40GBASE-SR4      OBJECT IDENTIFIER ::= { ibevtPortSwitchType 205 }  -- 40BASE-SR4 QSFP+ Optical Transceiver
ibevtPortSw-QSFP-PLUS-STACK-CONNECTOR  OBJECT IDENTIFIER ::= { ibevtPortSwitchType 206 }  -- QSFP+ STACK Transceiver
ibevtPortSw-QSFP-PLUS-TO-4SFP-PLUS-STACK-CONNECTOR OBJECT IDENTIFIER ::= { ibevtPortSwitchType 207 }  -- QSFP+ to 4 SFP+ STACK Transceiver
ibevtPortSw-SFP-STACK-CONNECTOR        OBJECT IDENTIFIER ::= { ibevtPortSwitchType 208 }  -- SFP STACK Transceiver
ibevtPortSw-QSFP-NO-CONNECTOR          OBJECT IDENTIFIER ::= { ibevtPortSwitchType 209 }  -- QSFP No Connector
ibevtPortSw-10GBase-T                  OBJECT IDENTIFIER ::= { ibevtPortSwitchType 210 }  -- 10G Base-T Port
ibevtPortSw-CFP-NO-CONNECTOR           OBJECT IDENTIFIER ::= { ibevtPortSwitchType 211 }  -- CFP No Connector
ibevtPortSw-CFP-40GBASE-LR4            OBJECT IDENTIFIER ::= { ibevtPortSwitchType 212 }  -- 40GBASE-LR4 CFP Transceiver
ibevtPortSw-QSFP-PLUS-NO-CONNECTOR     OBJECT IDENTIFIER ::= { ibevtPortSwitchType 213 }  -- QSFP+ No Connector
ibevtPortSw-QSFP-PLUS-40GBASE-LR4      OBJECT IDENTIFIER ::= { ibevtPortSwitchType 214 }  -- 40GBASE-LR4 QSFP+ Optical Transceiver
ibevtPortSw-CFP-40GBASE-SR4            OBJECT IDENTIFIER ::= { ibevtPortSwitchType 215 }  -- 40GBASE-SR4 CFP Optical Transceiver
ibevtPortSw-CFP-100GBASE-LR4           OBJECT IDENTIFIER ::= { ibevtPortSwitchType 216 }  -- 100GBASE-LR4 CFP Optical Transceiver
ibevtPortSw-CFP-100GBASE-SR10          OBJECT IDENTIFIER ::= { ibevtPortSwitchType 217 }  -- 100GBASE-SR10 CFP Optical Transceiver
ibevtPortSw-CXP-100GBASE-SR10          OBJECT IDENTIFIER ::= { ibevtPortSwitchType 218 }  -- 100GBASE-SR10 CXP Optical Transceiver
ibevtPortSw-CXP-NO-CONNECTOR           OBJECT IDENTIFIER ::= { ibevtPortSwitchType 219 }  -- CXP No Connector
ibevtPortSw-TRANSCEIVER-UNKNOWN        OBJECT IDENTIFIER ::= { ibevtPortSwitchType 220 }  -- Unknown Transceiver
ibevtPortSw-QSFP-PLUS-UNKNOWN          OBJECT IDENTIFIER ::= { ibevtPortSwitchType 221 }  -- Unknown QSFP+ Transceiver
ibevtPortSw-CFP-UNKNOWN                OBJECT IDENTIFIER ::= { ibevtPortSwitchType 222 }  -- Unknown CFP Transceiver
ibevtPortSw-QSFP-PLUS-40GBASE-CSR4     OBJECT IDENTIFIER ::= { ibevtPortSwitchType 223 }  -- 40GBASE-CSR4 QSFP+ Optical Transceiver
ibevtPortSw-CFP-40GBASE-ER4            OBJECT IDENTIFIER ::= { ibevtPortSwitchType 224 }  -- 40GBASE-ER4 CFP Optical Transceiver
ibevtPortSw-SFP-1000BASE-BIDI          OBJECT IDENTIFIER ::= { ibevtPortSwitchType 225 }  -- 1000BASE SFP Bi-direction Optical Transceiver
ibevtPortSw-SFP-PLUS-10GBASE-ZR-DWDM   OBJECT IDENTIFIER ::= { ibevtPortSwitchType 226 }  -- 10GBase-ZR SFP+ DWDM Optical Transceiver
ibevtPortSw-QSFP-PLUS-40GBASE-PSM      OBJECT IDENTIFIER ::= { ibevtPortSwitchType 227 }  -- 40GBASE QSFP+ Parallel SingleMode Optical Transceiver
ibevtPortSw-SFP-8GFC-SW                OBJECT IDENTIFIER ::= { ibevtPortSwitchType 228 }  -- SFP 8G FC Optical Transceiver short wave
ibevtPortSw-SFP-8GFC-LW                OBJECT IDENTIFIER ::= { ibevtPortSwitchType 229 }  -- SFP 8G FC Optical Transceiver long wave
ibevtPortSw-CXP-100GBASE-AOC           OBJECT IDENTIFIER ::= { ibevtPortSwitchType 230 }  -- 100GBASE CXP Active Optical Cable
ibevtPortSw-QSFP-PLUS-ACTIVE-STACK-CONNECTOR  OBJECT IDENTIFIER ::= { ibevtPortSwitchType 231 }  -- QSFP+ Active STACK Transceiver
ibevtPortSw-QSFP-PLUS-TO-4SFP-PLUS-ACTIVE-STACK-CONNECTOR  OBJECT IDENTIFIER ::= { ibevtPortSwitchType 232 }  -- QSFP+ to 4 SFP+ Active STACK Transceiver
ibevtPortSw-CFP2-100GBASE-LR4          OBJECT IDENTIFIER ::= { ibevtPortSwitchType 233 }  -- 100GBASE-LR4 CFP2 Optical Transceiver
ibevtPortSw-CFP2-100GBASE-SR10         OBJECT IDENTIFIER ::= { ibevtPortSwitchType 234 }  -- 100GBASE-SR10 CFP2 Optical Transceiver
ibevtPortSw-QSFP-PLUS-ACTIVE-OPTICAL-CABLE  OBJECT IDENTIFIER ::= { ibevtPortSwitchType 235 }  -- QSFP+ AOC
ibevtPortSw-QSFP-PLUS-TO-4SFP-PLUS-ACTIVE-OPTICAL-CABLE OBJECT IDENTIFIER ::= { ibevtPortSwitchType 236 }  -- QSFP+ to 4 SFP+ AOC
ibevtPortSw-SFP-PLUS-ACTIVE-OPTICAL-CABLE           OBJECT IDENTIFIER ::= { ibevtPortSwitchType 237 }  -- SFP+ AOC
ibevtPortSw-CFP2-NO-CONNECTOR                       OBJECT IDENTIFIER ::= { ibevtPortSwitchType 238 }  -- CFP2 No Connector
ibevtPortSw-QSFP28-NO-CONNECTOR                     OBJECT IDENTIFIER ::= { ibevtPortSwitchType 239 }  -- QSFP28 No Connector
ibevtPortSw-QSFP28-100GBASE-SR4                     OBJECT IDENTIFIER ::= { ibevtPortSwitchType 240 }  -- 100BASE-SR4 QSFP28 Optical Transceiver
ibevtPortSw-QSFP28-100GBASE-LR4                     OBJECT IDENTIFIER ::= { ibevtPortSwitchType 241 }  -- 100GBASE-LR4 QSFP28 Optical Transceiver
ibevtPortSw-QSFP28-100GBASE-ER4                     OBJECT IDENTIFIER ::= { ibevtPortSwitchType 242 }  -- 100GBASE-ER4 QSFP28 Optical Transceiver
ibevtPortSw-QSFP28-100GBASE-PSM4                    OBJECT IDENTIFIER ::= { ibevtPortSwitchType 243 }  -- 100GBASE-PSM4 QSFP28 Optical Transceiver
ibevtPortSw-QSFP28-100GBASE-CWDM4                   OBJECT IDENTIFIER ::= { ibevtPortSwitchType 244 }  -- 100GBASE-CWDM4 QSFP28 Optical Transceiver
ibevtPortSw-QSFP28-STACK-CONNECTOR                  OBJECT IDENTIFIER ::= { ibevtPortSwitchType 245 }  -- QSFP28 STACK Transceiver
ibevtPortSw-QSFP28-TO-4SFP28-STACK-CONNECTOR        OBJECT IDENTIFIER ::= { ibevtPortSwitchType 246 }  -- QSFP28 to 4 SFP28 STACK Transceiver
ibevtPortSw-QSFP28-ACTIVE-STACK-CONNECTOR           OBJECT IDENTIFIER ::= { ibevtPortSwitchType 247 }  -- QSFP28 Active STACK Transceiver
ibevtPortSw-QSFP28-TO-4SFP28-ACTIVE-STACK-CONNECTOR OBJECT IDENTIFIER ::= { ibevtPortSwitchType 248 }  -- QSFP28 to 4 SFP28 Active STACK Transceiver
ibevtPortSw-QSFP28-ACTIVE-OPTICAL-CABLE             OBJECT IDENTIFIER ::= { ibevtPortSwitchType 249 }  -- QSFP28 AOC
ibevtPortSw-QSFP28-TO-4SFP28-ACTIVE-OPTICAL-CABLE   OBJECT IDENTIFIER ::= { ibevtPortSwitchType 250 }  -- QSFP28 to 4 SFP28 AOC
ibevtPortSw-QSFP-PLUS-40GBASE-LM4                   OBJECT IDENTIFIER ::= { ibevtPortSwitchType 251 }  -- 40BASE-LM4 QSFP+ Optical Transceiver
ibevtPortSw-QSFP-PLUS-40GBASE-SWDM4                 OBJECT IDENTIFIER ::= { ibevtPortSwitchType 252 }  -- 40BASE-SWDM4 QSFP+ Optical Transceiver
ibevtPortSw-CFP-100GBASE-ER4                        OBJECT IDENTIFIER ::= { ibevtPortSwitchType 253 }  -- 100GBASE-ER4 CFP Transceiver
ibevtPortSw-QSFP-PLUS-40GBASE-ER4                   OBJECT IDENTIFIER ::= { ibevtPortSwitchType 254 }  -- 40BASE-ER4 QSFP+ Optical Transceiver
ibevtPortSw-QSFP-PLUS-40GBASE-ER4L                  OBJECT IDENTIFIER ::= { ibevtPortSwitchType 255 }  -- 40BASE-ER4L QSFP+ Optical Transceiver
ibevtPortSw-QSFP-PLUS-40GBASE-BIDI                  OBJECT IDENTIFIER ::= { ibevtPortSwitchType 256 }  -- 40BASE-BIDI QSFP+ Optical Transceiver
ibevtPortSw-QSFP-PLUS-40GBASE-LR4L                  OBJECT IDENTIFIER ::= { ibevtPortSwitchType 257 }  -- 40BASE-LR4L QSFP+ Optical Transceiver
ibevtPortSw-CFP2-100GBASE-eSR10                     OBJECT IDENTIFIER ::= { ibevtPortSwitchType 258 }  -- 100GBASE-eSR10 CFP2 Optical Transceiver
ibevtPortSw-TUNABLE-SFP-PLUS-10GBASE-ZR-DWDM        OBJECT IDENTIFIER ::= { ibevtPortSwitchType 259 }  -- 10GBase-ZR Tunable SFP+ DWDM Optical Transceiver
ibevtPortSw-SFP28-25GBASE-SR                        OBJECT IDENTIFIER ::= { ibevtPortSwitchType 260 }  -- 25GBASE-SR SFP28 Optical Transceiver
ibevtPortSw-SFP28-ACTIVE-OPTICAL-CABLE              OBJECT IDENTIFIER ::= { ibevtPortSwitchType 261 }  -- SFP28 AOC
ibevtPortSw-SFP28-STACK-CONNECTOR                   OBJECT IDENTIFIER ::= { ibevtPortSwitchType 262 }  -- SFP28 STACK Transceiver
ibevtPortSw-2DOT5GBASE-T                            OBJECT IDENTIFIER ::= { ibevtPortSwitchType 263 }  -- 2dot5G Base-T Port
ibevtPortSw-QSFP28-100GBASE-SWDM4                   OBJECT IDENTIFIER ::= { ibevtPortSwitchType 264 }  -- 100GBASE-SWDM4 QSFP28 Optical Transceiver
ibevtPortSw-QSFP28-100GBASE-eSWDM4                  OBJECT IDENTIFIER ::= { ibevtPortSwitchType 265 }  -- 100GBASE-eSWDM4 QSFP28 Optical Transceiver
ibevtPortSw-SFP-PLUS-10GBASE-T                      OBJECT IDENTIFIER ::= { ibevtPortSwitchType 266 }  -- 10GBase-T SFP+ Transceiver
ibevtPortSw-QSFP28-100GBASE-eSR4                    OBJECT IDENTIFIER ::= { ibevtPortSwitchType 267 }  -- 100BASE-eSR4 QSFP28 Optical Transceiver
ibevtPortSw-QSFP28-100GBASE-BIDI                    OBJECT IDENTIFIER ::= { ibevtPortSwitchType 268 }  -- 100GBASE-BIDI QSFP28 Optical Transceiver
ibevtPortSw-QSFP28-100GBASE-WDM2                    OBJECT IDENTIFIER ::= { ibevtPortSwitchType 269 }  -- 100GBASE-WDM2 QSFP28 Optical Transceiver
ibevtPortSw-SFP28-25GBASE-LR                        OBJECT IDENTIFIER ::= { ibevtPortSwitchType 270 }  -- 25GBASE-LR SFP28 Optical Transceiver
ibevtPortSw-CFP2-100GBASE-ER4                       OBJECT IDENTIFIER ::= { ibevtPortSwitchType 271 }  -- 100GBASE-ER4 CFP2 Optical Transceiver
ibevtPortSw-CFP2-DCO-200GBASE-ZR                    OBJECT IDENTIFIER ::= { ibevtPortSwitchType 272 }  -- 200GBASE-ZR CFP2-DCO Optical Transceiver
ibevtPortSw-CFP2-100GBASE-ER4L                      OBJECT IDENTIFIER ::= { ibevtPortSwitchType 273 }  -- 100GBASE-ER4L CFP2 Optical Transceiver
ibevtPortSw-SFP-16GFC-SW                            OBJECT IDENTIFIER ::= { ibevtPortSwitchType 274 }  -- SFP 16G FC Optical Transceiver short wave
ibevtPortSw-SFP-16GFC-LW                            OBJECT IDENTIFIER ::= { ibevtPortSwitchType 275 }  -- SFP 16G FC Optical Transceiver long wave
ibevtPortSw-SFP-32GFC-SW                            OBJECT IDENTIFIER ::= { ibevtPortSwitchType 276 }  -- SFP 32G FC Optical Transceiver short wave
ibevtPortSw-SFP-32GFC-LW                            OBJECT IDENTIFIER ::= { ibevtPortSwitchType 277 }  -- SFP 32G FC Optical Transceiver long wave
ibevtPortSw-XFP-10GBASE-PR-D3                       OBJECT IDENTIFIER ::= { ibevtPortSwitchType 278 }  -- XFP 10GBase PR-D3 Optical Transceiver
ibevtPortSw-XFP-10GBASE-PRX-D3                      OBJECT IDENTIFIER ::= { ibevtPortSwitchType 279 }  -- XFP 10GBase PRX-D3 Optical Transceiver
ibevtPortSw-5GBASE-T                                OBJECT IDENTIFIER ::= { ibevtPortSwitchType 280 }  -- 5G Base-T Port
ibevtPortSw-QSFP28-UNKNOWN                          OBJECT IDENTIFIER ::= { ibevtPortSwitchType 281 }  -- Unknown QSFP28 Transceiver
ibevtPortSw-SFP28-UNKNOWN                           OBJECT IDENTIFIER ::= { ibevtPortSwitchType 282 }  -- Unknown SFP28 Transceiver
ibevtPortSw-SFP28-NO-CONNECTOR                      OBJECT IDENTIFIER ::= { ibevtPortSwitchType 283 }  -- SFP28 No Connector
ibevtPortSw-SFP-PLUS-9-8GCRPI-IR                    OBJECT IDENTIFIER ::= { ibevtPortSwitchType 284 }  -- 9.8GCRPI-IR SFP+ Transceiver
ibevtPortSw-SFP-PLUS-9-8GCRPI-LR                    OBJECT IDENTIFIER ::= { ibevtPortSwitchType 285 }  -- 9.8GCRPI-LR SFP+ Transceiver
ibevtPortSw-50GBase-F                               OBJECT IDENTIFIER ::= { ibevtPortSwitchType 286 }  -- 50G Ethernet port with QSFP28
ibevtPortSw-QSFP28-50GBASE-PAM4-LR                  OBJECT IDENTIFIER ::= { ibevtPortSwitchType 287 }  -- 50GBASE-PAM4-LR QSFP28 Optical Transceiver
ibevtPortSw-10GBASE-BIDI-SFP                        OBJECT IDENTIFIER ::= { ibevtPortSwitchType 288 }  -- 10GBASE  SFP+ BIDI Optical Transceiver

ibevtPortSw-10GBASE-BIDI-U-SFP-PLUS                 OBJECT IDENTIFIER ::= { ibevtPortSwitchType 291 }  -- 10GBASE  SFP+ BIDI Up Optical Transceiver
ibevtPortSw-10GBASE-BIDI-D-SFP-PLUS                 OBJECT IDENTIFIER ::= { ibevtPortSwitchType 292 }  -- 10GBASE  SFP+ BIDI Down Optical Transceiver
ibevtPortSw-QSFPDD-STACK-CONNECTOR                  OBJECT IDENTIFIER ::= { ibevtPortSwitchType 293 }  -- QSFPDD-STACK-Transceiver
ibevtPortSw-QSFPDD-400GBASE-SR8                     OBJECT IDENTIFIER ::= { ibevtPortSwitchType 294 }  -- 400GBASE-SR8  QSFP-DD Optical Transceiver
ibevtPortSw-QSFP28-100GBASE-ZR2                     OBJECT IDENTIFIER ::= { ibevtPortSwitchType 295 }   -- 100GBASE-ZR2 QSFP28 Optical Transceiver
ibevtPortSw-QSFP28-50GBASE-ER                       OBJECT IDENTIFIER ::= { ibevtPortSwitchType 296 }  -- 50GBASE ER QSFP28 Optical Transceiver Module
ibevtPortSw-SFP28-25GBASE-eLR                       OBJECT IDENTIFIER ::= { ibevtPortSwitchType 297 }  -- 25GBASE-eLR SFP28 Optical Transceiver
ibevtPortSw-QSFP28-100GBASE-ER4-NO-FEC              OBJECT IDENTIFIER ::= { ibevtPortSwitchType 298 }  -- 100GBASE-ER4 QSFP28 Optical Transceiver Module
ibevtPortSw-QSFP28-100GBASE-ZR4                     OBJECT IDENTIFIER ::= { ibevtPortSwitchType 299 }  -- 100GBASE-ZR4 QSFP28 Optical Transceiver Module
ibevtPortSw-QSFPDD-400GBASE-FR4                     OBJECT IDENTIFIER ::= { ibevtPortSwitchType 300 }  -- 400GBASE-FR4 QSFP-DD Optical Transceiver
ibevtPortSw-QSFP56-200GBASE-FR4                     OBJECT IDENTIFIER ::= { ibevtPortSwitchType 301 }  -- 200GBASE-FR4 QSFP-56 Optical Transceiver
ibevtPortSw-QSFP56-200GBASE-SR4                     OBJECT IDENTIFIER ::= { ibevtPortSwitchType 302 }  -- 200GBASE-SR4 QSFP-56 Optical Transceiver
ibevtPortSw-QSFP56-200GBASE-AOC                     OBJECT IDENTIFIER ::= { ibevtPortSwitchType 303 }  -- 200GBASE-AOC QSFP-56 Active Optical Cable
ibevtPortSw-DSFP-100GBASE-AOC                       OBJECT IDENTIFIER ::= { ibevtPortSwitchType 304 }  -- 100GBASE-AOC DSFP Active Optical Cable
ibevtPortSw-SFP28-25GBASE-CSR                       OBJECT IDENTIFIER ::= { ibevtPortSwitchType 305 }  -- 25GBASE-CSR SFP28 Optical Transceiver
ibevtPortSw-QSFPDD-UNKNOWN                          OBJECT IDENTIFIER ::= { ibevtPortSwitchType 306 }  -- Unknown QSFPDD Transceiver
ibevtPortSw-QSFPDD-NO-CONNECTOR                     OBJECT IDENTIFIER ::= { ibevtPortSwitchType 307 }  -- QSFPDD No Connector
ibevtPortSw-DSFP-UNKNOWN                            OBJECT IDENTIFIER ::= { ibevtPortSwitchType 308 }  -- Unknown DSFP Transceiver
ibevtPortSw-DSFP-NO-CONNECTOR                       OBJECT IDENTIFIER ::= { ibevtPortSwitchType 309 }  -- DSFP No Connector
ibevtPortSw-QSFPDD-400GBASE-ZR                      OBJECT IDENTIFIER ::= { ibevtPortSwitchType 310 }  -- 400GBASE-ZR QSFP-DD Optical Transceiver
ibevtPortSw-QSFPDD-400GBASE-LR8                     OBJECT IDENTIFIER ::= { ibevtPortSwitchType 311 }  -- 400GBASE-LR8 QSFP-DD Optical Transceiver
ibevtPortSw-QSFP56-STACK-CONNECTOR                  OBJECT IDENTIFIER ::= { ibevtPortSwitchType 312 }  -- QSFP56-STACK-Transceiver
ibevtPortSw-QSFP56-UNKNOWN                          OBJECT IDENTIFIER ::= { ibevtPortSwitchType 313 }  -- Unknown QSFP56 Transceiver
ibevtPortSw-QSFP56-NO-CONNECTOR                     OBJECT IDENTIFIER ::= { ibevtPortSwitchType 314 }  -- QSFP56 No Connector
ibevtPortSw-DSFP-STACK-CONNECTOR                    OBJECT IDENTIFIER ::= { ibevtPortSwitchType 315 }  -- DSFP-STACK-Transceiver
ibevtPortSw-QSFP28-100GBASE-DR1                     OBJECT IDENTIFIER ::= { ibevtPortSwitchType 316 }  -- 100GBASE-DR1 QSFP28 Optical Transceiver
ibevtPortSw-QSFP28-100GBASE-FR1                     OBJECT IDENTIFIER ::= { ibevtPortSwitchType 317 }  -- 100GBASE-FR1 QSFP28 Optical Transceiver
ibevtPortSw-SFP-PLUS-10GBASE-EPON-OLT-PR30          OBJECT IDENTIFIER ::= { ibevtPortSwitchType 318 }  -- 10G BASE SFP+ EPON OLT PR30 Optical Transceiver
ibevtPortSw-SFP-PLUS-10GBASE-EPON-OLT-PR40          OBJECT IDENTIFIER ::= { ibevtPortSwitchType 319 }  -- 10G BASE SFP+ EPON OLT PR40 Optical Transceiver
ibevtPortSw-SFP-GPON-ONU-STICK-BP-SM1310-I          OBJECT IDENTIFIER ::= { ibevtPortSwitchType 320 }  -- SFP GPON Stick Optical Transceiver
ibevtPortSw-QSFPDD-400GBASE-LR4                     OBJECT IDENTIFIER ::= { ibevtPortSwitchType 321 }  -- 400GBASE-LR4 QSFP-DD Optical Transceiver
ibevtPortSw-QSFP-PLUS-40GBASE-LX4                   OBJECT IDENTIFIER ::= { ibevtPortSwitchType 322 }  -- 40GBASE-LX4 QSFP+ Optical Transceiver
ibevtPortSw-QSFPDD-400GBASE-DR4                     OBJECT IDENTIFIER ::= { ibevtPortSwitchType 323 }  -- 400GBASE-DR4 QSFP-DD Optical Transceiver
ibevtPortSw-SFP-PLUS-XGPON-COMBO-C-PLUS             OBJECT IDENTIFIER ::= { ibevtPortSwitchType 324 }  -- XGPON GPON COMBO C PLUS Optical Transceiver
ibevtPortSw-SFP-PLUS-XGSPON-COMBO-C-PLUS            OBJECT IDENTIFIER ::= { ibevtPortSwitchType 325 }  -- XGSPON GPON COMBO C PLUS Optical Transceiver
ibevtPortSw-SFP-PLUS-XGSPON-OLT-N2                  OBJECT IDENTIFIER ::= { ibevtPortSwitchType 326 }  -- XGSPON N2 OLT Optical Transceiver
ibevtPortSw-SFP-PLUS-XGSPON-OLT-E1                  OBJECT IDENTIFIER ::= { ibevtPortSwitchType 327 }  -- XGSPON E1 OLT Optical Transceiver
ibevtPortSw-SFP-GPON-ONU-C-PLUS-D                   OBJECT IDENTIFIER ::= { ibevtPortSwitchType 328 }  -- GPON C PLUS ONU Optical Transceiver
ibevtPortSw-SFP-PLUS-10G-EPON-ONU-PR40              OBJECT IDENTIFIER ::= { ibevtPortSwitchType 329 }  -- 10G EPON PR40 ONU Optical Transceiver
ibevtPortSw-SFP-PLUS-XGPON-ONU-N-E                  OBJECT IDENTIFIER ::= { ibevtPortSwitchType 330 }  -- XGPON N AND E ONU Optical Transceiver
ibevtPortSw-SFP-PLUS-10G-EPON-ONU-PR30              OBJECT IDENTIFIER ::= { ibevtPortSwitchType 331 }  -- 10G EPON PR30 ONU Optical Transceiver
ibevtPortSw-SFP-PLUS-XGSPON-ONU-N-E                 OBJECT IDENTIFIER ::= { ibevtPortSwitchType 332 }  -- XGSPON N AND E ONU Optical Transceiver
ibevtPortSw-SFP-GPON-ONU-B-PLUS                     OBJECT IDENTIFIER ::= { ibevtPortSwitchType 333 }  -- GPON B PLUS ONU Optical Transceiver
ibevtPortSw-SFP-2500BASE-LX10-I                     OBJECT IDENTIFIER ::= { ibevtPortSwitchType 334 }  -- 2500BASE-LX10 SFP Optical Transceiver
ibevtPortSw-QSFP56-100GBASE-AOC                     OBJECT IDENTIFIER ::= { ibevtPortSwitchType 335 }  -- 100GBASE-AOC QSFP56 Active Optical Cable
ibevtPortSw-QSFPDD-TO-8SFP56-STACK-CONNECTOR        OBJECT IDENTIFIER ::= { ibevtPortSwitchType 336 }  -- QSFPDD to 8SFP56 STACK Transceiver
ibevtPortSw-QSFP56-TO-2QSFP56-STACK-CONNECTOR       OBJECT IDENTIFIER ::= { ibevtPortSwitchType 337 }  -- QSFP56 to 2QSFP56 STACK Transceiver
ibevtPortSw-QSFP56-TO-2QSFP56-ACTIVE-OPTICAL-CABLE  OBJECT IDENTIFIER ::= { ibevtPortSwitchType 338 }  -- QSFP56 to 2QSFP56 AOC
ibevtPortSw-SFP56-STACK-CONNECTOR                   OBJECT IDENTIFIER ::= { ibevtPortSwitchType 339 }  -- SFP56 STACK Transceiver
ibevtPortSw-SFP-1000BASE-PoE                        OBJECT IDENTIFIER ::= { ibevtPortSwitchType 340 }  -- 1000BASE SFP PoE Optical Transceiver
ibevtPortSw-SFP-PLUS-10GBASE-PoE                    OBJECT IDENTIFIER ::= { ibevtPortSwitchType 341 }  -- 10GBASE SFP+ PoE Optical Transceiver
ibevtPortSw-QSFPDD-TO-4QSFP56-STACK-CONNECTOR       OBJECT IDENTIFIER ::= { ibevtPortSwitchType 342 }  -- QSFPDD to 4QSFP56 STACK Transceiver


ibevtPortSw-QSFPDD-400GBASE-AOC                     OBJECT IDENTIFIER ::= { ibevtPortSwitchType 343 }  -- 400GBASE-AOC QSFP-DD Active Optical Cable
ibevtPortSw-QSFPDD-TO-2QSFP56-ACTIVE-OPTICAL-CABLE  OBJECT IDENTIFIER ::= { ibevtPortSwitchType 344 }  -- QSFPDD to 2 QSFP56 AOC
ibevtPortSw-QSFPDD-TO-4QSFP56-ACTIVE-OPTICAL-CABLE  OBJECT IDENTIFIER ::= { ibevtPortSwitchType 345 }  -- QSFPDD to 4 QSFP56 AOC
ibevtPortSw-QSFPDD-TO-2QSFP56-STACK-CONNECTOR       OBJECT IDENTIFIER ::= { ibevtPortSwitchType 346 }  -- QSFPDD to 2 QSFP56 STACK Transceiver
ibevtPortSw-QSFP56-ACTIVE-COPPER-CONNECTOR          OBJECT IDENTIFIER ::= { ibevtPortSwitchType 347 }  -- QSFP56 Active COPPER Transceiver
ibevtPortSw-QSFP56-100GBASE-STACK-CONNECTOR         OBJECT IDENTIFIER ::= { ibevtPortSwitchType 348 }  -- 100GBASE QSFP56 STACK Transceiver
ibevtPortSw-QSFP112-400GBASE-SR4                    OBJECT IDENTIFIER ::= { ibevtPortSwitchType 349 }  -- 400GBASE-SR4 QSFP-112 Optical Transceiver
ibevtPortSw-QSFP112-400GBASE-DR4                    OBJECT IDENTIFIER ::= { ibevtPortSwitchType 350 }  -- 400GBASE-DR4 QSFP-112 Optical Transceiver
ibevtPortSw-QSFP112-400GBASE-FR4                    OBJECT IDENTIFIER ::= { ibevtPortSwitchType 351 }  -- 400GBASE-FR4 QSFP-112 Optical Transceiver
ibevtPortSw-1000BASE-BIDI-D-CSFP                    OBJECT IDENTIFIER ::= { ibevtPortSwitchType 352 }  -- 1000BASE CSFP BIDI Down Optical Transceiver
ibevtPortSw-QSFPDD-400GBASE-SR4                     OBJECT IDENTIFIER ::= { ibevtPortSwitchType 353 }  -- 400GBASE-SR4 QSFP-DD Optical Transceiver
ibevtPortSw-QSFP28-100GBASE-LR1                     OBJECT IDENTIFIER ::= { ibevtPortSwitchType 356 }  -- 100GBASE-LR1 QSFP28 Optical Transceiver
ibevtPortSw-QSFPDD-400GBASE-VR4                     OBJECT IDENTIFIER ::= { ibevtPortSwitchType 357 }  -- 400GBASE-VR4 QSFP-DD Optical Transceiver
ibevtPortSw-QSFPDD-400GBASE-PLR4                    OBJECT IDENTIFIER ::= { ibevtPortSwitchType 358 }  -- 400GBASE-PLR4 QSFP-DD Optical Transceiver
--
-- ibevtStack section:
--
ibevtStack     OBJECT IDENTIFIER ::= { ibEntityVendortypeObjects 11 }


END
