-- ==========================================================================
-- Copyright (C) 2023 Intelbras S.A. All rights reserved.
--
-- Description: The purpose of this MIB file is to provide the definition of
--              voice call record.
-- Reference:
-- Version: V1.1
-- History:
-- V1.0 2008-02-17 Initial version, created by Tian Xiaoqiang, Qu Jin
-- V1.1 2009-12-09 Add g729br8 to "IbCodecType", Wang Tong
-- ==========================================================================
IB-VOICE-CALL-HISTORY-MIB DEFINITIONS ::= BEGIN
IMPORTS
        OBJECT-TYPE, MODULE-IDENTITY, Integer32, Gauge32
    FROM SNMPv2-SMI
        InetAddressType, InetAddress
    FROM INET-ADDRESS-MIB
        InterfaceIndexOrZero
    FROM IF-MIB
        AbsoluteCounter32
    FROM DIAL-CONTROL-MIB
        TEXTUAL-CONVENTION, DisplayString, TimeStamp
    FROM SNMPv2-TC
        ibVoice
    FROM IB-OID-MIB;

ibVoCallHistory MODULE-IDENTITY
    LAST-UPDATED "200802170000Z"
    ORGANIZATION
        "Intelbras S.A. Industria de Telecomunicacao Eletronica Brasileria."
    CONTACT-INFO
        ""
    DESCRIPTION
        "This MIB file is to provide the definition of voice call
        history record information."
    REVISION "200802170000Z"
    DESCRIPTION
        "The initial version of this MIB file."
    ::= { ibVoice 16 }

-- ======================================
--          Type declaration
-- ======================================

IbGUid ::= TEXTUAL-CONVENTION
STATUS       current
DESCRIPTION
        "Represents a global call identifier.  The global call identifier is
         used as a unique identifier for an end-to-end call.  A zero length
         IbGUid indicates no value for the global call identifier."
SYNTAX       OCTET STRING(SIZE(0..16))

IbCodecType      ::= TEXTUAL-CONVENTION
STATUS       current
DESCRIPTION
        "Type of Codec."
SYNTAX  INTEGER
        {
        g711a(1),
        g711u(2),
        g723r53(3),
        g723r63(4),
        g729r8(5),
        g729a(6),
        g726r16(7),
        g726r24(8),
        g726r32(9),
        g726r40(10),
        unknown(11),
        g729br8(12)
        }

ibVoiceCallHistoryObjects OBJECT IDENTIFIER ::= { ibVoCallHistory 1 }

-- ===========================================================================
--                        ibCallHistoryTable
-- ===========================================================================
-- callHistoryTable
-- Table to store the past call information.  The destination number
-- and the call connect and disconnect time, and the disconnection
-- cause are stored.  These calls could be circuit switched or virtual
-- circuits.  History of each and every call is stored, of successful
-- calls as well as of unsuccessful and rejected calls.  An entry will
-- be created when a call is cleared.

ibCallHistoryTable OBJECT-TYPE
        SYNTAX      SEQUENCE OF IbCallHistoryEntry
        MAX-ACCESS  not-accessible
        STATUS      current
        DESCRIPTION
            "A table containing information about specific
             calls to a specific destination."
        ::= { ibVoiceCallHistoryObjects 1 }

ibCallHistoryEntry OBJECT-TYPE
        SYNTAX      IbCallHistoryEntry
        MAX-ACCESS  not-accessible
        STATUS      current
        DESCRIPTION
            "The information regarding a single connection."
        INDEX       { ibCallHistoryIndex }
        ::= { ibCallHistoryTable 1 }


IbCallHistoryEntry ::=
        SEQUENCE {
            ibCallHistoryIndex                     Integer32,
            ibCallHistorySetupTime                 TimeStamp,
            ibCallHistoryConnectTime               TimeStamp,
            ibCallHistoryTerminateTime             TimeStamp,
            ibCallHistoryPeerAddress               DisplayString,
            ibCallHistoryPeerId                    Integer32,
            ibCallHistoryLogicalIfIndex            InterfaceIndexOrZero,
            ibCallHistoryCallOrigin                INTEGER,
            ibCallHistoryChargedUnits              AbsoluteCounter32,
            ibCallHistoryInfoType                  INTEGER,
            ibCallHistoryTransmitPackets           AbsoluteCounter32,
            ibCallHistoryTransmitBytes             AbsoluteCounter32,
            ibCallHistoryReceivePackets            AbsoluteCounter32,
            ibCallHistoryReceiveBytes              AbsoluteCounter32
        }

ibCallHistoryIndex OBJECT-TYPE
        SYNTAX      Integer32 (1..2147483647)
        MAX-ACCESS  not-accessible
        STATUS      current
        DESCRIPTION
            "The index of the call history table.  It's a monotonically
             increasing integer for the sole purpose of indexing call
             disconnection events.  When it reaches to the maximum value,
             the value will back to 1."
        ::= { ibCallHistoryEntry 1 }

ibCallHistorySetupTime OBJECT-TYPE
        SYNTAX      TimeStamp
        MAX-ACCESS  read-only
        STATUS      current
        DESCRIPTION
            "The value of sysUpTime when the call was started."
        ::= { ibCallHistoryEntry 2 }

ibCallHistoryConnectTime OBJECT-TYPE
        SYNTAX      TimeStamp
        MAX-ACCESS  read-only
        STATUS      current
        DESCRIPTION
            "The value of sysUpTime when the call was connected.
             If the call is not connected, this object will have a
             value of zero."
        ::= { ibCallHistoryEntry 3 }

ibCallHistoryTerminateTime OBJECT-TYPE
        SYNTAX      TimeStamp
        MAX-ACCESS  read-only
        STATUS      current
        DESCRIPTION
            "The value of sysUpTime when the call was terminated."
        ::= { ibCallHistoryEntry 4 }

ibCallHistoryPeerAddress OBJECT-TYPE
        SYNTAX      DisplayString
        MAX-ACCESS  read-only
        STATUS      current
        DESCRIPTION
            "The number this call was connected to.  If the number is
             not available, it will have a length of zero."
        ::= { ibCallHistoryEntry 5 }

ibCallHistoryPeerId OBJECT-TYPE
        SYNTAX      Integer32 (0..2147483647)
        MAX-ACCESS  read-only
        STATUS      current
        DESCRIPTION
            "This object identifies a single peer.  This is the Id value
             of the peer table entry to which this call was made.  If a
             peer table entry for this call does not exist or is unknown,
             the value of this object will be zero."
        ::= { ibCallHistoryEntry 6 }

ibCallHistoryLogicalIfIndex OBJECT-TYPE
        SYNTAX      InterfaceIndexOrZero
        MAX-ACCESS  read-only
        STATUS      current
        DESCRIPTION
            "This is the ifIndex value of the logical interface through
             which this call was made.  For ISDN media, this would be
             the ifIndex of the B channel which was used for this call.
             If the ifIndex value is unknown, the value of this object
             will be zero."
        ::= { ibCallHistoryEntry 7 }

ibCallHistoryCallOrigin OBJECT-TYPE
        SYNTAX      INTEGER {
            originate(1),
            answer(2),
            callback(3)
        }
        MAX-ACCESS  read-only
        STATUS      current
        DESCRIPTION
            "The call origin.
             originate        The call that is initiated.
             answer           The call that is accepted.
             callback         Either rejects the call and then calls back,
                              or uses the 'Reverse charging' information
                              element if it is available. Note that callback(3)
                              is supposed to control charging, not security,
                              and applies to callback prior to accepting a call.
                              Callback for security reasons can be handled using
                              PPP callback."
        ::= { ibCallHistoryEntry 8 }

ibCallHistoryChargedUnits OBJECT-TYPE
        SYNTAX      AbsoluteCounter32
        MAX-ACCESS  read-only
        STATUS      current
        DESCRIPTION
            "The number of charged units for this connection.
             For incoming calls or if charging information is
             not supplied by the switch, the value of this object
             will be zero."
        ::= { ibCallHistoryEntry 9 }

ibCallHistoryInfoType OBJECT-TYPE
        SYNTAX      INTEGER {
            other(1),
            speech(2),
            unrestrictedDigital(3),
            unrestrictedDigital56(4),
            restrictedDigital(5),
            audio31(6),
            audio7(7),
            video(8),
            packetSwitched(9),
            fax(10)
        }
        MAX-ACCESS  read-only
        STATUS      current
        DESCRIPTION
            "The information type for this call.
             other                          E.g. for non-isdn media.
             speech                         Speech.
             unrestrictedDigital            Unrestricted digital information
                                            with 64k rate adaption.
             unrestrictedDigital56          Unrestricted digital information
                                            with 56k rate adaption.
             restrictedDigital              Restricted digital information.
             audio31                        3.1 kHz audio.
             audio7                         7 kHz audio.
             video                          Video.
             packetSwitched                 Packetswitch.
             fax                            Fax."
        ::= { ibCallHistoryEntry 10 }

ibCallHistoryTransmitPackets OBJECT-TYPE
        SYNTAX      AbsoluteCounter32
        MAX-ACCESS  read-only
        STATUS      current
        DESCRIPTION
            "The number of packets which were transmitted while this
             call was active."
        ::= { ibCallHistoryEntry 11 }

ibCallHistoryTransmitBytes OBJECT-TYPE
        SYNTAX      AbsoluteCounter32
        MAX-ACCESS  read-only
        STATUS      current
        DESCRIPTION
            "The number of bytes which were transmitted for this call."
        ::= { ibCallHistoryEntry 12 }

ibCallHistoryReceivePackets OBJECT-TYPE
        SYNTAX      AbsoluteCounter32
        MAX-ACCESS  read-only
        STATUS      current
        DESCRIPTION
            "The number of packets which were received for this call."
        ::= { ibCallHistoryEntry 13 }

ibCallHistoryReceiveBytes OBJECT-TYPE
        SYNTAX      AbsoluteCounter32
        MAX-ACCESS  read-only
        STATUS      current
        DESCRIPTION
            "The number of bytes which were received for this call."
        ::= { ibCallHistoryEntry 14 }

-- ===========================================================================
--                        ibVoiceCallHistoryTable
-- ===========================================================================

ibVoiceCallHistoryTable OBJECT-TYPE
        SYNTAX      SEQUENCE OF IbVoiceCallHistoryEntry
        MAX-ACCESS  not-accessible
        STATUS      current
        DESCRIPTION
            "This table is the voice extension to the call history table
            of DIAL-CONTROL-MIB.  It contains voice encapsulation call
            leg information that is derived from the statistics of lower
            layer telephony interface."
        ::= { ibVoiceCallHistoryObjects 2 }

ibVoiceCallHistoryEntry OBJECT-TYPE
        SYNTAX      IbVoiceCallHistoryEntry
        MAX-ACCESS  not-accessible
        STATUS      current
        DESCRIPTION
            "The information regarding a extended voice call history information."
        INDEX { ibCallHistoryIndex }
        ::= { ibVoiceCallHistoryTable 1 }

IbVoiceCallHistoryEntry ::= SEQUENCE {
        ibVoCallHistoryConnectionId    IbGUid,
        ibVoCallHistoryTxDuration      Gauge32,
        ibVoCallHistoryVoiceTxDuration Gauge32,
        ibVoCallHistoryFaxTxDuration   Gauge32,
        ibVoCallHistoryCoderType       IbCodecType,
        ibVoCallHistoryImgPageCount    Gauge32
    }

ibVoCallHistoryConnectionId OBJECT-TYPE
        SYNTAX      IbGUid
        MAX-ACCESS  read-only
        STATUS      current
        DESCRIPTION
            "The global call identifier of circuit switched network for
            the gateway call."
        ::= { ibVoiceCallHistoryEntry 1 }

ibVoCallHistoryTxDuration OBJECT-TYPE
        SYNTAX      Gauge32
        MAX-ACCESS  read-only
        STATUS      current
        DESCRIPTION
            "Duration of transmit path open from this peer to the
            voice gateway for the call.  The units is milliseconds."
        ::= { ibVoiceCallHistoryEntry 2 }

ibVoCallHistoryVoiceTxDuration OBJECT-TYPE
        SYNTAX      Gauge32
        MAX-ACCESS  read-only
        STATUS      current
        DESCRIPTION
            "Duration of voice transmitted from this peer to voice
            gateway for this call.  The voice utilization rate can be
            obtained by dividing this by ibVoCallHistoryTxDuration object.
            The units is milliseconds."
        ::= { ibVoiceCallHistoryEntry 3 }

ibVoCallHistoryFaxTxDuration OBJECT-TYPE
        SYNTAX      Gauge32
        MAX-ACCESS  read-only
        STATUS      current
        DESCRIPTION
            "Duration of fax transmitted from this peer to voice gateway
            for this call.  The fax utilization rate can be obtained by
            dividing this by ibVoCallHistoryTxDuration object.  The units
            is milliseconds."
        ::= { ibVoiceCallHistoryEntry 4 }

ibVoCallHistoryCoderType OBJECT-TYPE
        SYNTAX      IbCodecType
        MAX-ACCESS  read-only
        STATUS      current
        DESCRIPTION
            "The negotiated coder type.  It specifies the encode type to
            the PSTN leg of a call."
        ::= { ibVoiceCallHistoryEntry 5 }

ibVoCallHistoryImgPageCount OBJECT-TYPE
        SYNTAX      Gauge32
        MAX-ACCESS  read-only
        STATUS      current
        DESCRIPTION
            "The number of fax related image pages are received or
            transmitted via the peer for the call.  The units is page."
        ::= { ibVoiceCallHistoryEntry 6 }

-- ===========================================================================
--                        ibVoiceVoIPCallHistoryTable
-- ===========================================================================
ibVoiceVoIPCallHistoryTable OBJECT-TYPE
        SYNTAX      SEQUENCE OF IbVoiceVoIPCallHistoryEntry
        MAX-ACCESS  not-accessible
        STATUS      current
        DESCRIPTION
            "This table is the VoIP extension to the call active table of
            DIAL-CONTROL-MIB.  It contains VoIP call leg information about
            specific VoIP call destination."
        ::= { ibVoiceCallHistoryObjects 3 }

ibVoiceVoIPCallHistoryEntry OBJECT-TYPE
        SYNTAX      IbVoiceVoIPCallHistoryEntry
        MAX-ACCESS  not-accessible
        STATUS      current
        DESCRIPTION
            "The information regarding a extended VoIP call history
            information."
        INDEX {ibCallHistoryIndex }
        ::= { ibVoiceVoIPCallHistoryTable 1 }

IbVoiceVoIPCallHistoryEntry ::= SEQUENCE {
        ibVoVoIPCallHistoryConnectionId    IbGUid,
        ibVoVoIPCallHistoryRemSigIPType    InetAddressType,
        ibVoVoIPCallHistoryRemSigIPAddr    InetAddress,
        ibVoVoIPCallHistoryRemSigPort      Integer32,
        ibVoVoIPCallHistoryRemMedIPType    InetAddressType,
        ibVoVoIPCallHistoryRemMedIPAddr    InetAddress,
        ibVoVoIPCallHistoryRemMedPort      Integer32,
        ibVoVoIPCallHistorySessProtocol    INTEGER,
        ibVoVoIPCallHistoryCoderType       IbCodecType
    }

ibVoVoIPCallHistoryConnectionId OBJECT-TYPE
        SYNTAX      IbGUid
        MAX-ACCESS  read-only
        STATUS      current
        DESCRIPTION
            "The global call identifier of packet-switched network for the
            gateway call."
        ::= { ibVoiceVoIPCallHistoryEntry 1 }

ibVoVoIPCallHistoryRemSigIPType OBJECT-TYPE
        SYNTAX      InetAddressType
        MAX-ACCESS  read-only
        STATUS      current
        DESCRIPTION
            "The type of remote system signalling IP address for the VoIP call."
        ::= { ibVoiceVoIPCallHistoryEntry 2 }

ibVoVoIPCallHistoryRemSigIPAddr OBJECT-TYPE
        SYNTAX      InetAddress
        MAX-ACCESS  read-only
        STATUS      current
        DESCRIPTION
            "Remote system signalling IP address for the VoIP call."
        ::= { ibVoiceVoIPCallHistoryEntry 3 }

ibVoVoIPCallHistoryRemSigPort OBJECT-TYPE
        SYNTAX      Integer32(0..65535)
        MAX-ACCESS  read-only
        STATUS      current
        DESCRIPTION
            "Remote system UDP listener signalling port to which to
            transmit voice packets."
        ::= { ibVoiceVoIPCallHistoryEntry 4 }

ibVoVoIPCallHistoryRemMedIPType OBJECT-TYPE
        SYNTAX      InetAddressType
        MAX-ACCESS  read-only
        STATUS      current
        DESCRIPTION
            "The type of remote system media IP address for the VoIP call."
        ::= { ibVoiceVoIPCallHistoryEntry 5 }

ibVoVoIPCallHistoryRemMedIPAddr OBJECT-TYPE
        SYNTAX      InetAddress
        MAX-ACCESS  read-only
        STATUS      current
        DESCRIPTION
            "Remote system media IP address for the VoIP call."
        ::= { ibVoiceVoIPCallHistoryEntry 6 }

ibVoVoIPCallHistoryRemMedPort OBJECT-TYPE
        SYNTAX      Integer32(0..65535)
        MAX-ACCESS  read-only
        STATUS      current
        DESCRIPTION
            "Remote system UDP listener media port to which to transmit voice
            packets."
        ::= { ibVoiceVoIPCallHistoryEntry 7 }

ibVoVoIPCallHistorySessProtocol OBJECT-TYPE
        SYNTAX INTEGER {
            unknown(1),
            h323(2),
            sip(3)
            }
        MAX-ACCESS  read-only
        STATUS      current
        DESCRIPTION
            "The object specifies the session protocol to be used for internet
            call between local and remote router via IP backbone.
            unknown        The protocol is unknown.
            h323           The protocol is H323.
            sip            The protocol is session initiation."
        ::= { ibVoiceVoIPCallHistoryEntry 8 }

ibVoVoIPCallHistoryCoderType OBJECT-TYPE
        SYNTAX      IbCodecType
        MAX-ACCESS  read-only
        STATUS      current
        DESCRIPTION
            "The negotiated coder type.  It specifies the encode type to the
            VoIP leg of a call."
        ::= { ibVoiceVoIPCallHistoryEntry 9 }

END
