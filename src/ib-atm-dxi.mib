-- ============================================================================
-- Copyright (C) 2023 Intelbras S.A. All rights reserved.
-- Description:  This MIB is used for configuration of ATM-DXI.
--               include :1.ATM-DXI PVC
--                        2.ATM-DXI MAP
-- Reference:
-- Version: V1.0
-- History:
--   V1.0 2005/04/14 created by Liguanmin
-- ============================================================================
IB-ATM-DXI-MIB DEFINITIONS ::= BEGIN

      IMPORTS
                ibCommon
                    FROM IB-OID-MIB
                ifIndex
                    FROM RFC1213-MIB
                OBJECT-GROUP,MODULE-COMPLIANCE
                    FROM SNMPv2-CONF
                Integer32, OBJECT-TYPE, MODULE-IDENTITY
                    FROM SNMPv2-SMI
                InetAddressType,InetAddress
                    FROM INET-ADDRESS-MIB
                RowStatus
                    FROM SNMPv2-TC;

      ibAtmDxi MODULE-IDENTITY
                LAST-UPDATED "200504141518Z"            -- 14 April, 2005 at 15:18 GMT
                ORGANIZATION
                    "Intelbras S.A. Industria de Telecomunicacao Eletronica Brasileria."
                CONTACT-INFO
                    ""
                DESCRIPTION
                        "This MIB contains objects to manage configuration of ATM-DXI.
                         There are no constraints on this MIB."
                REVISION "200504141518Z"                -- 14 April, 2005 at 15:18 GMT
                DESCRIPTION
                        "The initial revision of this MIB module."
                ::= { ibCommon 49 }

--
-- Node definitions
--
        ibAtmDxiScalarGroup OBJECT IDENTIFIER ::= { ibAtmDxi 1 }

        ibAtmDxiConfMode OBJECT-TYPE
                SYNTAX INTEGER
                        {
                        mode1a(1),
                        mode1b(2),
                        mode2(3)
                        }
                MAX-ACCESS read-only
                STATUS current
                DESCRIPTION
                        "This node identifies the ATM-DXI mode being
                        used at the ATM-DXI port."
                ::= { ibAtmDxiScalarGroup 1 }


        ibAtmDxiIfObjects OBJECT IDENTIFIER ::= { ibAtmDxi 2 }


        ibAtmDxiPvcTable OBJECT-TYPE
                SYNTAX SEQUENCE OF IbAtmDxiPvcEntry
                MAX-ACCESS not-accessible
                STATUS current
                DESCRIPTION
                        "This table describes information of PVC in ATM-DXI interface."
                ::= { ibAtmDxiIfObjects 1 }


        ibAtmDxiPvcEntry OBJECT-TYPE
                SYNTAX IbAtmDxiPvcEntry
                MAX-ACCESS not-accessible
                STATUS current
                DESCRIPTION
                        "The entry of ibAtmDxiPvcTable."
                INDEX { ifIndex, ibAtmDxiPvcVpi, ibAtmDxiPvcVci }
                ::= { ibAtmDxiPvcTable 1 }


        IbAtmDxiPvcEntry ::=
                SEQUENCE {
                        ibAtmDxiPvcVpi
                                Integer32,
                        ibAtmDxiPvcVci
                                Integer32,
                        ibAtmDxiPvcDFA
                                Integer32,
                        ibAtmDxiPvcEncType
                                INTEGER,
                        ibAtmDxiPvcMapCount
                                Integer32,
                        ibAtmDxiPvcRowStatus
                                RowStatus
                 }


        ibAtmDxiPvcVpi OBJECT-TYPE
                SYNTAX Integer32 (0..15)
                MAX-ACCESS not-accessible
                STATUS current
                DESCRIPTION
                        "The value of VPI.  It can't be 0 if ibAtmDxiPvcVci is 0."
                ::= { ibAtmDxiPvcEntry 1 }


        ibAtmDxiPvcVci OBJECT-TYPE
                SYNTAX Integer32 (0..63)
                MAX-ACCESS not-accessible
                STATUS current
                DESCRIPTION
                        "The value of VCI.  It can't be 0 if ibAtmDxiPvcVpi is 0."
                ::= { ibAtmDxiPvcEntry 2 }


        ibAtmDxiPvcDFA OBJECT-TYPE
                SYNTAX Integer32
                MAX-ACCESS read-create
                STATUS current
                DESCRIPTION
                        "The index of PVC.  It is equal with vci and VPI.  And this node value
                        is correlate with ibAtmDxiPvcVpi and ibAtmDxiPvcVci. "
                ::= { ibAtmDxiPvcEntry 3 }


        ibAtmDxiPvcEncType OBJECT-TYPE
                SYNTAX INTEGER
                        {
                        snap(1),
                        nlpid(2),
                        mux(3)
                        }
                MAX-ACCESS read-create
                STATUS current
                DESCRIPTION
                        "Encapsulation type of the frame."
                DEFVAL { snap }
                ::= { ibAtmDxiPvcEntry 4 }


        ibAtmDxiPvcMapCount OBJECT-TYPE
                SYNTAX Integer32 (0..32)
                MAX-ACCESS read-create
                STATUS current
                DESCRIPTION
                        "The number of map.  One map can only associate with one PVC, but
                        one PVC can associate with 32 maps.  This node is the map count
                        which one PVC associated with."
                ::= { ibAtmDxiPvcEntry 5 }


        ibAtmDxiPvcRowStatus OBJECT-TYPE
                SYNTAX RowStatus
                MAX-ACCESS read-create
                STATUS current
                DESCRIPTION
                        "Only support 'destroy' 'createAndGo' and 'active'."
                ::= { ibAtmDxiPvcEntry 6 }


        ibAtmDxiMapTable OBJECT-TYPE
                SYNTAX SEQUENCE OF IbAtmDxiMapEntry
                MAX-ACCESS not-accessible
                STATUS current
                DESCRIPTION
                        "This table describes PVC map information."
                ::= { ibAtmDxiIfObjects 2 }


        ibAtmDxiMapEntry OBJECT-TYPE
                SYNTAX IbAtmDxiMapEntry
                MAX-ACCESS not-accessible
                STATUS current
                DESCRIPTION
                        "The entry of ibAtmDxiMapTable."
                INDEX { ifIndex,
                        ibAtmDxiMapPeerIpType,
                        ibAtmDxiMapPeerIp,
                        ibAtmDxiMapPvcVpi,
                        ibAtmDxiMapPvcVci,
                        ibAtmDxiMapType
                      }
                ::= { ibAtmDxiMapTable 1 }


        IbAtmDxiMapEntry ::=
                SEQUENCE {
                        ibAtmDxiMapPeerIpType
                                InetAddressType,
                        ibAtmDxiMapPeerIp
                                InetAddress,
                        ibAtmDxiMapPvcVpi
                                Integer32,
                        ibAtmDxiMapPvcVci
                                Integer32,
                        ibAtmDxiMapType
                                INTEGER,
                        ibAtmDxiMapInarpTime
                                Integer32,
                        ibAtmDxiMapBroEnable
                                INTEGER,
                        ibAtmDxiMapRowStatus
                                RowStatus
                 }

        ibAtmDxiMapPeerIpType OBJECT-TYPE
                SYNTAX InetAddressType
                MAX-ACCESS not-accessible
                STATUS current
                DESCRIPTION
                        "The type of ip address: IPv4 or IPv6."
                ::= { ibAtmDxiMapEntry 1 }

        ibAtmDxiMapPeerIp OBJECT-TYPE
                SYNTAX InetAddress
                MAX-ACCESS not-accessible
                STATUS current
                DESCRIPTION
                        "The peer ip address.  This ip address is the peer ip
                        address which the frame will arrive."
                ::= { ibAtmDxiMapEntry 2 }

        ibAtmDxiMapPvcVpi OBJECT-TYPE
                SYNTAX Integer32 (0..15)
                MAX-ACCESS not-accessible
                STATUS current
                DESCRIPTION
                        "The VPI of PVC.  It can't be 0 if ibAtmDxiMapPvcVci is 0."
                ::= { ibAtmDxiMapEntry 3 }

        ibAtmDxiMapPvcVci OBJECT-TYPE
                SYNTAX Integer32 (0..63)
                MAX-ACCESS not-accessible
                STATUS current
                DESCRIPTION
                        "The VCI of PVC.  It can't be 0 if ibAtmDxiMapPvcVpi is 0."
                ::= { ibAtmDxiMapEntry 4 }

        ibAtmDxiMapType OBJECT-TYPE
                SYNTAX INTEGER
                        {
                        address(1),
                        inarp(2),
                        default(3)
                        }
                MAX-ACCESS not-accessible
                STATUS current
                DESCRIPTION
                        "Pvc map type."
                ::= { ibAtmDxiMapEntry 5 }

        ibAtmDxiMapInarpTime OBJECT-TYPE
                SYNTAX Integer32 (0 | 5..10)
                MAX-ACCESS read-create
                STATUS current
                DESCRIPTION
                        "The interval time of inarp request.  This node describes
                        the interval time inarp request frame sent.  If the ibAtmDxiMapType
                        isn't inarp, this value is 0.  Its unit is minute."
                DEFVAL { 10 }
                ::= { ibAtmDxiMapEntry 6 }

        ibAtmDxiMapBroEnable OBJECT-TYPE
                SYNTAX INTEGER
                        {
                        enable(1),
                        disable(2)
                        }
                MAX-ACCESS read-create
                STATUS current
                DESCRIPTION
                        "Whether ATM-DXI map enable broadcast or not."
                DEFVAL { 2 }
                ::= { ibAtmDxiMapEntry 7 }

        ibAtmDxiMapRowStatus OBJECT-TYPE
                SYNTAX RowStatus
                MAX-ACCESS read-create
                STATUS current
                DESCRIPTION
                        "Only support 'destroy', 'createAndGo' and 'active'."
                ::= { ibAtmDxiMapEntry 8 }


        ibAtmDxiConformance OBJECT IDENTIFIER ::= { ibAtmDxi 3 }

        ibAtmDxiCompliances OBJECT IDENTIFIER ::= { ibAtmDxiConformance 1 }

        ibAtmDxiCompliance MODULE-COMPLIANCE
               STATUS current
               DESCRIPTION
                       "The compliance statement."
               MODULE
               MANDATORY-GROUPS { ibPVCMAPGroup }
               GROUP ibAtmDxiGeneralGroup
               DESCRIPTION
                       "If ATM-DXI protocol supports other ATM-DXI modes,
                       this group must be supported."
               ::= { ibAtmDxiCompliances 1 }

        ibAtmDxiGroup OBJECT IDENTIFIER ::= { ibAtmDxiConformance 2 }

        ibPVCMAPGroup OBJECT-GROUP
                OBJECTS { ibAtmDxiPvcDFA, ibAtmDxiPvcEncType, ibAtmDxiPvcMapCount,
                          ibAtmDxiPvcRowStatus, ibAtmDxiMapBroEnable, ibAtmDxiMapInarpTime,
                          ibAtmDxiMapRowStatus }
                STATUS current
                DESCRIPTION
                        "This group includes nodes which are associated with interface."
                ::= { ibAtmDxiGroup 1 }

        ibAtmDxiGeneralGroup OBJECT-GROUP
                OBJECTS { ibAtmDxiConfMode }
                STATUS current
                DESCRIPTION
                        "This group includes the general nodes about ATM-DXI."
                ::= { ibAtmDxiGroup 2 }

END
