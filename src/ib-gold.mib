-- =================================================================
-- Copyright (C) 2023 Intelbras S.A. All rights reserved.
--
-- Description: GOLD MIB
-- Version: V1.0
-- History:
--   V1.0 Created by meishenhe
--        Initial version 2021-03-13
-- =================================================================
IB-GOLD-MIB DEFINITIONS ::= BEGIN

IMPORTS
        ibCommon
    FROM IB-OID-MIB
        Integer32, OBJECT-TYPE, MODULE-IDENTITY, NOTIFICATION-TYPE
    FROM SNMPv2-SMI;

ibGold MODULE-IDENTITY
    LAST-UPDATED "202103131502Z"
    ORGANIZATION
        "Intelbras S.A. Industria de Telecomunicacao Eletronica Brasileria."
    CONTACT-INFO
        ""
    DESCRIPTION
        "This MIB is used to manage GOLD(Generic OnLine Diagnostics) detection.
         This MIB is applicable to products that support GOLD."
    REVISION "202103131502Z"
    DESCRIPTION
        "The initial revision of this MIB module."
    ::= { ibCommon 203 }

ibGoldTrap OBJECT IDENTIFIER ::= { ibGold 1 }

ibGoldTrapOjbects OBJECT IDENTIFIER ::= { ibGoldTrap 0 }

-- All trap definitions should be placed under this object.
ibGoldLipcLinkFail NOTIFICATION-TYPE
    OBJECTS
        {
            ibGoldLipcLinkSourceChassisID,
            ibGoldLipcLinkSourceSlotID,
            ibGoldLipcLinkSourceCpuID,
            ibGoldLipcLinkDestChassisID,
            ibGoldLipcLinkDestSlotID,
            ibGoldLipcLinkDestCpuID
        }
    STATUS      current
    DESCRIPTION
        "the ibGoldLipcLinkFail trap indicates that the GOLD function
        changed to the fail state."
    ::= { ibGoldTrapOjbects 1 }

ibGoldLipcLinkRecover NOTIFICATION-TYPE
    OBJECTS
        {
            ibGoldLipcLinkSourceChassisID,
            ibGoldLipcLinkSourceSlotID,
            ibGoldLipcLinkSourceCpuID,
            ibGoldLipcLinkDestChassisID,
            ibGoldLipcLinkDestSlotID,
            ibGoldLipcLinkDestCpuID
        }
    STATUS      current
    DESCRIPTION
        "the ibGoldLipcLinkRecover trap indicates that the GOLD function
        changed to the recover state."
    ::= { ibGoldTrapOjbects 2 }

ibGoldTrapObjectDefinitions OBJECT IDENTIFIER ::= { ibGoldTrap 1 }
-- All objects used for TRAP only are defined here.

ibGoldLipcLinkSourceChassisID OBJECT-TYPE
    SYNTAX         Integer32(0..65535)
    MAX-ACCESS     accessible-for-notify
    STATUS         current
    DESCRIPTION
        "The source chassis id of lipc node."
    ::= { ibGoldTrapObjectDefinitions 1 }

ibGoldLipcLinkSourceSlotID OBJECT-TYPE
    SYNTAX         Integer32(0..65535)
    MAX-ACCESS     accessible-for-notify
    STATUS         current
    DESCRIPTION
        "The source slot id of lipc node."
    ::= { ibGoldTrapObjectDefinitions 2 }

ibGoldLipcLinkSourceCpuID OBJECT-TYPE
    SYNTAX         Integer32(0..65535)
    MAX-ACCESS     accessible-for-notify
    STATUS         current
    DESCRIPTION
        "The source cpu id of lipc node."
    ::= { ibGoldTrapObjectDefinitions 3 }

ibGoldLipcLinkDestChassisID OBJECT-TYPE
    SYNTAX         Integer32(0..65535)
    MAX-ACCESS     accessible-for-notify
    STATUS         current
    DESCRIPTION
        "The destination chassis id of lipc node."
    ::= { ibGoldTrapObjectDefinitions 4 }

ibGoldLipcLinkDestSlotID OBJECT-TYPE
    SYNTAX         Integer32(0..65535)
    MAX-ACCESS     accessible-for-notify
    STATUS         current
    DESCRIPTION
        "The destination slot id of lipc node."
    ::= { ibGoldTrapObjectDefinitions 5 }

ibGoldLipcLinkDestCpuID OBJECT-TYPE
    SYNTAX         Integer32(0..65535)
    MAX-ACCESS     accessible-for-notify
    STATUS         current
    DESCRIPTION
        "The destination cpu id of lipc node."
    ::= { ibGoldTrapObjectDefinitions 6 }

END
