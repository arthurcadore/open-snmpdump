-- ============================================================================
-- Copyright (C) 2023 Intelbras S.A. All rights reserved.
--
-- Description: There are three standard MIB definitions, "LLDP-MIB", "LLDP-EXT-
--     DOT1-MIB", "LLDP-EXT-DOT3-MIB", define almost all MIB objects of LLDP.
--     This document defines more MIB objects privately For LLDP implementation.
--      1)LLDP default global status is disabled, a management object needed to
--        enable it.
--      2)LLDP needs to be compliable with CDP (Non standard IEEE link layer di-
--        scovery protocol).  A management object needed to enable or disable
--        compliance.
--      3)For compliance with CDP, port based control management object is need-
--        ed.
--      4)LLDP is able to control the status of a port that connects to a neigh-
--        bor by matching local neighbor identity information with the informat-
--        ion in the received chassis ID TLV and port ID TLV.
-- Reference:
-- Version: V1.4
-- History:
-- V1.0 created by qizhenglin 2009-03-20
-- V1.1 2015-09-01 Updated by zhaixiaoxiang
--      Add iblldpPortConfigValidationAction and iblldpPortConfigAgingAction
--       to iblldpPortConfigTable
--      Add the iblldpNbIdentityTable, iblldpPortStatusTable, and iblldpN-
--      otifications tables.
-- V1.2 2019-03-07 Updated by tuchanyong
--      Add iblldpRemManAddrTable.
-- V1.3 2019-09-17 Updated by tongwenxin
--      The value 'rx(3)' is added for data type 'iblldpPortConfigCDPComplian-
--      ceStatus'.
-- V1.4 2022-07-18 Updated by Zheng jun
--      add trap iblldpGlobalEnableStatus and iblldpLocManAddrChange
-- ============================================================================
IB-LLDP-EXT-MIB DEFINITIONS ::= BEGIN

IMPORTS
    MODULE-IDENTITY, OBJECT-TYPE, Integer32, NOTIFICATION-TYPE
        FROM SNMPv2-SMI
    TruthValue, RowStatus
        FROM SNMPv2-TC
    ibCommon
        FROM IB-OID-MIB
    AddressFamilyNumbers
        FROM IANA-ADDRESS-FAMILY-NUMBERS-MIB
    LldpPortNumber, lldpRemTimeMark, lldpRemLocalPortNum, lldpRemIndex,
    LldpManAddrIfSubtype, lldpRemManAddr, lldpRemManAddrSubtype
        FROM LLDP-MIB;

iblldp MODULE-IDENTITY
    LAST-UPDATED "202207181038Z"
    ORGANIZATION
        "Intelbras S.A. Industria de Telecomunicacao Eletronica Brasileria."
    CONTACT-INFO
        ""
    DESCRIPTION
        "LLDP extended management information."
    REVISION  "202207181038Z"
    DESCRIPTION "Add trap iblldpGlobalEnableStatus and iblldpLocManAddrChange."
    REVISION  "201909170000Z"
    DESCRIPTION "Add the value of iblldpPortConfigCDPComplian."
    REVISION  "201903070000Z"
    DESCRIPTION "Add iblldpRemManAddrTable."
    REVISION  "201509010000Z"
    DESCRIPTION "Update this MIB module."
    REVISION  "200903210000Z"
    DESCRIPTION "The initial revision of this MIB module."
    ::= { ibCommon 100 }

iblldpObjects                    OBJECT IDENTIFIER ::= { iblldp 1 }
iblldpNotifications              OBJECT IDENTIFIER ::= { iblldp 2 }
--
-- LLDP extended MIB Objects
--
iblldpConfiguration              OBJECT IDENTIFIER ::= { iblldpObjects 1 }
iblldpRemoteSystemsData          OBJECT IDENTIFIER ::= { iblldpObjects 2 }
--
-- LLDP extended global configuration
--
iblldpAdminStatus OBJECT-TYPE
    SYNTAX TruthValue
    MAX-ACCESS  read-write
    STATUS      current
    DESCRIPTION
        "The global administratively desired status of the local LLDP agent."
    ::= { iblldpConfiguration 1 }

iblldpComplianceCDPStatus OBJECT-TYPE
    SYNTAX TruthValue
    MAX-ACCESS  read-write
    STATUS      current
    DESCRIPTION
        "The global administratively desired status of CDP Compliance."
    ::= { iblldpConfiguration 2 }

--
-- iblldpPortConfigTable: LLDP configuration on a per port basis
--

iblldpPortConfigTable   OBJECT-TYPE
    SYNTAX      SEQUENCE OF IblldpPortConfigEntry
    MAX-ACCESS  not-accessible
    STATUS      current
    DESCRIPTION
        "The port-based table that controls extended functions."
    ::= { iblldpConfiguration 3 }

iblldpPortConfigEntry   OBJECT-TYPE
    SYNTAX      IblldpPortConfigEntry
    MAX-ACCESS  not-accessible
    STATUS      current
    DESCRIPTION
        "LLDP extended configuration information for a particular port.  This c-
        onfiguration parameter controls compliance with other non-standard link
        layer discovery protocol such as CDP."
    INDEX  { iblldpPortConfigPortNum }
    ::= { iblldpPortConfigTable 1 }

IblldpPortConfigEntry ::= SEQUENCE {
    iblldpPortConfigPortNum         LldpPortNumber,
    iblldpPortConfigCDPComplianceStatus        INTEGER,
    iblldpPortConfigValidationAction           Integer32,
    iblldpPortConfigAgingAction                Integer32 }

iblldpPortConfigPortNum   OBJECT-TYPE
    SYNTAX      LldpPortNumber
    MAX-ACCESS  not-accessible
    STATUS      current
    DESCRIPTION
        "The index value used to identify the port component associated with th-
         is entry."
    ::= { iblldpPortConfigEntry 1 }

iblldpPortConfigCDPComplianceStatus  OBJECT-TYPE
    SYNTAX INTEGER {
       txAndRx(1),
       disabled(2),
       rx(3)
    }
    MAX-ACCESS read-write
    STATUS     current
    DESCRIPTION
        "The administratively desired CDP Compliance status of the local LLDP a-
        gent.  If the associated iblldpPortConfigCDPComplianceStatus object h-
        as a value of 'txAndRx', then the LLDP agent will receive CDP frames on
        this port, and will transmit CDP frames only after receiving a CDP fram-
        es.If the associated lldpPortConfigAdminStatus object has a value of 'd-
        isabled', LLDP agent will not transmit or receive CDP frames on this po-
        rt.If the associated iblldpPortConfigCDPComplianceStatus object has a
        value of 'rx', then the LLDP agent will receive CDP frames on this port,
        and will not transmit CDP frames."
    DEFVAL  { disabled }
    ::= { iblldpPortConfigEntry 2 }

iblldpPortConfigValidationAction  OBJECT-TYPE
    SYNTAX Integer32
    MAX-ACCESS read-write
    STATUS     current
    DESCRIPTION
        "Action that neighbor validation takes on a port.  Bit 1 indicates the
        block action.  Bit 2 indicates the shutdown action."
    ::= { iblldpPortConfigEntry 3 }

iblldpPortConfigAgingAction  OBJECT-TYPE
    SYNTAX Integer32
    MAX-ACCESS read-write
    STATUS     current
    DESCRIPTION
        "Action that neighbor aging takes on a port.  Bit 1 indicates the block
         action.  Bit 2 indicates the shutdown action."
    ::= { iblldpPortConfigEntry 4 }

--
-- iblldpNbIdentityTable:
--

iblldpNbIdentityTable   OBJECT-TYPE
    SYNTAX      SEQUENCE OF IblldpNbIdentityEntry
    MAX-ACCESS  not-accessible
    STATUS      current
    DESCRIPTION
        "This table contains the neighbor identity information of a port."
    ::= { iblldpConfiguration 4 }

iblldpNbIdentityEntry   OBJECT-TYPE
    SYNTAX      IblldpNbIdentityEntry
    MAX-ACCESS  not-accessible
    STATUS      current
    DESCRIPTION
        "A list of objects containing the neighbor identity information of a
        port."
    INDEX  { iblldpNbIdentityPortNum }
    ::= { iblldpNbIdentityTable 1 }

IblldpNbIdentityEntry ::= SEQUENCE {
    iblldpNbIdentityPortNum          LldpPortNumber,
    iblldpNbIdentityChassisIDSubtype INTEGER,
    iblldpNbIdentityChassisID        OCTET STRING,
    iblldpNbIdentityPortIDSubtype    INTEGER,
    iblldpNbIdentityPortID           OCTET STRING,
    iblldpNbIdentityRowStatus        RowStatus }

iblldpNbIdentityPortNum   OBJECT-TYPE
    SYNTAX      LldpPortNumber
    MAX-ACCESS  not-accessible
    STATUS      current
    DESCRIPTION
        "Port number."
    ::= { iblldpNbIdentityEntry 1 }

iblldpNbIdentityChassisIDSubtype  OBJECT-TYPE
    SYNTAX INTEGER {
        default(0),
        chassisComponent(1),
        interfaceAlias(2),
        portComponent(3),
        macAddress(4),
        networkAddress(5),
        interfaceName(6),
        local(7)
    }
    MAX-ACCESS read-write
    STATUS     current
    DESCRIPTION
        "Chassis ID subtype.  The value range is 0 to 7, and the default value
        is 0.  The values 1 to 7 represents the chassis component, interface al-
        ias, port component, MAC address, network address, interface name, and
        locally assigned subtypes, respectively."
    ::= { iblldpNbIdentityEntry 2 }

iblldpNbIdentityChassisID  OBJECT-TYPE
    SYNTAX OCTET STRING (SIZE(0..255))
    MAX-ACCESS read-write
    STATUS     current
    DESCRIPTION
        "Chassis ID, a case-insensitive string of 1 to 255 characters.
        By default, the string is empty.  If the value of
        iblldpNbIdentityChassisIDSubtype is 4, the chassis ID must be
        a MAC address in H-H-H format."
    ::= { iblldpNbIdentityEntry 3 }

iblldpNbIdentityPortIDSubtype  OBJECT-TYPE
    SYNTAX INTEGER {
        default(0),
        interfaceAlias(1),
        portComponent(2),
        macAddress(3),
        networkAddress(4),
        interfaceName(5),
        agentCircuitId(6),
        local(7)
    }
    MAX-ACCESS read-write
    STATUS     current
    DESCRIPTION
        "Port ID subtype.  The value range is 0 to 7, and the default
         value is 0.  The values 1 to 7 represents the interface alias, port co-
         mponent, MAC address, network address, interface name, agent circuit
         ID, and locally assigned subtypes, respectively."
    ::= { iblldpNbIdentityEntry 4 }

iblldpNbIdentityPortID  OBJECT-TYPE
    SYNTAX OCTET STRING (SIZE(0..255))
    MAX-ACCESS read-write
    STATUS     current
    DESCRIPTION
        "Port ID, a case-insensitive string of 1 to 255 characters.
        By default, the string is empty.  If the value of
        iblldpNbIdentityPortIDSubtype is 3, the port ID must be
        a MAC address in H-H-H format."
    ::= { iblldpNbIdentityEntry 5 }

iblldpNbIdentityRowStatus   OBJECT-TYPE
    SYNTAX      RowStatus
    MAX-ACCESS  read-create
    STATUS      current
    DESCRIPTION
        "Row status: CreateAndGo, Active, or Destroy."
    ::= { iblldpNbIdentityEntry 6 }

--
-- iblldpPortStatusTable
--

iblldpPortStatusTable   OBJECT-TYPE
    SYNTAX      SEQUENCE OF IblldpPortStatusEntry
    MAX-ACCESS  not-accessible
    STATUS      current
    DESCRIPTION
        "This table contains the state information of a port."
    ::= { iblldpConfiguration 5 }

iblldpPortStatusEntry   OBJECT-TYPE
    SYNTAX      IblldpPortStatusEntry
    MAX-ACCESS  not-accessible
    STATUS      current
    DESCRIPTION
        "A list of objects containing the state information of a port."
    INDEX  { iblldpPortStatusPortNum }
    ::= { iblldpPortStatusTable 1 }

IblldpPortStatusEntry ::= SEQUENCE {
    iblldpPortStatusPortNum      LldpPortNumber,
    iblldpPortValidationStatus   Integer32,
    iblldpPortAgingStatus        Integer32
    }

iblldpPortStatusPortNum   OBJECT-TYPE
    SYNTAX      LldpPortNumber
    MAX-ACCESS  accessible-for-notify
    STATUS      current
    DESCRIPTION
        "Port number."
    ::= { iblldpPortStatusEntry 1 }

iblldpPortValidationStatus  OBJECT-TYPE
    SYNTAX Integer32
    MAX-ACCESS read-only
    STATUS     current
    DESCRIPTION
        "Neighbor validation protection status of the port.  The default value
         is 0."
    ::= { iblldpPortStatusEntry 2 }

iblldpPortAgingStatus  OBJECT-TYPE
    SYNTAX Integer32
    MAX-ACCESS read-only
    STATUS     current
    DESCRIPTION
        "Neighbor aging protection status of the port.  The default value is
         0."
    ::= { iblldpPortStatusEntry 3 }

--
-- iblldpRemManAddrTable
--

iblldpRemManAddrTable OBJECT-TYPE
    SYNTAX SEQUENCE OF IblldpRemManAddrEntry
    MAX-ACCESS not-accessible
    STATUS current
    DESCRIPTION
        "This table contains management address information on the remote
         system."
    ::= { iblldpRemoteSystemsData 1 }

iblldpRemManAddrEntry OBJECT-TYPE
    SYNTAX IblldpRemManAddrEntry
    MAX-ACCESS not-accessible
    STATUS current
    DESCRIPTION
        "A list of objects containing management address information."
    INDEX { lldpRemTimeMark,
            lldpRemLocalPortNum,
            lldpRemIndex,
            lldpRemManAddrSubtype,
            lldpRemManAddr }
    ::= { iblldpRemManAddrTable 1 }

IblldpRemManAddrEntry ::=    SEQUENCE {
    iblldpRemManAddrSubtype      AddressFamilyNumbers,
    iblldpRemManAddr             OCTET STRING,
    iblldpRemManAddrIfSubtype    LldpManAddrIfSubtype,
    iblldpRemManAddrIfId         Integer32,
    iblldpRemManAddrOID          OBJECT IDENTIFIER }

iblldpRemManAddrSubtype OBJECT-TYPE
    SYNTAX AddressFamilyNumbers
    MAX-ACCESS read-only
    STATUS current
    DESCRIPTION
        "The type of management address identifier."
    ::= { iblldpRemManAddrEntry 1 }

iblldpRemManAddr OBJECT-TYPE
    SYNTAX OCTET STRING (SIZE(1..255))
    MAX-ACCESS read-only
    STATUS current
    DESCRIPTION
        "The management address associated with the remote system.  The value
        of the management address is a string of 1 to 255 characters.

        If the value of iblldpRemManAddrSubtype is 1, the management address
        must be a IPv4 address in the dotted-decimal format.  If the value of
        iblldpRemManAddrSubtype is 2, the management address must be a IPv6
        address in the most appropriate IPv6 address format."
    ::= { iblldpRemManAddrEntry 2 }

iblldpRemManAddrIfSubtype OBJECT-TYPE
    SYNTAX LldpManAddrIfSubtype
    MAX-ACCESS read-only
    STATUS current
    DESCRIPTION
        "The enumeration value that identifies the interface numbering
         method used for defining the interface number."
    ::= { iblldpRemManAddrEntry 3 }

iblldpRemManAddrIfId OBJECT-TYPE
    SYNTAX Integer32
    MAX-ACCESS read-only
    STATUS current
    DESCRIPTION
        "The integer value used to identify the interface number
         regarding the management address component associated with
         the remote system."
    ::= { iblldpRemManAddrEntry 4 }

iblldpRemManAddrOID OBJECT-TYPE
    SYNTAX OBJECT IDENTIFIER
    MAX-ACCESS read-only
    STATUS current
    DESCRIPTION
        "The OID value used to identify the type of hardware component
         or protocol entity associated with the management address
         advertised by the remote system agent."
    ::= { iblldpRemManAddrEntry 5 }

--
-- ***********************************************************
--
--        L L D P   M I B   N O T I F I C A T I O N S
--
-- ***********************************************************
--

iblldpPortStatusTrap OBJECT IDENTIFIER ::= { iblldpNotifications 0 }

iblldpValidationStatusChange NOTIFICATION-TYPE
    OBJECTS {
        iblldpPortStatusPortNum,
        iblldpPortValidationStatus
    }
    STATUS        current
    DESCRIPTION
        "This notification will be sent when the neighbor validation
         protection status of a port is changed."
    ::= { iblldpPortStatusTrap 1 }

iblldpAgingStatusChange NOTIFICATION-TYPE
    OBJECTS {
        iblldpPortStatusPortNum,
        iblldpPortAgingStatus
    }
    STATUS        current
    DESCRIPTION
        "This notification will be sent when the neighbor aging protection
          status of a port is changed."
    ::= { iblldpPortStatusTrap 2 }

iblldpGlobalEnableStatus NOTIFICATION-TYPE
    OBJECTS { iblldpAdminStatus }
    STATUS        current
    DESCRIPTION
        "This notification will be sent when the global LLDP
        status is changed."
    ::= { iblldpPortStatusTrap 3 }

iblldpLocManAddrChange NOTIFICATION-TYPE
    OBJECTS { iblldpManAddr, iblldpPortName }
    STATUS        current
    DESCRIPTION
        "This notification will be sent when the local LLDP
        management address of a port is changed."
    ::= { iblldpPortStatusTrap 4 }

iblldpTrapObjects                OBJECT IDENTIFIER ::= { iblldp 3 }
iblldpManAddr OBJECT-TYPE
    SYNTAX OCTET STRING (SIZE (1..31))
    MAX-ACCESS accessible-for-notify
    STATUS current
    DESCRIPTION
        "Management address"
    ::= { iblldpTrapObjects 1 }

iblldpPortName OBJECT-TYPE
    SYNTAX OCTET STRING (SIZE (0..255))
    MAX-ACCESS accessible-for-notify
    STATUS current
    DESCRIPTION
        "Interface name"
    ::= { iblldpTrapObjects 2 }

END
