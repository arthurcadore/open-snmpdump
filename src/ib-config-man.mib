-- =================================================================
-- Copyright (C) 2023 Intelbras S.A. All rights reserved.
--
-- Description: Configuration management mib
-- Reference:
-- Version: V3.1
-- History:
--     Initial version 2002-12-20
--     V1.1 24th Feb 2004
--     Imported module from IB-OID-MIB,the root MIB.
--     V1.2 14th May 2004
--     Changed MIB object name from ibXXX to ib, etc.
--     V1.3 18th Aug 2004
--     Modified DESCRIPTION of 'ibCfgLogFile' by jinyi.
--     V1.4 16th Sept 2004
--     Modified DESCRIPTION of 'ibCfgLogTerminalType' and 'ibCfgLogTerminalNum' by wangyingxia
--     V1.5 9th Oct 2004
--     Modified DESCRIPTION of 'ibCfgRunModifiedLast' and 'ibCfgManEventlog' by wangrui
--     V1.6 30th Nov 2004
--     Modified DESCRIPTION of 'ibCfgOperateCompletion' by wangrui
--     V1.7 11th Jan 2005
--     Modified DESCRIPTION by gaolong and weixinzhe
--     V1.8 26th Apr 2005
--     Added ibCfgExecuteOperate and added ConfigOperationStateType by wangrui
--     Modified DESCRIPTION of 'ibCfgLogSrcData', 'ibCfgLogDesData' and 'ibCfgLogTerminalType' by fuzhenyu
--     V1.9 6th Jun 2005
--     Added enum value in SYNTAX of ibCfgOperateProtocol by jinyongfeng.
--     V2.0 27th sept 2005
--     Modified DESCRIPTION of 'ibCfgLogSrcCmd', 'ibCfgRunModifiedLast' and 'ibCfgLogDesData' by lisongfeng and wangrui
--     V2.1 2009-05-05 Added ibCfgOperateServerPort, ibCfgInvalidConfigFile by jinyi
--     V2.2 2009-12-20 Added ibCfgOperFailReason, ibCfgReset by shuaixiaojuan
--     V2.3 2010-10-30 Deprecated ibCfgOperateServerAddress, ibCfgLogCmdSrcAddress
--                     and ibCfgLogServerAddress,
--                     added enum in ConfigOperationStateType,
--                     added ibCfgOperateSrvAddrType, ibCfgOperateSrvAddrRev and
--                     ibCfgOperateSrvVPNName, ibCfgLogCmdSrcAddrType,
--                     ibCfgLogCmdSrcAddrRev, ibCfgLogCmdSrcAddrVPNName,
--                     ibCfgLogServerAddrType,ibCfgLogServerAddrRev, ibCfgLogServerAddrVPNName by songhao.
--     V2.4 2011-11-26 Added ibCfgFirstTrapTime by duyanbing 04404.
--     V2.5 2013-09-13 Added ibCfgReset2 by duyanbing 04404.
--          2014-01-17 Modified description of ibCfgLogCmdSrcAddress, ibCfgLogServerAddress
--                     and ibCfgOperateServerAddress.
--     V2.6 2014-08-11 Added running2File(7), file2Running(8) to ConfigOperationType,
--                     modified description of ibCfgOperateFileName by SongHao.
--          2014-11-13 Modified description of ConfigOperationType for defining 'startup' by g09715.
--     V2.7 2018-03-06 Added ibCfgOperateFailCmd ibCfgOperateFailCmdView ibCfgOperateFailCmdReason by wangweihui.
--     V2.8 2021-06-23 Modified size of ibCfgLogTerminalUser by Lianghuimin.
--     V2.9 2022-06-15 Added ibConfigManTrapV2, ibConfigManTrapV2Prefix, ibCfgBackupToServerSuccess,
--                     ibCfgBackupToServerFailed, ibCfgRestoreSuccess, ibConfigManTrapInfor,
--                     ibCfgBackupToServerIP, ibCfgBackupToServerTransType, ibCfgBackupToServerFailReason,
--                     ibCfgBackupToServerErrorCode, ibCfgRestoreType by caohao.
--     V3.0 2022-07-08 Added ibCfgSaveFailNotify, ibCfgFileChange, ibCfgSaveFailNotifyErrorNumber,
--                     ibCfgSaveFailNotifyDateTime, ibCfgSaveFailNotifySrcChassis, ibCfgSaveFailNotifySrcSlot,
--                     ibCfgSaveFailNotifySrcCpu, ibCfgFileChangeUI, ibCfgFileChangeAction, ibCfgFileChangeOperater,
--                     and ibCfgFileChangeOperateTime by tkf9872.
--     V3.1 2022-08-12 Added ibCfgFileChangeFileType by tkf9872.
-- =================================================================
IB-CONFIG-MAN-MIB DEFINITIONS ::= BEGIN

IMPORTS
    ibCommon
        FROM IB-OID-MIB
    OBJECT-GROUP, MODULE-COMPLIANCE, NOTIFICATION-GROUP
        FROM SNMPv2-CONF
    TimeTicks, IpAddress, Integer32, Counter32,
    OBJECT-TYPE, MODULE-IDENTITY, NOTIFICATION-TYPE
        FROM SNMPv2-SMI
    InetAddressType, InetAddress
        FROM INET-ADDRESS-MIB
    DisplayString, TruthValue, RowStatus, TEXTUAL-CONVENTION, DateAndTime
        FROM SNMPv2-TC;


ibConfig MODULE-IDENTITY
    LAST-UPDATED "202208120000Z"
    ORGANIZATION
        "Intelbras S.A. Industria de Telecomunicacao Eletronica Brasileria."
    CONTACT-INFO
        ""
    DESCRIPTION
        "This MIB contains objects for managing the system configuration.  It contains the
        model used to represent configuration data that exists elsewhere in the system and
        in peripheral devices.
        There are no constraints on this MIB."
    REVISION "202208120000Z"
    DESCRIPTION
        "Added ibCfgFileChangeFileType."
    REVISION "202207080000Z"
    DESCRIPTION
        "Added ibCfgSaveFailNotify, ibCfgFileChange, ibCfgSaveFailNotifyErrorNumber,
        ibCfgSaveFailNotifyDateTime, ibCfgSaveFailNotifySrcChassis,
        ibCfgSaveFailNotifySrcSlot, ibCfgSaveFailNotifySrcCpu, ibCfgFileChangeUI,
        ibCfgFileChangeAction, ibCfgFileChangeOperater, and ibCfgFileChangeOperateTime."
    REVISION "202206150000Z"
    DESCRIPTION
        "Added ibConfigManTrapV2, ibConfigManTrapV2Profix, ibCfgBackupToServerSuccess,
        ibCfgBackupToServerFailed, ibCfgRestoreSuccess,
        ibConfigManTrapInfor, ibCfgBackupToServerIP, ibCfgBackupToServerTransType,
        ibCfgBackupToServerFailReason, ibCfgBackupToServerErrorCode,
        ibCfgRestoreType."
    REVISION "202106230000Z"
    DESCRIPTION
        "Modified size of ibCfgLogTerminalUser."
    REVISION "201803060000Z"
    DESCRIPTION
        "Added ibCfgOperateFailCmd ibCfgOperateFailCmdView ibCfgOperateFailCmdReason."
    REVISION "201411140700Z"
    DESCRIPTION
        "Modified description of ConfigOperationType for defining 'startup'."
    REVISION "201408110904Z"
    DESCRIPTION
        "Added running2File(7), file2Running(8) to ConfigOperationType,
        modified description of ibCfgOperateFileName."
    REVISION "201401170000Z"
    DESCRIPTION
        "Modified description of ibCfgLogCmdSrcAddress, ibCfgLogServerAddress
        and ibCfgOperateServerAddress."
    REVISION "201309130000Z"
    DESCRIPTION
        "Added ibCfgReset2."
    REVISION "201111260000Z"
    DESCRIPTION
        "Added ibCfgFirstTrapTime."
    REVISION "201010300000Z"
    DESCRIPTION
        "Deprecated ibCfgOperateServerAddress, ibCfgLogCmdSrcAddress
        and ibCfgLogServerAddress, added enum in ConfigOperationStateType,
        added ibCfgOperateSrvAddrType, ibCfgOperateSrvAddrRev and
        ibCfgOperateSrvVPNName, ibCfgLogCmdSrcAddrType,
        ibCfgLogCmdSrcAddrRev, ibCfgLogCmdSrcAddrVPNName,
        ibCfgLogServerAddrType,ibCfgLogServerAddrRev, ibCfgLogServerAddrVPNName."
    REVISION "200912200000Z"
    DESCRIPTION
        "Added ibCfgOperFailReason, ibCfgReset."
    REVISION "200905050000Z"
    DESCRIPTION
        "Added ibCfgOperateServerPort, ibCfgInvalidConfigFile."
    REVISION "200509270000Z"
    DESCRIPTION
        "Modified DESCRIPTION of 'ibCfgLogSrcCmd', 'ibCfgRunModifiedLast' and
        'ibCfgLogDesData'."
    REVISION "200506060000Z"
    DESCRIPTION
        "Added enum value in SYNTAX of ibCfgOperateProtocol."
    REVISION "200504260000Z"
    DESCRIPTION
        "Added ibCfgExecuteOperate and added ConfigOperationStateType.
        Modified DESCRIPTION of 'ibCfgLogSrcData', 'ibCfgLogDesData' and
        'ibCfgLogTerminalType'."
    REVISION "200501110000Z"
    DESCRIPTION
        "Modified DESCRIPTION."
    REVISION "200411300000Z"
    DESCRIPTION
        "Modified DESCRIPTION of 'ibCfgOperateCompletion'."
    REVISION "200410090000Z"
    DESCRIPTION
        "Modified DESCRIPTION of 'ibCfgRunModifiedLast' and 'ibCfgManEventlog'."
    REVISION "200409160000Z"
    DESCRIPTION
        "Modified DESCRIPTION of 'ibCfgLogTerminalType' and 'ibCfgLogTerminalNum'."
    REVISION "200408180000Z"
    DESCRIPTION
        "Modified DESCRIPTION of 'ibCfgLogFile'."
    REVISION "200405140000Z"
    DESCRIPTION
        "Changed MIB object name from ibXXX to ib, etc."
    REVISION "200402240000Z"
    DESCRIPTION
        "Imported module from IB-OID-MIB, the root MIB."
    REVISION "200212200000Z"
    DESCRIPTION
        "Initial version. "
    ::= { ibCommon 4 }


--
-- Textual conventions
--

ConfigOperationType ::= TEXTUAL-CONVENTION
    STATUS current
    DESCRIPTION
        "Specify operation types on configuration.
        Currently, the following types of operations are provided:

        running2Startup(1):
            Update the next-startup configuration file
            with the current configuration running in the system.  This
            operation is equivalent to the 'save' command from command line.
            If  no next-startup configuration file exists, then the default
            startup configuration file is created to save the data and this
            becomes the next-startup configuration file.

        startup2Running(2):
            Update the current configuration running in the system
            with the current startup configuration file.  The
            commands in the file are executed as if they had been entered via
            the command line.  If the current startup configuration file does not
            exist, the operation will fail with error opFileOpenError(13).

        running2Net(3):
            Send the current configuration running in the system to the network
            by using the specified file transfer protocol.

        net2Running(4):
            Update the current configuration running in the system with a remote
            file from the network by using the specified file transfer protocol.
            The commands in the file are executed as if they had been entered via
            the command line.

        net2Startup(5):
            Download a remote file to the local system by using the specified file
            transfer protocol and replace the next-startup configuration file.
            If the next-startup configuration file does not exist,
            the default startup configuration file is created to save the data and
            this becomes the next-startup configuration file.

        startup2Net(6):
            Send the next-startup configuration file  to the network by using
            the specified file transfer protocol.  If the next-startup configuration
            file does not exist, the operation will fail with error opFileOpenError(13).

        running2File(7):
            Write current configuration running in the system into a file that is
            specified by ibCfgOperateFileName.
            After this operation, the next-startup configuration file will not be changed.

        file2Running(8):
            Update the current configuration running in the system with a file that is
            specified by ibCfgOperateFileName.
            The commands in the file are executed as if they had been entered via
            the command line."
    SYNTAX INTEGER
        {
            running2Startup(1),
            startup2Running(2),
            running2Net(3),
            net2Running(4),
            net2Startup(5),
            startup2Net(6),
            running2File(7),
            file2Running(8)
        }

ConfigOperationStateType ::= TEXTUAL-CONVENTION
    STATUS current
    DESCRIPTION
        "The status of the specified operation.

        opInProgress : Specified operation is active.
        opOperationSuccess : Specified operation is supported and
                             completed successfully.
        opInvalidOperation : Command invalid or command/protocol/device
                             combination unsupported.
        opInvalidProtocol : Invalid protocol specified.
        opInvalidSourceName : Invalid source file name specified.
        opInvalidDestName : Invalid target name  specified.
        opInvalidServerAddress : Invalid server address specified.
        opDeviceBusy : Specified device is in use and locked by another process.
        opDeviceOpenError : Invalid device name.
        opDeviceError : Device read, write or erase error.
        opDeviceNotProgrammable : Device is read-only but a write or erase
                                  operation was specified.
        opDeviceFull : Device is filled to capacity.
        opFileOpenError : Invalid file name; file not found in partition.
        opFileTransferError : File transfer was unsuccessful; network failure.
        opFileChecksumError : File checksum in Flash failed.
        opNoMemory : System running low on memory.
        opAuthFail: Invalid user name or password.
        opTimeOut : File transfer was timeout.
        opUnknownFailure : Failure unknown.
        opInvalidConfigFile: Invalid configuration file.
        opSlaveFull : Operation failed for a standby MPU or subordinate device because of insufficient space.
        opCopyToSlaveFailure : Failed to copy the file to a standby MPU or subordinate device.
        "
    SYNTAX INTEGER
        {
            opInProgress(1),
            opSuccess(2),
            opInvalidOperation(3),
            opInvalidProtocol(4),
            opInvalidSourceName(5),
            opInvalidDestName(6),
            opInvalidServerAddress(7),
            opDeviceBusy(8),
            opDeviceOpenError(9),
            opDeviceError(10),
            opDeviceNotProgrammable(11),
            opDeviceFull(12),
            opFileOpenError(13),
            opFileTransferError(14),
            opFileChecksumError(15),
            opNoMemory(16),
            opAuthFail(17),
            opTimeOut(18),
            opUnknownFailure(19),
            opInvalidConfigFile(20),
            opSlaveFull(21),
            opCopyToSlaveFailure(22)
        }

--
-- Node definitions
--

ibConfigManObjects OBJECT IDENTIFIER ::= { ibConfig 1 }


ibCfgLog OBJECT IDENTIFIER ::= { ibConfigManObjects 1 }


ibCfgRunModifiedLast OBJECT-TYPE
    SYNTAX TimeTicks
    MAX-ACCESS read-only
    STATUS current
    DESCRIPTION
        "The object records the value of sysUpTime when the current configuration
         running in the system was last modified.

         The value will be changed immediately after the system detects that the current
         configuration has been changed."
    ::= { ibCfgLog 1 }


ibCfgRunSavedLast OBJECT-TYPE
    SYNTAX TimeTicks
    MAX-ACCESS read-only
    STATUS current
    DESCRIPTION
        "The object records the value of sysUpTime when the current configuration
         running in the system was last saved.

         If the value of the object is smaller than
         ibCfgRunModifiedLast, the current configuration has been
         modified but not saved."
    ::= { ibCfgLog 2 }


ibCfgStartModifiedLast OBJECT-TYPE
    SYNTAX TimeTicks
    MAX-ACCESS read-only
    STATUS current
    DESCRIPTION
        "The object records the value of sysUpTime when the next-startup configuration
         used currently was last modified.  It may have been modified by a save operation of the
         current configuration running in the system or other methods such as copy."
    ::= { ibCfgLog 3 }


ibCfgLogLimitedEntries OBJECT-TYPE
    SYNTAX Integer32 (0..2147483647)
    MAX-ACCESS read-only
    STATUS current
    DESCRIPTION
        "The object shows the maximum number of rows in
        ibCfgLogTable.  The value supported by the system is 10.
        "
    ::= { ibCfgLog 4 }


ibCfgLogDeletedEntries OBJECT-TYPE
    SYNTAX Counter32
    MAX-ACCESS read-only
    STATUS current
    DESCRIPTION
        "The total number of rows deleted from ibCfgLogTable."
    ::= { ibCfgLog 5 }


ibCfgLogWantBackup OBJECT-TYPE
    SYNTAX TruthValue
    MAX-ACCESS read-write
    STATUS current
    DESCRIPTION
        "Decide whether to back up the values of objects for ibCfgLog."
    DEFVAL { true }
    ::= { ibCfgLog 6 }

-- If the value is true, the data of configuration log on the master will send to
-- slave.  Otherwise the data of log will be lost when master switches to
-- slave.


ibCfgLogTable OBJECT-TYPE
    SYNTAX SEQUENCE OF IbCfgLogEntry
    MAX-ACCESS not-accessible
    STATUS current
    DESCRIPTION
        "Table for logging configuration operations on device ."
    ::= { ibCfgLog 7 }

ibCfgLogEntry OBJECT-TYPE
    SYNTAX IbCfgLogEntry
    MAX-ACCESS not-accessible
    STATUS current
    DESCRIPTION
        "Information of the entry."
    INDEX { ibCfgLogIndex }
    ::= { ibCfgLogTable 1 }

IbCfgLogEntry ::=
    SEQUENCE
        {
            ibCfgLogIndex                  Integer32,
            ibCfgLogTime                   TimeTicks,
            ibCfgLogSrcCmd                 INTEGER,
            ibCfgLogSrcData                INTEGER,
            ibCfgLogDesData                INTEGER,
            ibCfgLogTerminalType           INTEGER,
            ibCfgLogTerminalUser           DisplayString,
            ibCfgLogTerminalNum            Integer32,
            ibCfgLogTerminalLocation       DisplayString,
            ibCfgLogCmdSrcAddress          IpAddress,
            ibCfgLogVirHost                DisplayString,
            ibCfgLogUserName               DisplayString,
            ibCfgLogServerAddress          IpAddress,
            ibCfgLogFile                   DisplayString,
            ibCfgLogCmdSrcAddrType         InetAddressType,
            ibCfgLogCmdSrcAddrRev          InetAddress,
            ibCfgLogCmdSrcAddrVPNName      DisplayString,
            ibCfgLogServerAddrType         InetAddressType,
            ibCfgLogServerAddrRev          InetAddress,
            ibCfgLogServerAddrVPNName      DisplayString
        }

ibCfgLogIndex OBJECT-TYPE
    SYNTAX Integer32 (1..2147483647)
    MAX-ACCESS not-accessible
    STATUS current
    DESCRIPTION
        "Index of the table beginning from 1."
    ::= { ibCfgLogEntry 1 }

ibCfgLogTime OBJECT-TYPE
    SYNTAX TimeTicks
    MAX-ACCESS read-only
    STATUS current
    DESCRIPTION
        "Specify the sysUpTime when the configuration log was generated."
    ::= { ibCfgLogEntry 2 }

ibCfgLogSrcCmd OBJECT-TYPE
    SYNTAX INTEGER
        {
            cmdLine(1),
            snmp(2),
            other(3)
        }
    MAX-ACCESS read-only
    STATUS current
    DESCRIPTION
        "Specify the source command which brought the log.
        Currently, we provide the following types of sources:
        1.cmdLine(1):configure log instigated by command line.
        2.snmp(2):configure log instigated by SNMPS.
        3.other(3):configure log instigated by other source unknown."
    ::= { ibCfgLogEntry 3 }

ibCfgLogSrcData OBJECT-TYPE
    SYNTAX INTEGER
        {
            erase(1),
            runningData(2),
            commandSource(3),
            startupData(4),
            local(5),
            netFtp(6),
            hotPlugging(7)
        }
    MAX-ACCESS read-only
    STATUS current
    DESCRIPTION
        "The source of the configuration data event.
        erase           erasing destination
        runningData     operational data alive
        commandSource   the command source itself
        startupData     what the system will use next reboot
        local           local NVRAM or flash
        netFtp          FTP network transfer
        hotPlugging     board is inserted or pulled out on line
        "
    ::= { ibCfgLogEntry 4 }

ibCfgLogDesData OBJECT-TYPE
    SYNTAX INTEGER
        {
            unknown(1),
            runningData(2),
            commandSource(3),
            startupData(4),
            local(5),
            netFtp(6),
            hotPlugging(7)
        }
    MAX-ACCESS read-only
    STATUS current
    DESCRIPTION
        "The destination for the configuration data event.
        unknown          unknown
        runningData     operational data alive
        commandSource   the command source itself
        startupData     what the system will use next reboot
        local           local NVRAM or flash
        netFtp          FTP network transfer
        hotPlugging     board is inserted or pulled out on line"
    ::= { ibCfgLogEntry 5 }

ibCfgLogTerminalType OBJECT-TYPE
    SYNTAX INTEGER
        {
            notApplicable(1),
            unknown(2),
            console(3),
            terminal(4),
            virtual(5),
            auxiliary(6)
        }
    MAX-ACCESS read-only
    STATUS current
    DESCRIPTION
        "Specifies the terminal type.
        If ibCfgLogSrcCmd is not 'cmdLine', use 'notApplicable'.

        The value list:
        notApplicable(1): no meaning at this time.
        unknown(2): unknown terminal type.
        console(3): console interface.
        terminal(4): generic terminal.
        virtual(5): virtual terminal such as Telnet.
        auxiliary(6): auxiliary interface."
    ::= { ibCfgLogEntry 6 }

ibCfgLogTerminalUser OBJECT-TYPE
    SYNTAX DisplayString (SIZE (0..255))
    MAX-ACCESS read-only
    STATUS current
    DESCRIPTION
        "The name of logging user which is available when ibCfgLogSrcCmd
        is 'cmdLine'.
        Other, a zero length string."
    ::= { ibCfgLogEntry 7 }

ibCfgLogTerminalNum OBJECT-TYPE
    SYNTAX Integer32
    MAX-ACCESS read-only
    STATUS current
    DESCRIPTION
        "Specifies the terminal number.
        If ibCfgLogSrcCmd is not 'cmdLine', use '-1'"
    ::= { ibCfgLogEntry 8 }

ibCfgLogTerminalLocation OBJECT-TYPE
    SYNTAX DisplayString (SIZE (0..64))
    MAX-ACCESS read-only
    STATUS current
    DESCRIPTION
        "The location of logging user which is available when ibCfgLogSrcCmd
        is 'cmdLine'.
        Other, a zero length string."
    ::= { ibCfgLogEntry 9 }

ibCfgLogCmdSrcAddress OBJECT-TYPE
    SYNTAX IpAddress
    MAX-ACCESS read-only
    STATUS deprecated
    DESCRIPTION
        "The address from which a request comes when the value of ibCfgLogSrcCmd is 'snmp(2)'.

        The ip address of the remote system connected when the value of ibCfgLogTerminalType
        is 'virtual'.

        Other, the value of 0.0.0.0.

        This object is replaced by ibCfgLogCmdSrcAddrRev for it only support IPv4."
    ::= { ibCfgLogEntry 10 }

ibCfgLogVirHost OBJECT-TYPE
    SYNTAX DisplayString (SIZE (0..64))
    MAX-ACCESS read-only
    STATUS current
    DESCRIPTION
        "The host name of remote system connected if
        ibCfgLogTerminalType has the value of 'virtual'.
        Other, a zero length string."
    ::= { ibCfgLogEntry 11 }

ibCfgLogUserName OBJECT-TYPE
    SYNTAX DisplayString (SIZE (0..64))
    MAX-ACCESS read-only
    STATUS current
    DESCRIPTION
        "The user name used when ibCfgLogSrcData or ibCfgLogDesData has
        the value of 'netFtp'.
        Other, a zero length string."
    ::= { ibCfgLogEntry 12 }

ibCfgLogServerAddress OBJECT-TYPE
    SYNTAX IpAddress
    MAX-ACCESS read-only
    STATUS deprecated
    DESCRIPTION
        "The remote server address when ibCfgLogSrcData or ibCfgLogDesData
        has the value of 'netFtp'.
        Other, a value of 0.0.0.0.

        This object is replaced by ibCfgLogServerAddrRev for it only support IPv4."
    ::= { ibCfgLogEntry 13 }

ibCfgLogFile OBJECT-TYPE
    SYNTAX DisplayString (SIZE (0..64))
    MAX-ACCESS read-only
    STATUS current
    DESCRIPTION
        "The current configuration file name when ibCfgLogSrcData has
         the value of 'netFtp', and ibCfgLogDesData has the value of 'startupData'.
         Other, a zero length string."
    ::= { ibCfgLogEntry 14 }

ibCfgLogCmdSrcAddrType OBJECT-TYPE
    SYNTAX InetAddressType
    MAX-ACCESS read-only
    STATUS current
    DESCRIPTION
        "The type of IP address for the ibCfgLogCmdSrcAddrRev."
    ::= { ibCfgLogEntry 15 }

ibCfgLogCmdSrcAddrRev OBJECT-TYPE
    SYNTAX InetAddress
    MAX-ACCESS read-only
    STATUS current
    DESCRIPTION
        "The address from which a request comes when the value of ibCfgLogSrcCmd is 'snmp(2)'.

        The ip address of the remote system connected when the value of ibCfgLogTerminalType
        is 'virtual'.

        Other, the value of 0.0.0.0."
    ::= { ibCfgLogEntry 16 }

ibCfgLogCmdSrcAddrVPNName OBJECT-TYPE
    SYNTAX DisplayString
    MAX-ACCESS read-only
    STATUS current
    DESCRIPTION
        "The VPN instance of this operation uses."
    ::= { ibCfgLogEntry 17 }

ibCfgLogServerAddrType OBJECT-TYPE
    SYNTAX InetAddressType
    MAX-ACCESS read-only
    STATUS current
    DESCRIPTION
        "The type of IP address for the ibCfgLogServerAddrRev."
    ::= { ibCfgLogEntry 18 }

ibCfgLogServerAddrRev OBJECT-TYPE
    SYNTAX InetAddress
    MAX-ACCESS read-only
    STATUS current
    DESCRIPTION
        "The remote server address when ibCfgLogSrcData or ibCfgLogDesData
        has the value of 'netFtp'.
        Other, a value of 0.0.0.0."
    ::= { ibCfgLogEntry 19 }

ibCfgLogServerAddrVPNName OBJECT-TYPE
    SYNTAX DisplayString
    MAX-ACCESS read-only
    STATUS current
    DESCRIPTION
        "The VPN instance of this operation uses."
    ::= { ibCfgLogEntry 20 }

ibCfgFirstTrapTime OBJECT-TYPE
    SYNTAX      TimeTicks
    MAX-ACCESS  accessible-for-notify
    STATUS      current
    DESCRIPTION
        "Time when the first trap is sent."
    ::= { ibCfgLog 8 }

ibCfgOperate OBJECT IDENTIFIER ::= { ibConfigManObjects 2 }


ibCfgOperateGlobalEntryLimit OBJECT-TYPE
    SYNTAX Integer32 (1..10)
    MAX-ACCESS read-only
    STATUS current
    DESCRIPTION
        "The maximum number of copy entries that may be held
        in ibCfgOperateTable.  A particular setting does not guarantee
        that much data can be held."
    DEFVAL { 5 }
    ::= { ibCfgOperate 1 }


ibCfgOperateEntryAgeOutTime OBJECT-TYPE
    SYNTAX Integer32 (1..60)
    UNITS "minute"
    MAX-ACCESS read-write
    STATUS current
    DESCRIPTION
        "The number of minutes an unactive ibCfgOperateEntry SHOULD be kept in the
        ibCfgOperateTable before it is active.  The object is a factor taken account
        of when it needs delete some rows make room in ibCfgOperateTable. "
    DEFVAL { 5 }
    ::= { ibCfgOperate 2 }

ibCfgOperateResultGlobalEntryLimit OBJECT-TYPE
    SYNTAX Integer32(1..50)
    MAX-ACCESS read-write
    STATUS current
    DESCRIPTION
        "The maximum number of copy entries that may be held
        in ibCfgOperateResultTable.  A particular setting does not guarantee
        that much data can be held."
    DEFVAL { 5 }
    ::= { ibCfgOperate 3 }


ibCfgOperateTable OBJECT-TYPE
    SYNTAX SEQUENCE OF IbCfgOperateEntry
    MAX-ACCESS not-accessible
    STATUS current
    DESCRIPTION
        "A table of config-operation requests."
    ::= { ibCfgOperate 4 }


ibCfgOperateEntry OBJECT-TYPE
    SYNTAX IbCfgOperateEntry
    MAX-ACCESS not-accessible
    STATUS current
    DESCRIPTION
        "An operate request entry."
    INDEX { ibCfgOperateIndex }
    ::= { ibCfgOperateTable 1 }


IbCfgOperateEntry ::=
    SEQUENCE
        {
            ibCfgOperateIndex                      Integer32,
            ibCfgOperateType                       ConfigOperationType,
            ibCfgOperateProtocol                   INTEGER,
            ibCfgOperateFileName                   DisplayString,
            ibCfgOperateServerAddress              IpAddress,
            ibCfgOperateUserName                   DisplayString,
            ibCfgOperateUserPassword               DisplayString,
            ibCfgOperateEndNotificationSwitch      TruthValue,
            ibCfgOperateRowStatus                  RowStatus,
            ibCfgOperateServerPort                 Integer32,
            ibCfgOperateSrvAddrType                InetAddressType,
            ibCfgOperateSrvAddrRev                 InetAddress,
            ibCfgOperateSrvVPNName                 DisplayString
        }

ibCfgOperateIndex OBJECT-TYPE
    SYNTAX Integer32 (1..2147483647)
    MAX-ACCESS not-accessible
    STATUS current
    DESCRIPTION
        "The unique index value of a row in this table."
    ::= { ibCfgOperateEntry 1 }

ibCfgOperateType OBJECT-TYPE
    SYNTAX ConfigOperationType
    MAX-ACCESS read-create
    STATUS current
    DESCRIPTION
        "Specify the type of operation on configuration."
    ::= { ibCfgOperateEntry 2 }

ibCfgOperateProtocol OBJECT-TYPE
    SYNTAX INTEGER
        {
            ftp(1),
            tftp(2),
            clusterftp(3),
            clustertftp(4)
        }
    MAX-ACCESS read-create
    STATUS current
    DESCRIPTION
        "If the value of ibCfgOperateType is running2Net,net2Running,net2Startup
         or startup2net,  this node specify the protocol to be
        used for file transfer .
        The default protocol is ftp if no protocol is specified.
        And for other value of ibCfgOperateType , this object may
        be ignored by the implementation.

        when clusterftp or clustertftp is selected,
        the ibCfgOperateServerAddress needn't be set,
        the server address can be acquired automatically, the value of ibCfgOperateServerAddress
        is uncertain during operation.
        both member switch and commander switch can use them if they support HGMP v2.
        "
    ::= { ibCfgOperateEntry 3 }

ibCfgOperateFileName OBJECT-TYPE
    SYNTAX DisplayString (SIZE (1..128))
    MAX-ACCESS read-create
    STATUS current
    DESCRIPTION
        "When the object of ibCfgOperateType has the value of net2Startup, net2running,
        running2Net, running2File or file2Running, the value must be specified.

        The file name may include the path if applicable.

        If the value of ibCfgOperateType is net2Startup or net2running, this node specify the
        source file name of transfers.

        If the value of ibCfgOperateType is running2Net,
        this node specify the destination file name of transfers.

        When ibCfgOperateType has the value of startup2net, the object may not be
        created instead of using the file name of startup configuration file.

        If the value of ibCfgOperateType is running2File or file2Running,
        this node specifies the file name to be written or loaded."
    ::= { ibCfgOperateEntry 4 }

ibCfgOperateServerAddress OBJECT-TYPE
    SYNTAX IpAddress
    MAX-ACCESS read-create
    STATUS deprecated
    DESCRIPTION
        "When the operation type is running2Net,net2Running,net2Startup
         or startup2net , the ip address of the ftp/tftp server from/to
        which to download/upload must be specified.
        Values of 0.0.0.0 or FF.FF.FF.FF are not permitted.

        This object is replaced by ibCfgOperateSrvAddrRev for it only support IPv4."
    ::= { ibCfgOperateEntry 5 }

ibCfgOperateUserName OBJECT-TYPE
    SYNTAX DisplayString (SIZE (0..40))
    MAX-ACCESS read-create
    STATUS current
    DESCRIPTION
        "When the operation type is running2Net,net2Running,net2Startup
         or startup2net, the user
        name for the ftp server from/to which to download/upload
        should be specified.  The object must be created if ibCfgOperateProtocol
        has the value of ftp."
    ::= { ibCfgOperateEntry 6 }

ibCfgOperateUserPassword OBJECT-TYPE
    SYNTAX DisplayString (SIZE (0..40))
    MAX-ACCESS read-create
    STATUS current
    DESCRIPTION
        "When the operation type is running2Net,net2Running,net2Startup
         or startup2net, the user
        password for the ftp server from/to which to download/upload
        should be specified.  The object must be created if ibCfgOperateProtocol
        has the value of ftp."
    ::= { ibCfgOperateEntry 7 }

ibCfgOperateEndNotificationSwitch OBJECT-TYPE
    SYNTAX TruthValue
    MAX-ACCESS read-create
    STATUS current
    DESCRIPTION
        "Specifies whether or not a notification should be
        issued on the completion of the operation."
    DEFVAL { false }
    ::= { ibCfgOperateEntry 8 }

ibCfgOperateRowStatus OBJECT-TYPE
    SYNTAX RowStatus
    MAX-ACCESS read-create
    STATUS current
    DESCRIPTION
        "The status of this table entry.
        When the status is active all the
        object's value in the entry is not
        allowed to be modified."
    ::= { ibCfgOperateEntry 9 }

ibCfgOperateServerPort OBJECT-TYPE
    SYNTAX Integer32 (0..65535)
    MAX-ACCESS read-create
    STATUS current
    DESCRIPTION
        "When the operation type is running2Net, net2Running, net2Startup or startup2Net,
         this node is used for specifying the remote port number.  If the value is 0 or not
         specified, the known port number will be used."
    ::= { ibCfgOperateEntry 10 }

ibCfgOperateSrvAddrType OBJECT-TYPE
    SYNTAX InetAddressType
    MAX-ACCESS read-create
    STATUS current
    DESCRIPTION
        "The type of IP address for ibCfgOperateSrvAddrRev."
    ::= { ibCfgOperateEntry 11 }

ibCfgOperateSrvAddrRev OBJECT-TYPE
    SYNTAX InetAddress
    MAX-ACCESS read-create
    STATUS current
    DESCRIPTION
        "When the operation type is running2Net,net2Running,net2Startup
        or startup2net , the ip address of the ftp/tftp server from/to
        which to download/upload must be specified."
    ::= { ibCfgOperateEntry 12 }

ibCfgOperateSrvVPNName OBJECT-TYPE
    SYNTAX DisplayString
    MAX-ACCESS read-create
    STATUS current
    DESCRIPTION
        "The VPN instance of this operation uses."
    ::= { ibCfgOperateEntry 13 }

ibCfgOperateResultTable OBJECT-TYPE
    SYNTAX SEQUENCE OF IbCfgOperateResultEntry
    MAX-ACCESS not-accessible
    STATUS current
    DESCRIPTION
        "A table of config-operation requests result."
    ::= { ibCfgOperate 5 }

ibCfgOperateResultEntry OBJECT-TYPE
    SYNTAX IbCfgOperateResultEntry
    MAX-ACCESS not-accessible
    STATUS current
    DESCRIPTION
        "The result entries of configuration operation requests."
    INDEX { ibCfgOperateResultIndex }
    ::= { ibCfgOperateResultTable 1 }


IbCfgOperateResultEntry ::=
    SEQUENCE
        {
            ibCfgOperateResultIndex            Integer32,
            ibCfgOperateResultOptIndex         Integer32,
            ibCfgOperateResultOpType           ConfigOperationType,
            ibCfgOperateState                  ConfigOperationStateType,
            ibCfgOperateTime                   TimeTicks,
            ibCfgOperateEndTime                TimeTicks,
            ibCfgOperFailReason                DisplayString,
            ibCfgOperateFailCmd                DisplayString,
            ibCfgOperateFailCmdView            DisplayString,
            ibCfgOperateFailCmdReason          DisplayString
        }

ibCfgOperateResultIndex OBJECT-TYPE
    SYNTAX Integer32 (1..2147483647)
    MAX-ACCESS not-accessible
    STATUS current
    DESCRIPTION
        "The index of Table, which is an incremental integer.
        The maximum value of the node is 2147483647.  The agent should wrap the
        value to 1 and flush all the existing entries when the maximum value
        is reached."
    ::= { ibCfgOperateResultEntry 1 }


ibCfgOperateResultOptIndex OBJECT-TYPE
    SYNTAX Integer32 (1..2147483647)
    MAX-ACCESS read-only
    STATUS current
    DESCRIPTION
        "The operation index in the ibCfgOperateTable."
    ::= { ibCfgOperateResultEntry 2 }

ibCfgOperateResultOpType OBJECT-TYPE
    SYNTAX ConfigOperationType
    MAX-ACCESS read-only
    STATUS current
    DESCRIPTION
        "The operation type in the ibCfgOperateTable."
    ::= { ibCfgOperateResultEntry 3 }

ibCfgOperateState OBJECT-TYPE
    SYNTAX ConfigOperationStateType
    MAX-ACCESS read-only
    STATUS current
    DESCRIPTION
        "The operation state type in the ibCfgOperateTable."
    ::= { ibCfgOperateResultEntry 4 }

ibCfgOperateTime OBJECT-TYPE
    SYNTAX TimeTicks
    MAX-ACCESS read-only
    STATUS current
    DESCRIPTION
        "Record the time taken for the operation.  This object will
        be like a stopwatch, starting when the operation
        starts, and stopping when the operation completes."
    ::= { ibCfgOperateResultEntry 5 }

ibCfgOperateEndTime OBJECT-TYPE
    SYNTAX TimeTicks
    MAX-ACCESS read-only
    STATUS current
    DESCRIPTION
        "The value of sysUpTime when the configuration operation is finished."
    ::= { ibCfgOperateResultEntry 6 }

ibCfgOperFailReason OBJECT-TYPE
    SYNTAX DisplayString
    MAX-ACCESS read-only
    STATUS current
    DESCRIPTION
        "The failure reasons of configuration operation."
    ::= { ibCfgOperateResultEntry 7 }

ibCfgOperateFailCmd OBJECT-TYPE
    SYNTAX DisplayString (SIZE (0..512))
    MAX-ACCESS read-only
    STATUS current
    DESCRIPTION
        "The failure cmd of configuration operation."
    ::= { ibCfgOperateResultEntry 8 }

ibCfgOperateFailCmdView OBJECT-TYPE
    SYNTAX DisplayString (SIZE (0..264))
    MAX-ACCESS read-only
    STATUS current
    DESCRIPTION
        "The failure cmd view of configuration operation."
    ::= { ibCfgOperateResultEntry 9 }

ibCfgOperateFailCmdReason OBJECT-TYPE
    SYNTAX DisplayString (SIZE (0..255))
    MAX-ACCESS read-only
    STATUS current
    DESCRIPTION
        "The failure cmd reasons of configuration operation.
        The failed reason is :
        'Failed to execute command.'
        'Failed to parse command.'
        "
    ::= { ibCfgOperateResultEntry 10 }

ibCfgExecuteOperate OBJECT IDENTIFIER ::= { ibCfgOperate 6 }

ibCfgExecuteOperateResultEntryLimit OBJECT-TYPE
    SYNTAX Integer32(5..20)
    MAX-ACCESS read-write
    STATUS current
    DESCRIPTION
        "The maximum number of ConfigOperationType entries that may be held
        in ibCfgExecuteResultTable.  A particular setting does not guarantee
        that much data can be held."
    DEFVAL { 5 }
    ::= { ibCfgExecuteOperate 1 }

ibCfgExecuteResultTable OBJECT-TYPE
    SYNTAX SEQUENCE OF IbCfgExecuteResultEntry
    MAX-ACCESS not-accessible
    STATUS current
    DESCRIPTION
        "A table of configuration execute result."
    ::= { ibCfgExecuteOperate 2 }


ibCfgExecuteResultEntry OBJECT-TYPE
    SYNTAX IbCfgExecuteResultEntry
    MAX-ACCESS not-accessible
    STATUS current
    DESCRIPTION
        "The result entries of configuration execute operation."
    INDEX { ibCfgExecuteResultIndex }
    ::= { ibCfgExecuteResultTable 1 }

IbCfgExecuteResultEntry ::=
    SEQUENCE
        {
            ibCfgExecuteResultIndex            Integer32,
            ibCfgExecuteResultOptIndex         Integer32,
            ibCfgExecuteResultOpType           ConfigOperationType,
            ibCfgExecuteState                  ConfigOperationStateType,
            ibCfgExecuteTime                   TimeTicks,
            ibCfgExecuteEndTime                TimeTicks
        }

ibCfgExecuteResultIndex OBJECT-TYPE
    SYNTAX Integer32 (1..2147483647)
    MAX-ACCESS not-accessible
    STATUS current
    DESCRIPTION
        "The index of Table, which is an incremental integer.
        The maximum value of the node is 2147483647.  The agent should wrap the
        value to 1 and flush all the existing entries when the maximum value
        is reached."
    ::= { ibCfgExecuteResultEntry 1 }


ibCfgExecuteResultOptIndex OBJECT-TYPE
    SYNTAX Integer32 (1..2147483647)
    MAX-ACCESS read-only
    STATUS current
    DESCRIPTION
        "The configuration execute operation index in the ibCfgExecuteResultTable."
    ::= { ibCfgExecuteResultEntry 2 }

ibCfgExecuteResultOpType OBJECT-TYPE
    SYNTAX ConfigOperationType
    MAX-ACCESS read-only
    STATUS current
    DESCRIPTION
        "The operation type in the ibCfgExecuteResultTable."
    ::= { ibCfgExecuteResultEntry 3 }


ibCfgExecuteState OBJECT-TYPE
    SYNTAX ConfigOperationStateType
    MAX-ACCESS read-only
    STATUS current
    DESCRIPTION
        "Record the status of the specified operation."
    ::= { ibCfgExecuteResultEntry 4 }


ibCfgExecuteTime OBJECT-TYPE
    SYNTAX TimeTicks
    MAX-ACCESS read-only
    STATUS current
    DESCRIPTION
        "Record the time of the execution starts."
    ::= { ibCfgExecuteResultEntry 5 }

ibCfgExecuteEndTime OBJECT-TYPE
    SYNTAX TimeTicks
    MAX-ACCESS read-only
    STATUS current
    DESCRIPTION
        "Record the time of the execution is finished."
    ::= { ibCfgExecuteResultEntry 6 }

ibCfgReset OBJECT-TYPE
    SYNTAX INTEGER
        {
            normal(1),
            reset(2)
        }
    MAX-ACCESS read-write
    STATUS current
    DESCRIPTION
        "Reboot the device with the default configuration."
    ::= { ibCfgOperate 7 }

ibCfgReset2 OBJECT-TYPE
    SYNTAX INTEGER
        {
            normal(0),
            reset(1)
        }
    MAX-ACCESS read-write
    STATUS current
    DESCRIPTION
        "normal:do nothing.
        reset  :reboot the device with the default configuration.
        'normal' will be returned when getting.
        This node differs from ibCfgReset in value."
    ::= { ibCfgOperate 8 }

ibConfigManNotifications OBJECT IDENTIFIER ::= { ibConfig 2 }


ibCfgManEventlog NOTIFICATION-TYPE
    OBJECTS { ibCfgLogSrcCmd, ibCfgLogSrcData, ibCfgLogDesData }
    STATUS current
    DESCRIPTION
        "The object calculates the checksum on the current config per 10 minutes and
        even if it is different from the saved config but if a trap has been sent
        with the same checksum then don't send again until the checksum is different."
    ::= { ibConfigManNotifications 1 }


ibCfgOperateCompletion NOTIFICATION-TYPE
    OBJECTS { ibCfgOperateType, ibCfgOperateTime, ibCfgOperateState, ibCfgOperateEndTime, ibCfgOperFailReason }
    STATUS current
    DESCRIPTION
        "When create ibCfgOperateTable successfully, a
        notification may be generated."
    ::= { ibConfigManNotifications 2 }

ibCfgInvalidConfigFile NOTIFICATION-TYPE
    OBJECTS
        {
            ibCfgOperateType,
            ibCfgOperateFileName,
            ibCfgFirstTrapTime
        }
    STATUS current
    DESCRIPTION
        "When the configuration file is invalid, this
         notification will be generated."
    ::= { ibConfigManNotifications 3 }

ibConfigManConformance OBJECT IDENTIFIER ::= { ibConfig 3 }


ibConfigManCompliances OBJECT IDENTIFIER ::= { ibConfigManConformance 1 }


ibConfigManCompliance MODULE-COMPLIANCE
    STATUS current
    DESCRIPTION
        "The statement of compliance for those implementing
        the configuration management MIB."
    MODULE -- this module
    MANDATORY-GROUPS { ibCfgManLogGroup, ibCfgOperateGroup, ibCfgManNotificationGroup }
    OBJECT ibCfgOperateType
    SYNTAX ConfigOperationType
    WRITE-SYNTAX INTEGER
        {
            running2Startup(1),
            startup2Running(2),
            running2Net(3),
            net2Running(4),
            net2Startup(5),
            startup2Net(6)
        }
    DESCRIPTION
        " "
    ::= { ibConfigManCompliances 1 }


ibConfigManGroups OBJECT IDENTIFIER ::= { ibConfigManConformance 2 }


ibCfgManLogGroup OBJECT-GROUP
    OBJECTS
        { ibCfgRunModifiedLast, ibCfgRunSavedLast, ibCfgStartModifiedLast, ibCfgLogLimitedEntries, ibCfgLogDeletedEntries,
        ibCfgLogTime, ibCfgLogSrcCmd, ibCfgLogTerminalType, ibCfgLogTerminalNum, ibCfgLogTerminalUser,
        ibCfgLogTerminalLocation, ibCfgLogCmdSrcAddress, ibCfgLogVirHost, ibCfgLogServerAddress, ibCfgLogFile,
        ibCfgLogUserName, ibCfgLogWantBackup, ibCfgLogSrcData, ibCfgLogDesData }
    STATUS current
    DESCRIPTION
        "A collection of objects configuration log group."
    ::= { ibConfigManGroups 1 }


ibCfgOperateGroup OBJECT-GROUP
    OBJECTS
        { ibCfgOperateGlobalEntryLimit, ibCfgOperateEntryAgeOutTime, ibCfgOperateType, ibCfgOperateProtocol, ibCfgOperateFileName,
        ibCfgOperateServerAddress, ibCfgOperateUserName, ibCfgOperateUserPassword, ibCfgOperateTime,  ibCfgOperateEndNotificationSwitch,
        ibCfgOperateResultGlobalEntryLimit, ibCfgOperateState, ibCfgOperateRowStatus, ibCfgOperateResultOptIndex,
        ibCfgOperateResultOpType, ibCfgOperateEndTime, ibCfgOperFailReason, ibCfgOperateServerPort }
    STATUS current
    DESCRIPTION
        "A group of configuration operation."
    ::= { ibConfigManGroups 2 }


ibCfgManNotificationGroup NOTIFICATION-GROUP
    NOTIFICATIONS { ibCfgManEventlog, ibCfgOperateCompletion, ibCfgInvalidConfigFile }
    STATUS current
    DESCRIPTION
        "Collection of notification objects."
    ::= { ibConfigManGroups 3 }

ibConfigManTrapV2 OBJECT IDENTIFIER ::= { ibConfig 4 }
ibConfigManTrapV2Prefix OBJECT IDENTIFIER ::= { ibConfigManTrapV2 0 }

ibCfgBackupToServerSuccess NOTIFICATION-TYPE
      OBJECTS
        {
            ibCfgBackupToServerIPType,
            ibCfgBackupToServerIP,
            ibCfgBackupToServerVPNName,
            ibCfgBackupToServerTransType
        }
      STATUS current
      DESCRIPTION
        "This notification is generated when configuration backup succeeds."
      ::= { ibConfigManTrapV2Prefix 1 }

ibCfgBackupToServerFailed NOTIFICATION-TYPE
      OBJECTS
        {
            ibCfgBackupToServerIPType,
            ibCfgBackupToServerIP,
            ibCfgBackupToServerVPNName,
            ibCfgBackupToServerTransType,
            ibCfgBackupToServerFailReason,
            ibCfgBackupToServerErrorCode
        }
      STATUS current
      DESCRIPTION
        "This notification is generated when configuration backup fails."
      ::= { ibConfigManTrapV2Prefix 2 }

ibCfgRestoreSuccess NOTIFICATION-TYPE
      OBJECTS { ibCfgRestoreType }
      STATUS current
      DESCRIPTION
        "This notification is generated when configuration restoration succeeds."
      ::= { ibConfigManTrapV2Prefix 3 }

ibCfgSaveFailNotify NOTIFICATION-TYPE
    OBJECTS
        {
            ibCfgSaveFailNotifyErrorNumber,
            ibCfgSaveFailNotifyDateTime,
            ibCfgSaveFailNotifySrcChassis,
            ibCfgSaveFailNotifySrcSlot,
            ibCfgSaveFailNotifySrcCpu
        }
    STATUS current
    DESCRIPTION
        "This notification is generated when a configuration save operation fails."
    ::= { ibConfigManTrapV2Prefix 4 }

ibCfgFileChange NOTIFICATION-TYPE
    OBJECTS
        {
            ibCfgFileChangeUI,
            ibCfgFileChangeAction,
            ibCfgFileChangeOperater,
            ibCfgFileChangeOperateTime,
            ibCfgFileChangeFileType
        }
    STATUS current
    DESCRIPTION
        "This notification is generated when a startup configuration file is modified."
    ::= { ibConfigManTrapV2Prefix 5 }

ibConfigManTrapInfor OBJECT IDENTIFIER ::= { ibConfig 5 }

ibCfgBackupToServerIPType OBJECT-TYPE
    SYNTAX InetAddressType
    MAX-ACCESS accessible-for-notify
    STATUS current
    DESCRIPTION
        "IP address type of the configuration backup server"
    ::= { ibConfigManTrapInfor 1}

ibCfgBackupToServerIP OBJECT-TYPE
    SYNTAX InetAddress
    MAX-ACCESS accessible-for-notify
    STATUS current
    DESCRIPTION
        "IP address of the configuration backup server"
    ::= { ibConfigManTrapInfor 2}

ibCfgBackupToServerVPNName OBJECT-TYPE
    SYNTAX DisplayString (SIZE (0..255))
    MAX-ACCESS accessible-for-notify
    STATUS current
    DESCRIPTION
        "VPN instance to which the configuration backup server belongs"
    ::= { ibConfigManTrapInfor 3}

ibCfgBackupToServerTransType OBJECT-TYPE
    SYNTAX INTEGER
        {
            ftp(1),
            tftp(2),
            scp(3)
        }
    MAX-ACCESS accessible-for-notify
    STATUS current
    DESCRIPTION
        "Protocol used for transferring the file to the backup server"
    ::= { ibConfigManTrapInfor 4}

ibCfgBackupToServerFailReason OBJECT-TYPE
    SYNTAX DisplayString (SIZE (0..255))
    MAX-ACCESS accessible-for-notify
    STATUS current
    DESCRIPTION
        "Configuration backup failure reason"
    ::= { ibConfigManTrapInfor 5}

ibCfgBackupToServerErrorCode  OBJECT-TYPE
    SYNTAX Integer32
    MAX-ACCESS accessible-for-notify
    STATUS current
    DESCRIPTION
        "Configuration backup failure error code.
            Authentication failed(1),
            Failed to save text file(2),
            Transfer failed(3),
            Failed to update file list(4)"
    ::= { ibConfigManTrapInfor 6}

ibCfgRestoreType OBJECT-TYPE
    SYNTAX INTEGER
        {
            binary(1),
            text(2)
        }
    MAX-ACCESS accessible-for-notify
    STATUS current
    DESCRIPTION
        "Type of the configuration file used for configuration restoration"
    ::= { ibConfigManTrapInfor 7}

ibCfgSaveFailNotifyErrorNumber  OBJECT-TYPE
    SYNTAX Integer32
    MAX-ACCESS accessible-for-notify
    STATUS current
    DESCRIPTION
        "Error code for a configuration save failure."
    ::= { ibConfigManTrapInfor 8}

ibCfgSaveFailNotifyDateTime OBJECT-TYPE
    SYNTAX DateAndTime (SIZE(8))
    MAX-ACCESS  accessible-for-notify
    STATUS      current
    DESCRIPTION
        "Time when the configuration save failure occurred."
    ::= { ibConfigManTrapInfor 9}

ibCfgSaveFailNotifySrcChassis  OBJECT-TYPE
    SYNTAX Integer32
    MAX-ACCESS accessible-for-notify
    STATUS current
    DESCRIPTION
        "Number of the chassis where the configuration save failure occurred."
    ::= { ibConfigManTrapInfor 10}

ibCfgSaveFailNotifySrcSlot  OBJECT-TYPE
    SYNTAX Integer32
    MAX-ACCESS accessible-for-notify
    STATUS current
    DESCRIPTION
        "Number of the slot where the configuration save failure occurred."
    ::= { ibConfigManTrapInfor 11}

ibCfgSaveFailNotifySrcCpu  OBJECT-TYPE
    SYNTAX Integer32
    MAX-ACCESS accessible-for-notify
    STATUS current
    DESCRIPTION
        "Number of the CPU where the configuration save failure occurred."
    ::= { ibConfigManTrapInfor 12}

ibCfgFileChangeUI  OBJECT-TYPE
    SYNTAX Integer32
    MAX-ACCESS accessible-for-notify
    STATUS current
    DESCRIPTION
        "Source that triggered configuration changes."
    ::= { ibConfigManTrapInfor 13}

ibCfgFileChangeAction  OBJECT-TYPE
    SYNTAX Integer32
    MAX-ACCESS accessible-for-notify
    STATUS current
    DESCRIPTION
        "Actions that triggered the configuration changes."
    ::= { ibConfigManTrapInfor 14}

ibCfgFileChangeOperater OBJECT-TYPE
    SYNTAX DisplayString (SIZE (0..255))
    MAX-ACCESS accessible-for-notify
    STATUS current
    DESCRIPTION
        "Name of the operator that triggered the configuration changes."
    ::= { ibConfigManTrapInfor 15}

ibCfgFileChangeOperateTime OBJECT-TYPE
    SYNTAX DateAndTime (SIZE(8))
    MAX-ACCESS  accessible-for-notify
    STATUS      current
    DESCRIPTION
        "Time when the configuration changes were triggered."
    ::= { ibConfigManTrapInfor 16}

ibCfgFileChangeFileType OBJECT-TYPE
    SYNTAX INTEGER
        {
            main(1),
            backup(2)
        }
    MAX-ACCESS  accessible-for-notify
    STATUS      current
    DESCRIPTION
        "File type that triggered configuration changes."
    ::= { ibConfigManTrapInfor 17}

END
