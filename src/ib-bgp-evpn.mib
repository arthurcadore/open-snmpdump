-- =============================================================================
-- Copyright (C) 2023 Intelbras S.A. All rights reserved.
--
-- Description: This MIB module contains managed object definitions for
--              Border Gateway Protocol (BGP) Ethernet Virtual Private Network (EVPN).
-- Reference:
-- Version: V1.1
-- History:
--   V1.0 2017-11-20 Initial version Created by AnXiaoFeng
--   V1.1 2018-07-07 Update ibBgpEvpnNbrPrefixTable by shanyangyang
-- =============================================================================
IB-BGP-EVPN-MIB DEFINITIONS ::= BEGIN
IMPORTS
    MODULE-IDENTITY, OBJECT-TYPE,
    Integer32, Unsigned32, IpAddress
        FROM SNMPv2-SMI
    TruthValue
        FROM SNMPv2-TC
    ibCommon
        FROM IB-OID-MIB;

-- =============================================================================
-- module identity part
-- =============================================================================
ibBgpEvpn MODULE-IDENTITY
    LAST-UPDATED "201807071430Z"
    ORGANIZATION
        "Intelbras S.A. Industria de Telecomunicacao Eletronica Brasileria."
    CONTACT-INFO
        ""
    DESCRIPTION
        "This MIB contains managed object definitions for the
         Border Gateway Protocol (BGP) Ethernet Virtual Private
         Network (EVPN) as defined in : ."
    REVISION
        "201807071430Z"
    DESCRIPTION
        "Change the objects of ibBgpEvpnNbrPrefixTable." 
    REVISION
        "201711291431Z"
    DESCRIPTION
        "modified according to review suggestions."
    REVISION
        "201711041431Z"
    DESCRIPTION
        "Initial version of this MIB."
    ::= { ibCommon 172 }

-- =============================================================================
-- object definition begin
-- =============================================================================
ibBgpEvpnObjects OBJECT IDENTIFIER ::= { ibBgpEvpn 1 }
ibBgpEvpnConf    OBJECT IDENTIFIER ::= { ibBgpEvpnObjects 1 }

-- =============================================================================
-- ibBgpEvpnNbrAddrTable Definition
-- =============================================================================
ibBgpEvpnNbrAddrTable OBJECT-TYPE
    SYNTAX      SEQUENCE OF IbBgpEvpnNbrAddrEntry
    MAX-ACCESS  not-accessible
    STATUS      current
    DESCRIPTION
        "This table specifies per-interface BGP EVPN neighbor
         addresses for both PEs and CEs."
    ::= { ibBgpEvpnConf 1 }

ibBgpEvpnNbrAddrEntry OBJECT-TYPE
    SYNTAX      IbBgpEvpnNbrAddrEntry
    MAX-ACCESS  not-accessible
    STATUS      current
    DESCRIPTION
        "An entry in this table is created by an LSR for
         every VRF capable of supporting BGP EVPN.  The
         indexing provides an ordering of BGP prefixes
         per VRF."
    INDEX {
            ibBgpEvpnNbrAddr
          }
    ::= { ibBgpEvpnNbrAddrTable 1 }

IbBgpEvpnNbrAddrEntry ::= SEQUENCE {
    ibBgpEvpnNbrAddr         IpAddress,
    ibBgpEvpnNbrAsNumber     Unsigned32
}

ibBgpEvpnNbrAddr OBJECT-TYPE
    SYNTAX      IpAddress
    MAX-ACCESS  not-accessible
    STATUS      current
    DESCRIPTION
        "Denotes the BGP neighbor address."
    ::= { ibBgpEvpnNbrAddrEntry 1 }

ibBgpEvpnNbrAsNumber OBJECT-TYPE
    SYNTAX      Unsigned32
    MAX-ACCESS  read-only
    STATUS      current
    DESCRIPTION
        "The Autonomous System that the BGP's neighbor in."
    ::= { ibBgpEvpnNbrAddrEntry 2 }

-- =============================================================================
-- End of ibBgpEvpnNbrAddrTable Definition
-- =============================================================================

-- =============================================================================
-- ibBgpEvpnNbrPrefixTable Definition
-- =============================================================================
ibBgpEvpnNbrPrefixTable OBJECT-TYPE
    SYNTAX      SEQUENCE OF IbBgpEvpnNbrPrefixEntry
    MAX-ACCESS  not-accessible
    STATUS      current
    DESCRIPTION
        "This table specifies per-VRF vpnv4 multi-protocol
         prefixes supported by BGP EVPN"
    ::= { ibBgpEvpnConf 2 }

ibBgpEvpnNbrPrefixEntry OBJECT-TYPE
    SYNTAX      IbBgpEvpnNbrPrefixEntry
    MAX-ACCESS  not-accessible
    STATUS      current
    DESCRIPTION
        "An entry in this table is created by an LSR for
         every BGP prefix associated with a VRF supporting a
         BGP EVPN.  The indexing provides an ordering of
         BGP prefixes per VRF."
    INDEX {
            ibBgpEvpnPAtrRD,
            ibBgpEvpnPAtrAddrPrefix,
            ibBgpEvpnPAtrAddrPrefixLen,
            ibBgpEvpnPAtrPeer
          }
    ::= { ibBgpEvpnNbrPrefixTable 1 }

IbBgpEvpnNbrPrefixEntry ::= SEQUENCE {
    ibBgpEvpnPAtrRD              OCTET STRING,
    ibBgpEvpnPAtrAddrPrefix      OCTET STRING,
    ibBgpEvpnPAtrAddrPrefixLen   Integer32,
    ibBgpEvpnPAtrPeer            IpAddress,
    ibBgpEvpnPAtrRouteType       Unsigned32,
    ibBgpEvpnPAtrOrigin          INTEGER,
    ibBgpEvpnPAtrASPathSegment   OCTET STRING,
    ibBgpEvpnPAtrNextHop         IpAddress,
    ibBgpEvpnPAtrMultiExitDisc   Integer32,
    ibBgpEvpnPAtrLocalPref       Integer32,
    ibBgpEvpnPAtrIGMPFlags       INTEGER,
    ibBgpEvpnPAtrMaxRespTime     Unsigned32,
    ibBgpEvpnPAtrPMSITunnel      OCTET STRING,
    ibBgpEvpnPAtrL2VNI           Unsigned32,
    ibBgpEvpnPAtrL3VNI           Unsigned32,
    ibBgpEvpnPAtrBest            TruthValue,
    ibBgpEvpnPAtrUnknown         OCTET STRING
}

ibBgpEvpnPAtrRD OBJECT-TYPE
    SYNTAX      OCTET STRING (SIZE (3..21))
    MAX-ACCESS  not-accessible
    STATUS      current
    DESCRIPTION
        "The route distinguisher."
    ::= { ibBgpEvpnNbrPrefixEntry 1 }

ibBgpEvpnPAtrAddrPrefix OBJECT-TYPE
    SYNTAX      OCTET STRING (SIZE (1..86))
    MAX-ACCESS  not-accessible
    STATUS      current
    DESCRIPTION
        "The EVPN information in the Network Layer
        Reachability Information field. BGP EVPN
        prefix includes:
        [1][ESI][EthernetTagID]:
           ESI: each Ethernet segment(ES) is identified
           by a unique non-zero identifier called an
           Ethernet Segment Identifier.
           EthernetTagID: This attribute identifies a
           particular broadcast domain in an EVPN instance.
        [2][EthernetTagID][MACLength][MAC][IPAddressLength][IPAddress]
        [3][EthernetTagID][IPAddressLength][IPAddress]
        [4][ESI][IPAddressLength][IPAddress]
        [5][EthernetTagID][IPAddressLength][IPAddress]
        [6][EthernetTagID][MulticastSourceLength]
           [MulticastSourceAddress][MulticastGroupLength]
           [MulticastGroupAddress][OriginatorRouterLength]
           [OriginatorRouterAddress]
        [7][ESI][EthernetTagID][MulticastSourceLength]
           [MulticastSourceAddress][MulticastGroupLength]
           [MulticastGroupAddress][OriginatorRouterLength]
           [OriginatorRouterAddress][LeaveGroupSyn]
           LeaveGroupSyn: This attribute identifies the
           specific (x, G) leave group synchronization
           procedure initiated by the advertising PE,
           which increments the value whenever it
           initiates a procedure.
        [8][ESI][EthernetTagID][MulticastSourceLength]
           [MulticastSourceAddress][MulticastGroupLength]
           [MulticastGroupAddress][OriginatorRouterLength]
           [OriginatorRouterAddress][LeaveGroupSyn]"
    ::= { ibBgpEvpnNbrPrefixEntry 2 }

ibBgpEvpnPAtrAddrPrefixLen OBJECT-TYPE
    SYNTAX      Integer32  (0..300)
    MAX-ACCESS  not-accessible
    STATUS      current
    DESCRIPTION
       "Length in bits of the Network
        Layer Reachability Information field."
    ::= { ibBgpEvpnNbrPrefixEntry 3 }

ibBgpEvpnPAtrPeer OBJECT-TYPE
    SYNTAX      IpAddress
    MAX-ACCESS  not-accessible
    STATUS      current
    DESCRIPTION
        "The IP address of the peer where the path
         information was learned."
    ::= { ibBgpEvpnNbrPrefixEntry 4 }

ibBgpEvpnPAtrRouteType OBJECT-TYPE
    SYNTAX      Unsigned32
    MAX-ACCESS  read-only
    STATUS      current
    DESCRIPTION
        "Defines the following Route Types:
         1 - Ethernet Auto-Discovery (A-D) route
         2 - MAC/IP Advertisement route
         3 - Inclusive Multicast Ethernet Tag route
         4 - Ethernet Segment route
         5 - IP Prefix Route
         6 - Selective Multicast Ethernet Tag Route
         7 - IGMP Join Synch Route
         8 - IGMP Leave Synch Route"
    ::= { ibBgpEvpnNbrPrefixEntry 5 }

ibBgpEvpnPAtrOrigin OBJECT-TYPE
    SYNTAX      INTEGER { igp(1),-- networks are interior
                          egp(2),-- networks learned via EGP
                          incomplete(3) -- undetermined
                        }
    MAX-ACCESS  read-only
    STATUS      current
    DESCRIPTION
        "The ultimate origin of the path
         information."
    ::= { ibBgpEvpnNbrPrefixEntry 6 }

ibBgpEvpnPAtrASPathSegment OBJECT-TYPE
    SYNTAX      OCTET STRING (SIZE (2..255))
    MAX-ACCESS  read-only
    STATUS      current
    DESCRIPTION
        "The sequence of AS path segments.  Each AS
         path segment is represented by a triple
         <type, length, value>.

          The type is a 1-octet field which has two
          possible values:
              1      AS_SET: unordered set of ASs a
                     route in the UPDATE
                     message has traversed
              2      AS_SEQUENCE: ordered set of ASs
                     a route in the UPDATE
                     message has traversed.
                     The length is a 1-octet field containing the
                     number of ASs in the value field.

                     The value field contains one or more AS
                     numbers, each AS is represented in the octet
                     string as a pair of octets according to the
                     following algorithm:
                     first-byte-of-pair = ASNumber / 256;
                     second-byte-of-pair = ASNumber & 255;"
    ::= { ibBgpEvpnNbrPrefixEntry 7 }

ibBgpEvpnPAtrNextHop OBJECT-TYPE
    SYNTAX      IpAddress
    MAX-ACCESS  read-only
    STATUS      current
    DESCRIPTION
        "The address of the router that should be
         used for the destination network.  This address is
         the NEXT_HOP address received in the UPDATE packet."
    ::= { ibBgpEvpnNbrPrefixEntry 8 }

ibBgpEvpnPAtrMultiExitDisc OBJECT-TYPE
    SYNTAX      Integer32 (-1..2147483647)
    MAX-ACCESS  read-only
    STATUS      current
    DESCRIPTION
        "The MED attribute received in the UPDATE packet.
         When the actual value is range from 2147483647 to
         4294967295,the return value will be 2147483647."
    ::= { ibBgpEvpnNbrPrefixEntry 9 }

ibBgpEvpnPAtrLocalPref OBJECT-TYPE
    SYNTAX      Integer32 (-1..2147483647)
    MAX-ACCESS  read-only
    STATUS      current
    DESCRIPTION
        "The local preference attribute received in the UPDATE packet.
         When the actual value is range from 2147483647 to 4294967295,
         the return value will be 2147483647."
    ::= { ibBgpEvpnNbrPrefixEntry 10 }

ibBgpEvpnPAtrIGMPFlags OBJECT-TYPE
    SYNTAX      INTEGER { igmpv1(1),
                          igmpv2(2),
                          igmpv3(3)
                        }
    MAX-ACCESS  read-only
    STATUS      current
    DESCRIPTION
        "This attribute indicates support for IGMP version."
    ::= { ibBgpEvpnNbrPrefixEntry 11 }

ibBgpEvpnPAtrMaxRespTime OBJECT-TYPE
    SYNTAX      Unsigned32
    UNITS       "ms"
    MAX-ACCESS  read-only
    STATUS      current
    DESCRIPTION
        "The Maximum Response Time is the duration of (x, G)
         leave group synchronization procedure."
    ::= { ibBgpEvpnNbrPrefixEntry 12 }

ibBgpEvpnPAtrPMSITunnel OBJECT-TYPE
    SYNTAX      OCTET STRING (SIZE (9..21))
    MAX-ACCESS  read-only
    STATUS      current
    DESCRIPTION
        "This attribute identifies the
         P-tunnel used for sending broadcast."
    ::= { ibBgpEvpnNbrPrefixEntry 13 }

ibBgpEvpnPAtrL2VNI OBJECT-TYPE
    SYNTAX      Unsigned32
    MAX-ACCESS  read-only
    STATUS      current
    DESCRIPTION
         "L2 VXLAN ID."
    ::= { ibBgpEvpnNbrPrefixEntry 14 }

ibBgpEvpnPAtrL3VNI OBJECT-TYPE
    SYNTAX      Unsigned32
    MAX-ACCESS  read-only
    STATUS      current
    DESCRIPTION
         "L3 VXLAN ID."
    ::= { ibBgpEvpnNbrPrefixEntry 15 }

ibBgpEvpnPAtrBest OBJECT-TYPE
    SYNTAX      TruthValue
    MAX-ACCESS  read-only
    STATUS      current
    DESCRIPTION
        "An indication of whether this route
         was chosen as the best BGP4 route for
         this destination."
    ::= { ibBgpEvpnNbrPrefixEntry 16 }

ibBgpEvpnPAtrUnknown OBJECT-TYPE
    SYNTAX      OCTET STRING (SIZE(0..255))
    MAX-ACCESS  read-only
    STATUS      current
    DESCRIPTION
        "One or more path attributes not
         understood by this BGP4 speaker."
    ::= { ibBgpEvpnNbrPrefixEntry 17 }

-- =============================================================================
-- End of ibBgpEvpnNbrPrefixTable Definition
-- =============================================================================
-- End of IB-BGP-EVPN-MIB
END
