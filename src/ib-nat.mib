-- ============================================================================
-- Copyright (C) 2023 Intelbras S.A. All rights reserved.
-- Description:  This MIB file is used for configuration of NAT.
--                include :1.NAT pool
--                         2.NAT out bound
--                         3.NAT inside server
--                         4.NAT aging-time
--                         5.NAT blacklist
--                         6.NAT statistics information
--                         7.NAT DNS
-- Reference:
-- Version: V2.0
-- History:
-- V1.0 2004/09/17 created by xiaoshuchao
-- V1.1 2005/06/01 Modified by liguanmin
--      Modify the value range of the node ibNATOutboundPoolIdx
-- V1.2 2007/05/22 Modified by tangjiafeng
--      Modify the value range of the node ibNATSessionPeerPort
-- V1.3 2014/07/11 Modified by hupengfei
--      Add the ibNATTotalNATSessionCount, ibNATEimTableCount,
--      ibNATInboundNoPATTableCount, ibNATOutboundNoPATTableCount,
--      ibNATMaxDynamicPortblock, ibNATMaxStaticPortblock,
--      ibNATActiveDynamicPortblock, ibNATActiveStaticPortblock
-- V1.4 2016/12/25 Modified by wangxiaohua
--      Add the ibNATSessionCreateRate
-- V1.5 2017/04/07 Modified by wangfuchao
--      Add the ibNATAddrGrpStatTable
-- V1.6 2019/10/10 Modified by quanxin
--      Add the ibNATCurBandwidthRatio
--      Add the ibNATBandwidthTraps
-- V1.7 2019/12/01 Modified by z15066
--      Add the ibInstAddrGrpUsgTable
--      Add the ibInstAddrGrpMemberUsgTable
--      Add the ibInstAddrGrpUsageTraps
-- V1.8 2020/12/29 Modified by w21520
--      Add the ibNatIPPoolGroupTable
--      Add the ibNatIPPoolAddrUsageExceedTraps
--      Add the ibNatIPPoolAddrUsageRecoveryTraps
--      Add the ibInstAddrUsgTotalIPCount, ibInstAddrUsgUsedIPCount,
--      ibInstAddrUsgUnusedIPCount, ibInstAddrMemUsgGrpIPMask
-- V1.9 2021/09/17 Modified by j18129
--      Add the ibNatIPPoolIpAllocFailTrap,
--      ibNatIPPoolIpAllocFailRecoveryTrap, ibNatIPPoolIpApplyFailTrap,
--      ibNatPortBlockAllocFailTrap, ibNatPortBlockAllocFailRecoveryTrap,
--      ibNatPortAllocFailTrap, ibNatPortAllocFailRecoveryTrap,
--      ibNatPortUsageTrap, ibNatPortUsageRecoveryTrap
-- V2.0 2022/08/03 Modified by l17656
--      Add the ibNat444PortBlockOverTrap,
--      ibNat444PortBlockBelowTrap, ibNatEIMOverTrap,
--      ibNatEIMBelowTrap, ibNatNoPatOverTrap,
--      ibNatNoPatBelowTrap, ibNatNqaTrap, ibNatNqaExcessiveTrap,
--      ibNatNqaBelowTrap,ibNatPortSplitTrap, ibNatPortRecycleTrap,
--      ibNatTrapChassis, ibNatTrapSlot, ibNatTrapCpu, ibNatAddrNum, ibNat444PortBlockCount,
--      ibNat444PortBlockUseCount, ibNat444PortBlockUsage, ibNatNqaAddr, ibNatConflictVar
-- ============================================================================
IB-NAT-MIB DEFINITIONS ::= BEGIN

                IMPORTS
                        ibCommon
                                FROM IB-OID-MIB
                        ifIndex
                                FROM IF-MIB
                        InetAddress, InetAddressType
                                FROM INET-ADDRESS-MIB
                        TimeTicks, IpAddress, Integer32, Counter32, Counter64, Unsigned32, OBJECT-TYPE,
                        MODULE-IDENTITY, NOTIFICATION-TYPE
                                FROM SNMPv2-SMI
                        RowStatus, DisplayString
                                FROM SNMPv2-TC;


                ibNat MODULE-IDENTITY
                        LAST-UPDATED "202208031105Z"             -- August 3, 2022 at 11:05 GMT
                        ORGANIZATION
                            "Intelbras S.A. Industria de Telecomunicacao Eletronica Brasileria."
                        CONTACT-INFO
                            ""
                        DESCRIPTION
                                "Add the ibNatIPPoolIpAllocFailTrap,
                                 ibNatIPPoolIpAllocFailRecoveryTrap,
                                 ibNatIPPoolIpApplyFailTrap,
                                 ibNatPortBlockAllocFailTrap,
                                 ibNatPortBlockAllocFailRecoveryTrap,
                                 ibNatPortAllocFailTrap,
                                 ibNatPortAllocFailRecoveryTrap,
                                 ibNatPortUsageTrap,
                                 ibNatPortUsageRecoveryTrap"

                        REVISION "202208031105Z"                -- August 3, 2022 at 11:05 GMT
                        DESCRIPTION
                                "Add the ibNat444PortBlockOverTrap,ibNatEIMOverTrap,ibNatEIMBelowTrap,
                                ibNat444PortBlockBelowTrap,ibNatNoPatOverTrap,ibNatNoPatBelowTrap,
                                ibNatIPPoolAddrUsageRecoveryTraps,ibNatNqaTrap, ibNatNqaExcessiveTrap,
                ibNatNqaBelowTrap,ibNatPortSplitTrap, ibNatPortRecycleTrap,
                ibNatTrapChassis, ibNatTrapSlot, ibNatTrapCpu, ibNatAddrNum, ibNat444PortBlockCount,
                ibNat444PortBlockUseCount, ibNat444PortBlockUsage, ibNatNqaAddr, ibNatConflictVar"
            REVISION "202109171711Z"                -- september 17, 2021 at 17:11 GMT
                        DESCRIPTION
                                "Add the ibNatIPPoolGroupTable,
                                ibNatIPPoolAddrUsageExceedTraps,
                                ibNatIPPoolAddrUsageRecoveryTraps"

                        REVISION "202012291440Z"                -- December 29, 2020 at 14:40 GMT
                        DESCRIPTION
                                "This MIB contains objects to manage configuration of NAT.
                                There are no constraints on this MIB."

                        REVISION "201912011446Z"                -- December 1, 2019 at 14:46 GMT
                        DESCRIPTION
                                "Add the ibInstAddrGrpUsgTable,
                                ibInstAddrGrpMemberUsgTable,
                                ibInstAddrGrpUsageTraps."

                        REVISION "201910101752Z"                -- October 10, 2019 at 17:52 GMT
                        DESCRIPTION
                                "Add the ibNATCurBandwidthRatio,
                                 ibNATBandwidthTraps."
                        REVISION "201704071503Z"                -- April 7, 2017 at 15:03 GMT
                        DESCRIPTION
                                "Add the ibNATAddrGrpStatTable."

                        REVISION "201612251105Z"                -- December 25, 2016 at 11:05 GMT
                        DESCRIPTION
                                "Add the ibNATSessionCreateRate."

                        REVISION "201407111115Z"                -- July 11, 2014 at 11:15 GMT
                        DESCRIPTION
                                "Add the ibNATTotalNATSessionCount,
                                 ibNATEimTableCount,
                                 ibNATInboundNoPATTableCount,
                                 ibNATOutboundNoPATTableCount,
                                 ibNATMaxDynamicPortblock,
                                 ibNATMaxStaticPortblock,
                                 ibNATActiveDynamicPortblock,
                                 ibNATActiveStaticPortblock."

                        REVISION "200501201518Z"                -- January 20, 2005 at 15:18 GMT
                        DESCRIPTION
                                "The initial revision of this MIB module."
                        ::= { ibCommon 18 }




--
-- Node definitions
--

-- Global Variants
                ibNATGlobalVars OBJECT IDENTIFIER ::= { ibNat 1 }


--                     **************Global Variants***************
-- NAT Clear Session
                ibNATClearSession OBJECT IDENTIFIER ::= { ibNATGlobalVars 1 }


                ibNATClearSessionSlotNo OBJECT-TYPE
                        SYNTAX Integer32 (1..14 | 255)
                        MAX-ACCESS read-write
                        STATUS current
                        DESCRIPTION
                                "The number of NAT board in which administrator wants to
                                clear data of the session. In router, the value is 255
                                because no NAT board in it. This node only supports 'set' operation.
                                The return value of 'get' operation is meaningless."
                        ::= { ibNATClearSession 1 }


-- NAT blacklist UserConnectLimitPara
                ibNATBLConnectLimitPara OBJECT IDENTIFIER ::= { ibNATGlobalVars 2 }


                ibNATBLConnectHighValue OBJECT-TYPE
                        SYNTAX Integer32 (20..20000)
                        MAX-ACCESS read-write
                        STATUS current
                        DESCRIPTION
                                "The maximal connection amount.  If the connection amount exceeds the
                                value, the IP address will be added into blacklist.  The IP address
                                will not be removed from blacklist until the connection amount is
                                less than the minimal connection amount."
                        DEFVAL { 500 }
                        ::= { ibNATBLConnectLimitPara 1 }


                ibNATBLConnectLowValue OBJECT-TYPE
                        SYNTAX Integer32 (20..20000)
                        MAX-ACCESS read-write
                        STATUS current
                        DESCRIPTION
                                "The minimal connection amount."
                        DEFVAL { 200 }
                        ::= { ibNATBLConnectLimitPara 2 }


                ibNATBLConnectHighRate OBJECT-TYPE
                        SYNTAX Integer32 (20..21474836)
                        MAX-ACCESS read-write
                        STATUS current
                        DESCRIPTION
                                "The maximal connection rate(in second).  If the connection rate exceed the
                                value, the IP address will be added into blacklist.  The IP address
                                will not be removed from blacklist until the connection rate is
                                less than the minimal connection rate."
                        DEFVAL { 250 }
                        ::= { ibNATBLConnectLimitPara 3 }


                ibNATBLConnectLowRate OBJECT-TYPE
                        SYNTAX Integer32 (20..21474836)
                        MAX-ACCESS read-write
                        STATUS current
                        DESCRIPTION
                                "The minimal connection rate(in second)."
                        DEFVAL { 100 }
                        ::= { ibNATBLConnectLimitPara 4 }


                ibNATBLSpecialConnectHighRate OBJECT-TYPE
                        SYNTAX Integer32 (20..21474836)
                        MAX-ACCESS read-write
                        STATUS current
                        DESCRIPTION
                                "The maximal special connection rate(in second).  When administrator
                                wants to control the speed of connection, he can selects the connection
                                speed rate or special connection rate."
                        DEFVAL { 250 }
                        ::= { ibNATBLConnectLimitPara 5 }


                ibNATBLSpecialConnectLowRate OBJECT-TYPE
                        SYNTAX Integer32 (20..21474836)
                        MAX-ACCESS read-write
                        STATUS current
                        DESCRIPTION
                                "The minimal special connection rate(in second)."
                        DEFVAL { 100 }
                        ::= { ibNATBLConnectLimitPara 6 }


-- NAT blacklist property control Enable
                ibNATBLCtrlEnable OBJECT IDENTIFIER ::= { ibNATGlobalVars 3 }


                ibNATBLConnectSumEnable OBJECT-TYPE
                        SYNTAX INTEGER
                                {
                                enable(1),
                                disable(2)
                                }
                        MAX-ACCESS read-write
                        STATUS current
                        DESCRIPTION
                                "Enable or disable the connection amount control."
                        DEFVAL { disable }
                        ::= { ibNATBLCtrlEnable 1 }


                ibNATBLConnectRateEnable OBJECT-TYPE
                        SYNTAX INTEGER
                                {
                                enable(1),
                                disable(2)
                                }
                        MAX-ACCESS read-write
                        STATUS current
                        DESCRIPTION
                                "Enable or disable the connection rate control."
                        DEFVAL { disable }
                        ::= { ibNATBLCtrlEnable 2 }


-- NAT NP aging-time
                ibNATNPTimer OBJECT IDENTIFIER ::= { ibNATGlobalVars 4 }


                ibNATNPAgingTime OBJECT-TYPE
                        SYNTAX INTEGER
                                {
                                fast(1),
                                slow(2)
                                }
                        MAX-ACCESS read-write
                        STATUS current
                        DESCRIPTION
                                "There are two kinds of aging time in NP.  One is fast and the other is
                                slow.  Administrator can select one or other.  The default is fast."
                        DEFVAL { fast }
                        ::= { ibNATNPTimer 1 }


                ibNATMibObjects OBJECT IDENTIFIER ::= { ibNat 2 }


--                      **************MibObjects***************
-- NAT address pool table
                ibNATPoolInfoTable OBJECT-TYPE
                        SYNTAX SEQUENCE OF IbNATPoolInfoEntry
                        MAX-ACCESS not-accessible
                        STATUS current
                        DESCRIPTION
                                "NAT address pool table : The address in the pool is
                                the IP address in the global network. The pool can span
                                255 IP addresses.All address pools configured by administrator
                                are recorded in this table."
                        ::= { ibNATMibObjects 1 }


                ibNATPoolInfoEntry OBJECT-TYPE
                        SYNTAX IbNATPoolInfoEntry
                        MAX-ACCESS not-accessible
                        STATUS current
                        DESCRIPTION
                                "The entry of NAT address pool table."
                        INDEX { ibNATPoolIdx }
                        ::= { ibNATPoolInfoTable 1 }


                IbNATPoolInfoEntry ::=
                        SEQUENCE {
                                ibNATPoolIdx
                                        Integer32,
                                ibNATPoolStartIpAddr
                                        IpAddress,
                                ibNATPoolEndIpAddr
                                        IpAddress,
                                ibNATPoolSlotNo
                                        Integer32,
                                ibNATPoolRefCounter
                                        Integer32,
                                ibNATPoolRowStatus
                                        RowStatus
                         }

                ibNATPoolIdx OBJECT-TYPE
                        SYNTAX Integer32 (1..320)
                        MAX-ACCESS not-accessible
                        STATUS current
                        DESCRIPTION
                                "Index of the address pool: The index uniquely indicates
                                the address pool in the system, and its range is from 1 to 320. "
                        ::= { ibNATPoolInfoEntry 1 }


                ibNATPoolStartIpAddr OBJECT-TYPE
                        SYNTAX IpAddress
                        MAX-ACCESS read-create
                        STATUS current
                        DESCRIPTION
                                "The start IP address of address pool:
                                It must be less than or equal to the end IP address."
                        ::= { ibNATPoolInfoEntry 2 }


                ibNATPoolEndIpAddr OBJECT-TYPE
                        SYNTAX IpAddress
                        MAX-ACCESS read-create
                        STATUS current
                        DESCRIPTION
                                "The end IP address of address pool:
                                It must be more than or equal to the start IP address."
                        ::= { ibNATPoolInfoEntry 3 }


                ibNATPoolSlotNo OBJECT-TYPE
                        SYNTAX Integer32 (1..14 | 255)
                        MAX-ACCESS read-create
                        STATUS current
                        DESCRIPTION
                                "The number of NAT board to which the address pool is bound.
                                The address translation is processed by this NAT board .
                                The relation between address pool and slotNo is n:1.
                                When the address pool is not bound to the NAT board,the value is 255. "
                        ::= { ibNATPoolInfoEntry 4 }


                ibNATPoolRefCounter OBJECT-TYPE
                        SYNTAX Integer32
                        MAX-ACCESS read-create
                        STATUS current
                        DESCRIPTION
                                "The counter of reference.  An address pool can be associated with
                                more than one ACL and the counter of reference is recorded in this
                                field.  When the address pool is not associated with ACL, the value is 0."
                        ::= { ibNATPoolInfoEntry 5 }


                ibNATPoolRowStatus OBJECT-TYPE
                        SYNTAX RowStatus
                        MAX-ACCESS read-create
                        STATUS current
                        DESCRIPTION
                                "Only support 'destroy' and 'createAndGo'.
                                If ibNATPoolIdx, ibNATPoolStartIpAddr and
                                ibNATPoolEndIpAddr were provided correctly,
                                its value is changed 'active'."
                        ::= { ibNATPoolInfoEntry 6 }


--     NAT Out bound Table
                ibNATOutboundTable OBJECT-TYPE
                        SYNTAX SEQUENCE OF IbNATOutboundEntry
                        MAX-ACCESS not-accessible
                        STATUS current
                        DESCRIPTION
                                "NAT out bound table: through associating ACL number,
                                address pool with NAT board, administrator can designate
                                which inside IP address can be translated to global IP
                                address in the pool and the translation is processed by
                                which NAT board."
                        ::= { ibNATMibObjects 2 }


                ibNATOutboundEntry OBJECT-TYPE
                        SYNTAX IbNATOutboundEntry
                        MAX-ACCESS not-accessible
                        STATUS current
                        DESCRIPTION
                                "The entry of NAT out bound table."
                        INDEX { ifIndex, ibNATOutboundAclNo }
                        ::= { ibNATOutboundTable 1 }


                IbNATOutboundEntry ::=
                        SEQUENCE {
                                ibNATOutboundAclNo
                                        Integer32,
                                ibNATOutboundPoolIdx
                                        Integer32,
                                ibNATOutboundIsNoPat
                                        INTEGER,
                                ibNATOutboundSlotNo
                                        Integer32,
                                ibNATOutboundRowStatus
                                        RowStatus
                         }

                ibNATOutboundAclNo OBJECT-TYPE
                        SYNTAX Integer32 (2000..3999)
                        MAX-ACCESS not-accessible
                        STATUS current
                        DESCRIPTION
                                "The number of ACL(Access Control List).  When the packet accords with
                                the rule in the ACL, its source IP address will be translated to IP
                                address in Address pool."
                        ::= { ibNATOutboundEntry 1 }


                ibNATOutboundPoolIdx OBJECT-TYPE
                        SYNTAX Integer32 (0..320 | 2147483647)
                        MAX-ACCESS read-create
                        STATUS current
                        DESCRIPTION
                                "The index of address pool in ibNATPoolInfoTable.
                                when administrator doesn't use the address pool and
                                use the IP address of the interface as the address of
                                global network, the value is 2147483647."
                        ::= { ibNATOutboundEntry 2 }


                ibNATOutboundIsNoPat OBJECT-TYPE
                        SYNTAX INTEGER
                                {
                                true(1),
                                false(2)
                                }
                        MAX-ACCESS read-create
                        STATUS current
                        DESCRIPTION
                                "Whether to use no pat manner.  The translation of no pat
                                is that the translation doesn't use the port information of packet."
                        DEFVAL { false }
                        ::= { ibNATOutboundEntry 3 }


                ibNATOutboundSlotNo OBJECT-TYPE
                        SYNTAX Integer32 (1..14 | 255)
                        MAX-ACCESS read-create
                        STATUS current
                        DESCRIPTION
                                "The number of NAT board.  In router, the value is 255 because no NAT board in it."
                        ::= { ibNATOutboundEntry 4 }


                ibNATOutboundRowStatus OBJECT-TYPE
                        SYNTAX RowStatus
                        MAX-ACCESS read-create
                        STATUS current
                        DESCRIPTION
                                "Only support 'destroy' and 'createAndGo'.
                                If ibNATOutboundAclNo or ibNATOutboundAclNo
                                and ibNATOutboundPoolIdx were provided correctly,
                                its value is changed 'active'."
                        ::= { ibNATOutboundEntry 5 }


--     NAT inside Server Table
                ibNATServerTable OBJECT-TYPE
                        SYNTAX SEQUENCE OF IbNATServerEntry
                        MAX-ACCESS not-accessible
                        STATUS current
                        DESCRIPTION
                                "NAT inside Server Table.  Administrator can configure server in the
                                private network which can provide service for people in the public network.
                                The translation map is :
                                (InsideIP     , InsidePort--> GlobalIP, GlobalPort    )
                                (InsideIP + 1 , InsidePort--> GlobalIP, GlobalPort + 1)
                                (InsideIP + 2 , InsidePort--> GlobalIP, GlobalPort + 2)
                                ...
                                ...
                                ...
                                (InsideIP+n(=InsideIP2),InsidePort--> GlobalIP,GlobalPort+n(=GlobalPort2))
                                "
                        ::= { ibNATMibObjects 3 }


                ibNATServerEntry OBJECT-TYPE
                        SYNTAX IbNATServerEntry
                        MAX-ACCESS not-accessible
                        STATUS current
                        DESCRIPTION
                                "The entry of NAT inside server table."
                        INDEX { ifIndex, ibNATServerProType, ibNATServerGlobalIP, ibNATServerStartGlobalPort, ibNATServerVpnIndex
                                 }
                        ::= { ibNATServerTable 1 }


                IbNATServerEntry ::=
                        SEQUENCE {
                                ibNATServerProType
                                        Integer32,
                                ibNATServerGlobalIP
                                        IpAddress,
                                ibNATServerStartGlobalPort
                                        Integer32,
                                ibNATServerEndGlobalPort
                                        Integer32,
                                ibNATServerStartInsideIP
                                        IpAddress,
                                ibNATServerEndInsideIP
                                        IpAddress,
                                ibNATServerInsidePort
                                        Integer32,
                                ibNATServerSlotNo
                                        Integer32,
                                ibNATServerVpnIndex
                                        Integer32,
                                ibNATServerAclNumber
                                        Integer32,
                                ibNATServerRowStatus
                                        RowStatus
                         }

                ibNATServerProType OBJECT-TYPE
                        SYNTAX Integer32 (1..255)
                        MAX-ACCESS not-accessible
                        STATUS current
                        DESCRIPTION
                                "The type of protocol: icmp(1), tcp(6), udp(17) and others."
                        ::= { ibNATServerEntry 1 }


                ibNATServerGlobalIP OBJECT-TYPE
                        SYNTAX IpAddress
                        MAX-ACCESS not-accessible
                        STATUS current
                        DESCRIPTION
                                "The global IP address of Inside Server."
                        ::= { ibNATServerEntry 2 }


                ibNATServerStartGlobalPort OBJECT-TYPE
                        SYNTAX Integer32 (0..65535)
                        MAX-ACCESS not-accessible
                        STATUS current
                        DESCRIPTION
                                "The start global port of Inside Server.
                                When the port need not be configured, the value is 0."
                        ::= { ibNATServerEntry 3 }


                ibNATServerEndGlobalPort OBJECT-TYPE
                        SYNTAX Integer32 (0..65535)
                        MAX-ACCESS read-create
                        STATUS current
                        DESCRIPTION
                                "The end global port of Inside Server.  When administrator doesn't
                                configure a series of inside server, the value is 0.
                                If the value is not zero, the value of (GlobalPort2-GlobalPort)
                                must be equal to (InsideIP2 - InsideIP)."
                        ::= { ibNATServerEntry 4 }


                ibNATServerStartInsideIP OBJECT-TYPE
                        SYNTAX IpAddress
                        MAX-ACCESS read-create
                        STATUS current
                        DESCRIPTION
                                "The start private IP address of Inside Server."
                        ::= { ibNATServerEntry 5 }


                ibNATServerEndInsideIP OBJECT-TYPE
                        SYNTAX IpAddress
                        MAX-ACCESS read-create
                        STATUS current
                        DESCRIPTION
                                "The end private IP address of Inside Server.  When administrator doesn't
                                configure a series of inside server, the value is 0.0.0.0."
                        ::= { ibNATServerEntry 6 }


                ibNATServerInsidePort OBJECT-TYPE
                        SYNTAX Integer32 (0..65535)
                        MAX-ACCESS read-create
                        STATUS current
                        DESCRIPTION
                                "The private port of Inside Server."
                        ::= { ibNATServerEntry 7 }


                ibNATServerSlotNo OBJECT-TYPE
                        SYNTAX Integer32 (1..14 | 255)
                        MAX-ACCESS read-create
                        STATUS current
                        DESCRIPTION
                                "The number of NAT board.  In router, the value is 255 because no NAT board in it."
                        ::= { ibNATServerEntry 8 }


                ibNATServerVpnIndex OBJECT-TYPE
                        SYNTAX Integer32 (0..65535)
                        MAX-ACCESS not-accessible
                        STATUS current
                        DESCRIPTION
                                "The VPN index of server."
                        ::= { ibNATServerEntry 10 }


                ibNATServerAclNumber OBJECT-TYPE
                        SYNTAX Integer32 (1..10000)
                        MAX-ACCESS read-create
                        STATUS current
                        DESCRIPTION
                                "Number of basic or advanced ACL."
                        ::= { ibNATServerEntry 11 }


                ibNATServerRowStatus OBJECT-TYPE
                        SYNTAX RowStatus
                        MAX-ACCESS read-create
                        STATUS current
                        DESCRIPTION
                                "Only support 'destroy' and 'createAndGo'.
                                If ibNATServerProType, ibNATServerGlobalIP, ibNATServerGlobalPort
                                and ibNATServerInsideIP were provided correctly,
                                its value is changed 'active'."
                        ::= { ibNATServerEntry 12 }


--     NAT Time out Table
                ibNATTimeOutTable OBJECT-TYPE
                        SYNTAX SEQUENCE OF IbNATTimeOutEntry
                        MAX-ACCESS not-accessible
                        STATUS current
                        DESCRIPTION
                                "NAT Time out Table. When a connection is established,
                                if there are not any actives in this connection between
                                the time, it will be disconnected."
                        ::= { ibNATMibObjects 4 }


                ibNATTimeOutEntry OBJECT-TYPE
                        SYNTAX IbNATTimeOutEntry
                        MAX-ACCESS not-accessible
                        STATUS current
                        DESCRIPTION
                                "The entry of NAT Time out Table."
                        INDEX { ibNATTimeOutProtocol }
                        ::= { ibNATTimeOutTable 1 }


                IbNATTimeOutEntry ::=
                        SEQUENCE {
                                ibNATTimeOutProtocol
                                        INTEGER,
                                ibNATTimeOutTimeValue
                                        Integer32
                         }

                ibNATTimeOutProtocol OBJECT-TYPE
                        SYNTAX INTEGER
                                {
                                tcp(1),
                                udp(2),
                                icmp(3),
                                pptp(4),
                                dns(5),
                                tcpFin(6),
                                tcpSyn(7),
                                ftpCtrl(8),
                                ftpData(9)
                                }
                        MAX-ACCESS not-accessible
                        STATUS current
                        DESCRIPTION
                                "The type of protocol."
                        ::= { ibNATTimeOutEntry 1 }


                ibNATTimeOutTimeValue OBJECT-TYPE
                        SYNTAX Integer32 (10..86400)
                        MAX-ACCESS read-write
                        STATUS current
                        DESCRIPTION
                                "The time of time out."
                        ::= { ibNATTimeOutEntry 2 }


--     NAT blacklist Enable(start/stop) Table
                ibNATBLEnableTable OBJECT-TYPE
                        SYNTAX SEQUENCE OF IbNATBLEnableEntry
                        MAX-ACCESS not-accessible
                        STATUS current
                        DESCRIPTION
                                "NAT blacklist function Enable Table.  In this table, administrator can decide
                                whether to start the function of blacklist in the NAT board.
                                When the function of blacklist can't be set for a NAT board,
                                the number of NAT board is 256."
                        ::= { ibNATMibObjects 5 }


                ibNATBLEnableEntry OBJECT-TYPE
                        SYNTAX IbNATBLEnableEntry
                        MAX-ACCESS not-accessible
                        STATUS current
                        DESCRIPTION
                                "The entry of NAT blacklist Enable Table."
                        INDEX { ibNATBLEnableSlotNo }
                        ::= { ibNATBLEnableTable 1 }


                IbNATBLEnableEntry ::=
                        SEQUENCE {
                                ibNATBLEnableSlotNo
                                        Integer32,
                                ibNATBLEnable
                                        INTEGER
                         }

                ibNATBLEnableSlotNo OBJECT-TYPE
                        SYNTAX Integer32 (1..14 | 255)
                        MAX-ACCESS not-accessible
                        STATUS current
                        DESCRIPTION
                                "The number of NAT board.
                                When the function of blacklist can't be set for a NAT board,
                                the value is 255."
                        ::= { ibNATBLEnableEntry 1 }


                ibNATBLEnable OBJECT-TYPE
                        SYNTAX INTEGER
                                {
                                enable(1),
                                disable(2)
                                }
                        MAX-ACCESS read-write
                        STATUS current
                        DESCRIPTION
                                "Start or stop of function of blacklist."
                        DEFVAL { disable }
                        ::= { ibNATBLEnableEntry 2 }


--     NAT special IP ConnectLimitPara Table
                ibNATBLIPConnectLimitParaTable OBJECT-TYPE
                        SYNTAX SEQUENCE OF IbNATBLIPConnectLimitParaEntry
                        MAX-ACCESS not-accessible
                        STATUS current
                        DESCRIPTION
                                "The table of connection control of special IP address.  In this table, administrator can decide to
                                adopt which manner to control the connection which IP address is the
                                special IP address."
                        ::= { ibNATMibObjects 6 }


                ibNATBLIPConnectLimitParaEntry OBJECT-TYPE
                        SYNTAX IbNATBLIPConnectLimitParaEntry
                        MAX-ACCESS not-accessible
                        STATUS current
                        DESCRIPTION
                                "The entry of the table of connection control of special IP address."
                        INDEX { ibNATBLIPConnectLimitParaIP }
                        ::= { ibNATBLIPConnectLimitParaTable 1 }


                IbNATBLIPConnectLimitParaEntry ::=
                        SEQUENCE {
                                ibNATBLIPConnectLimitParaIP
                                        IpAddress,
                                ibNATBLIPConnectHighValue
                                        Integer32,
                                ibNATBLIPConnectLowValue
                                        Integer32,
                                ibNATBLIPUseSpecialConnectRate
                                        INTEGER,
                                ibNATBLIPConnectLimitRowStatus
                                        RowStatus
                         }

                ibNATBLIPConnectLimitParaIP OBJECT-TYPE
                        SYNTAX IpAddress
                        MAX-ACCESS not-accessible
                        STATUS current
                        DESCRIPTION
                                "The special IP address.  The IP is private IP address."
                        ::= { ibNATBLIPConnectLimitParaEntry 1 }


                ibNATBLIPConnectHighValue OBJECT-TYPE
                        SYNTAX Integer32 (20..20000)
                        MAX-ACCESS read-create
                        STATUS current
                        DESCRIPTION
                                "The maximal connection amount.  It must be more than the minimal connection amount."
                        DEFVAL { 500 }
                        ::= { ibNATBLIPConnectLimitParaEntry 2 }


                ibNATBLIPConnectLowValue OBJECT-TYPE
                        SYNTAX Integer32 (20..20000)
                        MAX-ACCESS read-create
                        STATUS current
                        DESCRIPTION
                                "The minimal connection amount.  It must be less than the maximal connection amount."
                        DEFVAL { 200 }
                        ::= { ibNATBLIPConnectLimitParaEntry 3 }


                ibNATBLIPUseSpecialConnectRate OBJECT-TYPE
                        SYNTAX INTEGER
                                {
                                true(1),
                                false(2)
                                }
                        MAX-ACCESS read-create
                        STATUS current
                        DESCRIPTION
                                "Whether to use the special connection rate control."
                        DEFVAL { false }
                        ::= { ibNATBLIPConnectLimitParaEntry 4 }


                ibNATBLIPConnectLimitRowStatus OBJECT-TYPE
                        SYNTAX RowStatus
                        MAX-ACCESS read-create
                        STATUS current
                        DESCRIPTION
                                "Only support 'destroy' and 'createAndGo'.
                                 If ibNATBLIPConnectHighValue, ibNATBLIPConnectLowValue
                                 and ibNATBLIPUseSpecialConnectRate were provided correctly,
                                 its value is changed 'active'."
                        ::= { ibNATBLIPConnectLimitParaEntry 5 }


--     NAT blacklist Manager Table
                ibNATBLManagerTable OBJECT-TYPE
                        SYNTAX SEQUENCE OF IbNATBLManagerEntry
                        MAX-ACCESS not-accessible
                        STATUS current
                        DESCRIPTION
                                "The management table of blacklist.
                                The table doesn't support 'getnext' operation."
                        ::= { ibNATMibObjects 7 }


                ibNATBLManagerEntry OBJECT-TYPE
                        SYNTAX IbNATBLManagerEntry
                        MAX-ACCESS not-accessible
                        STATUS current
                        DESCRIPTION
                                "The entry of management table of blacklist."
                        INDEX { ibNATBLIpAdress, ibNATBLSlotNo }
                        ::= { ibNATBLManagerTable 1 }


                IbNATBLManagerEntry ::=
                        SEQUENCE {
                                ibNATBLIpAdress
                                        IpAddress,
                                ibNATBLSlotNo
                                        Integer32,
                                ibNATBLConSum
                                        Integer32,
                                ibNATBLConSpd
                                        INTEGER
                         }

                ibNATBLIpAdress OBJECT-TYPE
                        SYNTAX IpAddress
                        MAX-ACCESS not-accessible
                        STATUS current
                        DESCRIPTION
                                "The IP address of entry of blacklist."
                        ::= { ibNATBLManagerEntry 1 }


                ibNATBLSlotNo OBJECT-TYPE
                        SYNTAX Integer32 (1..14)
                        MAX-ACCESS not-accessible
                        STATUS current
                        DESCRIPTION
                                "The number of NAT board."
                        ::= { ibNATBLManagerEntry 2 }


                ibNATBLConSum OBJECT-TYPE
                        SYNTAX Integer32
                        MAX-ACCESS read-only
                        STATUS current
                        DESCRIPTION
                                "The connection amount."
                        ::= { ibNATBLManagerEntry 3 }


                ibNATBLConSpd OBJECT-TYPE
                        SYNTAX INTEGER
                                {
                                red(1),
                                yellow(2),
                                green(3)
                                }
                        MAX-ACCESS read-only
                        STATUS current
                        DESCRIPTION
                                "The state of connection rate:
                                red(1)   : the connection rate is above the upper limit.
                                yellow(2): the connection rate is between the upper and lower limit.
                                green(3) : the connection rate is below the lower limit."
                        ::= { ibNATBLManagerEntry 4 }


--     NAT Statistics Info
                ibNATStatTable OBJECT-TYPE
                        SYNTAX SEQUENCE OF IbNATStatEntry
                        MAX-ACCESS not-accessible
                        STATUS current
                        DESCRIPTION
                                "The statistics information table of NAT module."
                        ::= { ibNATMibObjects 8 }


                ibNATStatEntry OBJECT-TYPE
                        SYNTAX IbNATStatEntry
                        MAX-ACCESS not-accessible
                        STATUS current
                        DESCRIPTION
                                "The entry of statistics information table of NAT module."
                        INDEX { ibNATStatNATBoardNo }
                        ::= { ibNATStatTable 1 }


                IbNATStatEntry ::=
                        SEQUENCE {
                                ibNATStatNATBoardNo
                                        Integer32,
                                ibNATStatActiveTblCount
                                        Counter32,
                                ibNATStatActiveTblCountInNP
                                        Counter32,
                                ibNATStatActiveNatTblCount
                                        Counter32,
                                ibNATStatActiveSvrTblCount
                                        Counter32,
                                ibNATStatActivePoolTblCount
                                        Counter32,
                                ibNATStatNumOfUsedPort
                                        Counter32,
                                ibNATStatNumOfGoodPkt
                                        Counter32,
                                ibNATStatNumOfBadPkt
                                        Counter32,
                                ibNATStaticSessionCount
                                        Integer32,
                                ibNATFragmentSessionCount
                                        Integer32,
                                ibNATSequenceSessionCount
                                        Integer32,
                                ibNATLogCount
                                        Integer32
                         }

                ibNATStatNATBoardNo OBJECT-TYPE
                        SYNTAX Integer32 (1..14 | 255)
                        MAX-ACCESS not-accessible
                        STATUS current
                        DESCRIPTION
                                "The number of NAT board.  In router, the value is 255 because no NAT board in it."
                        ::= { ibNATStatEntry 1 }


                ibNATStatActiveTblCount OBJECT-TYPE
                        SYNTAX Counter32
                        MAX-ACCESS read-only
                        STATUS current
                        DESCRIPTION
                                "Active PAT session count In software."
                        ::= { ibNATStatEntry 2 }


                ibNATStatActiveTblCountInNP OBJECT-TYPE
                        SYNTAX Counter32
                        MAX-ACCESS read-only
                        STATUS current
                        DESCRIPTION
                                "Active PAT session count In NP."
                        ::= { ibNATStatEntry 3 }


                ibNATStatActiveNatTblCount OBJECT-TYPE
                        SYNTAX Counter32
                        MAX-ACCESS read-only
                        STATUS current
                        DESCRIPTION
                                "Active NO-PAT session count."
                        ::= { ibNATStatEntry 4 }


                ibNATStatActiveSvrTblCount OBJECT-TYPE
                        SYNTAX Counter32
                        MAX-ACCESS read-only
                        STATUS current
                        DESCRIPTION
                                "Active SERVER session count."
                        ::= { ibNATStatEntry 5 }


                ibNATStatActivePoolTblCount OBJECT-TYPE
                        SYNTAX Counter32
                        MAX-ACCESS read-only
                        STATUS current
                        DESCRIPTION
                                "Active address pool session count."
                        ::= { ibNATStatEntry 6 }


                ibNATStatNumOfUsedPort OBJECT-TYPE
                        SYNTAX Counter32
                        MAX-ACCESS read-only
                        STATUS current
                        DESCRIPTION
                                "The number of used port in NP."
                        ::= { ibNATStatEntry 7 }


                ibNATStatNumOfGoodPkt OBJECT-TYPE
                        SYNTAX Counter32
                        MAX-ACCESS read-only
                        STATUS current
                        DESCRIPTION
                                "The number of good packet in NP."
                        ::= { ibNATStatEntry 8 }


                ibNATStatNumOfBadPkt OBJECT-TYPE
                        SYNTAX Counter32
                        MAX-ACCESS read-only
                        STATUS current
                        DESCRIPTION
                                "The number of bad packet in NP."
                        ::= { ibNATStatEntry 9 }


                ibNATStaticSessionCount OBJECT-TYPE
                        SYNTAX Integer32
                        MAX-ACCESS read-only
                        STATUS current
                        DESCRIPTION
                                "Active STATIC session count."
                        ::= { ibNATStatEntry 10 }


                ibNATFragmentSessionCount OBJECT-TYPE
                        SYNTAX Integer32
                        MAX-ACCESS read-only
                        STATUS current
                        DESCRIPTION
                                "Active fragment packet session count."
                        ::= { ibNATStatEntry 11 }


                ibNATSequenceSessionCount OBJECT-TYPE
                        SYNTAX Integer32
                        MAX-ACCESS read-only
                        STATUS current
                        DESCRIPTION
                                "Active session table count hash by private IP."
                        ::= { ibNATStatEntry 12 }


                ibNATLogCount OBJECT-TYPE
                        SYNTAX Integer32
                        MAX-ACCESS read-only
                        STATUS current
                        DESCRIPTION
                                "Buffered Nat LOG table count."
                        ::= { ibNATStatEntry 13 }


--     nat session
                ibNATSessionTable OBJECT-TYPE
                        SYNTAX SEQUENCE OF IbNATSessionEntry
                        MAX-ACCESS not-accessible
                        STATUS current
                        DESCRIPTION
                                "The nat session information table.  There is the address translation information in the table.
                                The sketch map of connection is
                                pc1(private Net)------------------>NAT Device ------------------>Server(public Net)
                                InsideIP, InsidePort---->translating to GlobalIP, GlobalPort------>PeerIP, PeerPort.
                                "
                        ::= { ibNATMibObjects 9 }


                ibNATSessionEntry OBJECT-TYPE
                        SYNTAX IbNATSessionEntry
                        MAX-ACCESS not-accessible
                        STATUS current
                        DESCRIPTION
                                "The entry of session information table."
                        INDEX { ibNATSessionHashNumber, ibNATSessionProtocol, ibNATSessionInsideIP, ibNATSessionInsidePort, ibNATSessionPeerIP,
                                ibNATSessionPeerPort, ibNATSessionVpnIndex }
                        ::= { ibNATSessionTable 1 }


                IbNATSessionEntry ::=
                        SEQUENCE {
                                ibNATSessionHashNumber
                                        Integer32,
                                ibNATSessionProtocol
                                        Integer32,
                                ibNATSessionGlobalIP
                                        IpAddress,
                                ibNATSessionGlobalPort
                                        Integer32,
                                ibNATSessionInsideIP
                                        IpAddress,
                                ibNATSessionInsidePort
                                        Integer32,
                                ibNATSessionPeerIP
                                        IpAddress,
                                ibNATSessionPeerPort
                                        Integer32,
                                ibNATSessionVpnIndex
                                        Integer32,
                                ibNATSessionTTL
                                        Integer32,
                                ibNATSessionStatus
                                        Integer32,
                                ibNATSessionLeftTime
                                        TimeTicks
                         }

                ibNATSessionHashNumber OBJECT-TYPE
                        SYNTAX Integer32 (1..300000)
                        MAX-ACCESS not-accessible
                        STATUS current
                        DESCRIPTION
                                "The row number of the hash table."
                        ::= { ibNATSessionEntry 1 }


                ibNATSessionProtocol OBJECT-TYPE
                        SYNTAX Integer32 (1..255)
                        MAX-ACCESS not-accessible
                        STATUS current
                        DESCRIPTION
                                "The protocol type of session."
                        ::= { ibNATSessionEntry 2 }


                ibNATSessionGlobalIP OBJECT-TYPE
                        SYNTAX IpAddress
                        MAX-ACCESS read-only
                        STATUS current
                        DESCRIPTION
                                "The global IP of session. "
                        ::= { ibNATSessionEntry 3 }


                ibNATSessionGlobalPort OBJECT-TYPE
                        SYNTAX Integer32 (0..65535)
                        MAX-ACCESS read-only
                        STATUS current
                        DESCRIPTION
                                "The global port of session."
                        ::= { ibNATSessionEntry 4 }


                ibNATSessionInsideIP OBJECT-TYPE
                        SYNTAX IpAddress
                        MAX-ACCESS not-accessible
                        STATUS current
                        DESCRIPTION
                                "The Inside IP of session."
                        ::= { ibNATSessionEntry 5 }


                ibNATSessionInsidePort OBJECT-TYPE
                        SYNTAX Integer32 (0..65535)
                        MAX-ACCESS not-accessible
                        STATUS current
                        DESCRIPTION
                                "The Inside port of session."
                        ::= { ibNATSessionEntry 6 }


                ibNATSessionPeerIP OBJECT-TYPE
                        SYNTAX IpAddress
                        MAX-ACCESS not-accessible
                        STATUS current
                        DESCRIPTION
                                "The peer IP of session."
                        ::= { ibNATSessionEntry 7 }


                ibNATSessionPeerPort OBJECT-TYPE
                        SYNTAX Integer32 (0..65535)
                        MAX-ACCESS not-accessible
                        STATUS current
                        DESCRIPTION
                                "The peer port of session."
                        ::= { ibNATSessionEntry 8 }


                ibNATSessionVpnIndex OBJECT-TYPE
                        SYNTAX Integer32 (0..255)
                        MAX-ACCESS not-accessible
                        STATUS current
                        DESCRIPTION
                                "The VPN index of session."
                        ::= { ibNATSessionEntry 9 }


                ibNATSessionTTL OBJECT-TYPE
                        SYNTAX Integer32
                        MAX-ACCESS read-only
                        STATUS current
                        DESCRIPTION
                                "The TTL of session."
                        ::= { ibNATSessionEntry 10 }


                ibNATSessionStatus OBJECT-TYPE
                        SYNTAX Integer32
                        MAX-ACCESS read-only
                        STATUS current
                        DESCRIPTION
                                "The status of session."
                        ::= { ibNATSessionEntry 11 }


                ibNATSessionLeftTime OBJECT-TYPE
                        SYNTAX TimeTicks
                        MAX-ACCESS read-only
                        STATUS current
                        DESCRIPTION
                                "The Left time of session."
                        ::= { ibNATSessionEntry 12 }


                ibNATStaticConfTable OBJECT-TYPE
                        SYNTAX SEQUENCE OF IbNATStaticConfEntry
                        MAX-ACCESS not-accessible
                        STATUS current
                        DESCRIPTION
                                "Static Nat configuration table."
                        ::= { ibNATMibObjects 10 }


                ibNATStaticConfEntry OBJECT-TYPE
                        SYNTAX IbNATStaticConfEntry
                        MAX-ACCESS not-accessible
                        STATUS current
                        DESCRIPTION
                                "Configure static Nat."
                        INDEX { ibNATStaticInsideIp }
                        ::= { ibNATStaticConfTable 1 }


                IbNATStaticConfEntry ::=
                        SEQUENCE {
                                ibNATStaticInsideIp
                                        IpAddress,
                                ibNATStaticGlobalIp
                                        IpAddress,
                                ibNATStaticRowStatus
                                        RowStatus
                         }

                ibNATStaticInsideIp OBJECT-TYPE
                        SYNTAX IpAddress
                        MAX-ACCESS not-accessible
                        STATUS current
                        DESCRIPTION
                                "Inside ip address."
                        ::= { ibNATStaticConfEntry 1 }


                ibNATStaticGlobalIp OBJECT-TYPE
                        SYNTAX IpAddress
                        MAX-ACCESS read-create
                        STATUS current
                        DESCRIPTION
                                "Global Ip address."
                        ::= { ibNATStaticConfEntry 2 }


                ibNATStaticRowStatus OBJECT-TYPE
                        SYNTAX RowStatus
                        MAX-ACCESS read-create
                        STATUS current
                        DESCRIPTION
                                "Only support 'destroy' and 'createAndGo'.
                                If ibNATStaticInsideIp and ibNATStaticGlobalIp were provided correctly,
                                its value is changed 'active'."
                        ::= { ibNATStaticConfEntry 3 }


                ibNATStaticEnableTable OBJECT-TYPE
                        SYNTAX SEQUENCE OF IbNATStaticEnableEntry
                        MAX-ACCESS not-accessible
                        STATUS current
                        DESCRIPTION
                                "Active the static Nat on interface."
                        ::= { ibNATMibObjects 11 }


                ibNATStaticEnableEntry OBJECT-TYPE
                        SYNTAX IbNATStaticEnableEntry
                        MAX-ACCESS not-accessible
                        STATUS current
                        DESCRIPTION
                                "Active the static Nat on interface."
                        INDEX { ifIndex }
                        ::= { ibNATStaticEnableTable 1 }


                IbNATStaticEnableEntry ::=
                        SEQUENCE {
                                ibNATStaticEnable
                                        INTEGER
                         }

                ibNATStaticEnable OBJECT-TYPE
                        SYNTAX INTEGER
                                {
                                disable(0),
                                enable(1)
                                }
                        MAX-ACCESS read-write
                        STATUS current
                        DESCRIPTION
                                "Enable/disable the static Nat on the interface(ibNatStaticEnableIfIndex).
                                disable  (0)
                                enable   (1)
                                                            "
                        ::= { ibNATStaticEnableEntry 2 }


                ibNATDnsMapTable OBJECT-TYPE
                        SYNTAX SEQUENCE OF IbNATDnsMapEntry
                        MAX-ACCESS not-accessible
                        STATUS current
                        DESCRIPTION
                                "This table is used to set mapping of DNS."
                        ::= { ibNATMibObjects 12 }


                ibNATDnsMapEntry OBJECT-TYPE
                        SYNTAX IbNATDnsMapEntry
                        MAX-ACCESS not-accessible
                        STATUS current
                        DESCRIPTION
                                "The entry of ibNATDnsMapTable."
                        INDEX { ibNATDnsMapDomainName }
                        ::= { ibNATDnsMapTable 1 }


                IbNATDnsMapEntry ::=
                        SEQUENCE {
                                ibNATDnsMapDomainName
                                        DisplayString,
                                ibNATDnsMapGlobalIp
                                        IpAddress,
                                ibNATDnsMapGlobalPort
                                        Integer32,
                                ibNATDnsMapProtocolType
                                        INTEGER,
                                ibNATDnsMapLastUseTime
                                        TimeTicks,
                                ibNATDnsMapRowStatus
                                        RowStatus
                         }

                ibNATDnsMapDomainName OBJECT-TYPE
                        SYNTAX DisplayString
                        MAX-ACCESS not-accessible
                        STATUS current
                        DESCRIPTION
                                "Domain name."
                        ::= { ibNATDnsMapEntry 1 }


                ibNATDnsMapGlobalIp OBJECT-TYPE
                        SYNTAX IpAddress
                        MAX-ACCESS read-create
                        STATUS current
                        DESCRIPTION
                                "Global IP address."
                        ::= { ibNATDnsMapEntry 2 }


                ibNATDnsMapGlobalPort OBJECT-TYPE
                        SYNTAX Integer32 (1..65535)
                        MAX-ACCESS read-create
                        STATUS current
                        DESCRIPTION
                                " Global port number."
                        ::= { ibNATDnsMapEntry 3 }


                ibNATDnsMapProtocolType OBJECT-TYPE
                        SYNTAX INTEGER
                                {
                                any(0),
                                typeTCP(1),
                                typeUDP(2)
                                }
                        MAX-ACCESS read-create
                        STATUS current
                        DESCRIPTION
                                "TCP   Transmission Control Protocol.
                                UDP   User Datagram Protocol."
                        ::= { ibNATDnsMapEntry 4 }


                ibNATDnsMapLastUseTime OBJECT-TYPE
                        SYNTAX TimeTicks
                        MAX-ACCESS read-create
                        STATUS current
                        DESCRIPTION
                                "Its value is the time that the device uses
                                from startup to last use 'Dns Map'record.
                                If the value is 0,the device never use this
                                record."
                        ::= { ibNATDnsMapEntry 5 }


                ibNATDnsMapRowStatus OBJECT-TYPE
                        SYNTAX RowStatus
                        MAX-ACCESS read-create
                        STATUS current
                        DESCRIPTION
                                "Only support 'destroy' and 'createAndGo'.
                                If ibNATDnsMapDomainName, ibNATDnsMapGlobalIp
                                and ibNATDnsMapGlobalPortor ibNATDnsMapDomainName,
                                ibNATDnsMapGlobalIp, ibNATDnsMapGlobalPort and
                                ibNATDnsMapProtocolType were provided correctly,
                                its value is changed 'active'."
                        ::= { ibNATDnsMapEntry 6 }

--     new NAT statistics
                ibNATStatVer2Table OBJECT-TYPE
                        SYNTAX  SEQUENCE OF IbNATStatVer2TableEntry
                        MAX-ACCESS  not-accessible
                        STATUS  current
                        DESCRIPTION
                        "The new statistics of NAT."
                    ::= { ibNATMibObjects 13 }

                ibNATStatVer2TableEntry OBJECT-TYPE
                    SYNTAX  IbNATStatVer2TableEntry
                    MAX-ACCESS  not-accessible
                    STATUS  current
                    DESCRIPTION
                    "An entry (conceptual row) representing NAT
                     statistics information."
                    INDEX { ibNATStatChassis, ibNATStatSlot, ibNATStatCPUID }
                ::= { ibNATStatVer2Table 1 }

                IbNATStatVer2TableEntry ::= SEQUENCE {
                    ibNATStatChassis                       Unsigned32,
                    ibNATStatSlot                          Unsigned32,
                    ibNATStatCPUID                         Unsigned32,
                    ibNATTotalNATSessionCount              Unsigned32,
                    ibNATEimTableCount                     Unsigned32,
                    ibNATInboundNoPATTableCount            Unsigned32,
                    ibNATOutboundNoPATTableCount           Unsigned32,
                    ibNATMaxDynamicPortblock               Unsigned32,
                    ibNATMaxStaticPortblock                Unsigned32,
                    ibNATActiveDynamicPortblock            Unsigned32,
                    ibNATActiveStaticPortblock             Unsigned32,
                    ibNATSessionCreateRate                 Unsigned32,
                    ibNATCurBandwidthRatio                 Unsigned32
                    }

                ibNATStatChassis   OBJECT-TYPE
                    SYNTAX Unsigned32(0..65534)
                    MAX-ACCESS  not-accessible
                    STATUS  current
                    DESCRIPTION
                    "An IRF member device ID."
                ::= { ibNATStatVer2TableEntry  1 }

                ibNATStatSlot    OBJECT-TYPE
                    SYNTAX Unsigned32(0..65534)
                    MAX-ACCESS  not-accessible
                    STATUS  current
                    DESCRIPTION
                    "The slot where the card resides."
                ::= { ibNATStatVer2TableEntry  2 }

                ibNATStatCPUID   OBJECT-TYPE
                    SYNTAX Unsigned32(0..7)
                    MAX-ACCESS  not-accessible
                    STATUS  current
                    DESCRIPTION
                    "CPU ID."
                ::= { ibNATStatVer2TableEntry  3 }

                ibNATTotalNATSessionCount   OBJECT-TYPE
                    SYNTAX Unsigned32
                    MAX-ACCESS  read-only
                    STATUS  current
                    DESCRIPTION
                    "The number of current NAT sessions."
                ::= { ibNATStatVer2TableEntry  4 }

                ibNATEimTableCount   OBJECT-TYPE
                    SYNTAX Unsigned32
                    MAX-ACCESS  read-only
                    STATUS  current
                    DESCRIPTION
                    "The number of current EIM tables."
                ::= { ibNATStatVer2TableEntry  5 }

                ibNATInboundNoPATTableCount   OBJECT-TYPE
                    SYNTAX Unsigned32
                    MAX-ACCESS  read-only
                    STATUS  current
                    DESCRIPTION
                    "The number of current NO-PAT tables built on NAT inbound
                     translation."
                ::= { ibNATStatVer2TableEntry  6 }

                ibNATOutboundNoPATTableCount   OBJECT-TYPE
                    SYNTAX Unsigned32
                    MAX-ACCESS  read-only
                    STATUS  current
                    DESCRIPTION
                    "The number of current NO-PAT tables built on NAT outbound
                     translation."
                ::= { ibNATStatVer2TableEntry  7 }

                ibNATMaxDynamicPortblock   OBJECT-TYPE
                    SYNTAX Unsigned32
                    MAX-ACCESS  read-only
                    STATUS  current
                    DESCRIPTION
                    "The number of current NAT444 dynamic port blocks."
                ::= { ibNATStatVer2TableEntry  8 }

                ibNATMaxStaticPortblock   OBJECT-TYPE
                    SYNTAX Unsigned32
                    MAX-ACCESS  read-only
                    STATUS  current
                    DESCRIPTION
                    "The number of current NAT444 static port blocks."
                ::= { ibNATStatVer2TableEntry  9 }

                ibNATActiveDynamicPortblock   OBJECT-TYPE
                    SYNTAX Unsigned32
                    MAX-ACCESS  read-only
                    STATUS  current
                    DESCRIPTION
                    "The number of current active NAT444 dynamic port blocks."
                ::= { ibNATStatVer2TableEntry  10 }

                ibNATActiveStaticPortblock   OBJECT-TYPE
                    SYNTAX Unsigned32
                    MAX-ACCESS  read-only
                    STATUS  current
                    DESCRIPTION
                    "The number of current active NAT444 static port blocks."
                ::= { ibNATStatVer2TableEntry  11 }

                ibNATSessionCreateRate       OBJECT-TYPE
                    SYNTAX Unsigned32
                    MAX-ACCESS  read-only
                    STATUS  current
                    DESCRIPTION
                    "The rate of nat session create."
                ::= { ibNATStatVer2TableEntry  12 }

ibNATCurBandwidthRatio     OBJECT-TYPE
                    SYNTAX Unsigned32(0..100)
                    MAX-ACCESS  read-only
                    STATUS  current
                    DESCRIPTION
                    "The value of the current CGN card bandwidth usage."
                ::= { ibNATStatVer2TableEntry  13 }

-- Nodes of NAT Address Group Statistics

        ibNATAddrGrpStatTable OBJECT-TYPE
            SYNTAX SEQUENCE OF IbNATAddrGrpStatTableEntry
            MAX-ACCESS not-accessible
            STATUS current
            DESCRIPTION
                "The statistics of NAT address groups."
            ::= { ibNATMibObjects 14 }

        ibNATAddrGrpStatTableEntry OBJECT-TYPE
            SYNTAX IbNATAddrGrpStatTableEntry
            MAX-ACCESS not-accessible
            STATUS current
            DESCRIPTION
                "An entry (conceptual row) representing NAT
                     address group statistics."
            INDEX
            {
                ibNATAddrGrpStatChassis,
                ibNATAddrGrpStatSlot,
                ibNATAddrGrpStatCPUID,
                ibNATAddrGrpStatAddrGrpNum
            }
            ::= { ibNATAddrGrpStatTable 1 }

        IbNATAddrGrpStatTableEntry ::=
        SEQUENCE
        {
            ibNATAddrGrpStatChassis
                Unsigned32,
            ibNATAddrGrpStatSlot
                Unsigned32,
            ibNATAddrGrpStatCPUID
                Unsigned32,
            ibNATAddrGrpStatAddrGrpNum
                Unsigned32,
            ibNATAddrGrpStatFailAllocPort
                Unsigned32,
            ibNATAddrGrpStatAddrGrpSessCnt
                Counter64
        }

        ibNATAddrGrpStatChassis OBJECT-TYPE
            SYNTAX Unsigned32(0..65534)
            MAX-ACCESS not-accessible
            STATUS current
            DESCRIPTION
                "An IRF member device ID."
            ::= { ibNATAddrGrpStatTableEntry 1 }

        ibNATAddrGrpStatSlot OBJECT-TYPE
            SYNTAX Unsigned32(0..65534)
            MAX-ACCESS not-accessible
            STATUS current
            DESCRIPTION
                "The slot where the card resides."
            ::= { ibNATAddrGrpStatTableEntry 2 }

        ibNATAddrGrpStatCPUID OBJECT-TYPE
            SYNTAX Unsigned32(0..7)
            MAX-ACCESS not-accessible
            STATUS current
            DESCRIPTION
                "CPU ID."
            ::= { ibNATAddrGrpStatTableEntry 3 }

        ibNATAddrGrpStatAddrGrpNum OBJECT-TYPE
            SYNTAX Unsigned32(0..65535)
            MAX-ACCESS not-accessible
            STATUS current
            DESCRIPTION
                "The NAT address group number."
            ::= { ibNATAddrGrpStatTableEntry 4 }

        ibNATAddrGrpStatFailAllocPort OBJECT-TYPE
            SYNTAX Unsigned32
            MAX-ACCESS read-only
            STATUS current
            DESCRIPTION
                "The count of NAT port allocation failures."
            ::= { ibNATAddrGrpStatTableEntry 5 }

        ibNATAddrGrpStatAddrGrpSessCnt OBJECT-TYPE
            SYNTAX Counter64
            MAX-ACCESS read-only
            STATUS current
            DESCRIPTION
                "The session count of current NAT address group."
            ::= { ibNATAddrGrpStatTableEntry 6 }
-- Describe objects for CGN bandwidth usage trap
ibNATBandwidthTraps OBJECT IDENTIFIER ::= { ibNATMibObjects 15 }
ibNATBandwidthPrefix OBJECT IDENTIFIER ::= { ibNATBandwidthTraps 0 }
ibNATBandwidthTrap NOTIFICATION-TYPE
    OBJECTS
        {
            ibNATBandwidthRatio,
            ibNATChassis,
            ibNATSlot,
            ibNATCpu
        }
    STATUS      current
    DESCRIPTION
    "Send trap when the bandwidth usage of a CGN card has reached the ibNATBandwidthRatio."
    ::= { ibNATBandwidthPrefix 1 }
ibNATBandwidthRecoveryTrap NOTIFICATION-TYPE
    OBJECTS
        {
            ibNATChassis,
            ibNATSlot,
            ibNATCpu
         }
    STATUS      current
    DESCRIPTION
    "Send trap when the CGN card bandwidth usage has dropped below the threshold."
    ::= { ibNATBandwidthPrefix 2 }
ibNATBandwidthTrapObjects OBJECT IDENTIFIER ::= { ibNATBandwidthTraps 1 }
ibNATBandwidthRatio OBJECT-TYPE
SYNTAX      Unsigned32
UNITS       "percent"
    MAX-ACCESS  accessible-for-notify
    STATUS      current
    DESCRIPTION
    "The usage of CGN card bandwidth."
    ::= { ibNATBandwidthTrapObjects 1 }
ibNATChassis OBJECT-TYPE
    SYNTAX      Unsigned32(0..65534)
    MAX-ACCESS  accessible-for-notify
    STATUS      current
    DESCRIPTION
    "An IRF member device ID."
    ::= { ibNATBandwidthTrapObjects 2 }
ibNATSlot OBJECT-TYPE
    SYNTAX      Unsigned32(0..65534)
    MAX-ACCESS  accessible-for-notify
    STATUS      current
    DESCRIPTION
    "The slot where the card resides."
    ::= { ibNATBandwidthTrapObjects 3 }
ibNATCpu OBJECT-TYPE
    SYNTAX      Unsigned32(0..7)
    MAX-ACCESS  accessible-for-notify
    STATUS      current
    DESCRIPTION
    "CPU ID."
    ::= { ibNATBandwidthTrapObjects 4 }

-- Describe objects for NAT Instance Address Group Resource Usage
ibInstAddrGrpUsgTable OBJECT-TYPE
   SYNTAX SEQUENCE OF IbInstAddrGrpUsgEntry
   MAX-ACCESS not-accessible
   STATUS current
   DESCRIPTION "The usage of NAT instance address group resources(port-block usage)."
::= { ibNATMibObjects 16 }

ibInstAddrGrpUsgEntry OBJECT-TYPE
   SYNTAX IbInstAddrGrpUsgEntry
   MAX-ACCESS not-accessible
   STATUS current
   DESCRIPTION
   "The resource usage info of an address group."
   INDEX {
           ibInstAddrUsgInstName,
           ibInstAddrUsgGrpIndex
         }
::= { ibInstAddrGrpUsgTable 1 }

IbInstAddrGrpUsgEntry ::= SEQUENCE
{
   ibInstAddrUsgInstName    OCTET STRING,
   ibInstAddrUsgGrpIndex    Unsigned32,
   ibInstAddrUsgInstIndex   Unsigned32,
   ibInstAddrUsgGrpUsage    Unsigned32,
   ibInstAddrUsgTotalIPCount  Unsigned32,
   ibInstAddrUsgUsedIPCount   Unsigned32,
   ibInstAddrUsgUnusedIPCount Unsigned32
}

ibInstAddrUsgInstName OBJECT-TYPE
   SYNTAX OCTET STRING(SIZE (1..32))
   MAX-ACCESS not-accessible
   STATUS current
   DESCRIPTION
   "NAT instance name."
::= { ibInstAddrGrpUsgEntry 1 }

ibInstAddrUsgGrpIndex OBJECT-TYPE
   SYNTAX Unsigned32(1..65536)
   MAX-ACCESS not-accessible
   STATUS current
   DESCRIPTION
   "NAT address group ID."
::= { ibInstAddrGrpUsgEntry 2 }

ibInstAddrUsgInstIndex OBJECT-TYPE
   SYNTAX Unsigned32(1..127)
   MAX-ACCESS read-only
   STATUS current
   DESCRIPTION
   "NAT instance index."
::= { ibInstAddrGrpUsgEntry 3 }

ibInstAddrUsgGrpUsage OBJECT-TYPE
   SYNTAX Unsigned32(0..100)
   UNITS "percent"
   MAX-ACCESS read-only
   STATUS current
   DESCRIPTION
   "The usage of address group resources."
::= { ibInstAddrGrpUsgEntry 4 }

ibInstAddrUsgTotalIPCount OBJECT-TYPE
   SYNTAX Unsigned32(0..65536)
   MAX-ACCESS read-only
   STATUS current
   DESCRIPTION
   "The total number of NAT addresses."
::= { ibInstAddrGrpUsgEntry 5 }

ibInstAddrUsgUsedIPCount OBJECT-TYPE
   SYNTAX Unsigned32(0..65536)
   MAX-ACCESS read-only
   STATUS current
   DESCRIPTION
   "The number of NAT addresses used."
::= { ibInstAddrGrpUsgEntry 6 }

ibInstAddrUsgUnusedIPCount OBJECT-TYPE
   SYNTAX Unsigned32(0..65536)
   UNITS "percent"
   MAX-ACCESS read-only
   STATUS current
   DESCRIPTION
   "The number of NAT addresses not in use."
::= { ibInstAddrGrpUsgEntry 7 }

-- Describe objects for NAT Instance Address Group Member Resource Usage
ibInstAddrGrpMemberUsgTable OBJECT-TYPE
   SYNTAX SEQUENCE OF IbInstAddrGrpMemberUsgEntry
   MAX-ACCESS not-accessible
   STATUS current
   DESCRIPTION "The usage of CGN address group member resources(port-block usage)."
::= { ibNATMibObjects 17 }

ibInstAddrGrpMemberUsgEntry OBJECT-TYPE
   SYNTAX IbInstAddrGrpMemberUsgEntry
   MAX-ACCESS not-accessible
   STATUS current
   DESCRIPTION
   "The resource usage info of an address group member."
   INDEX {
           ibInstAddrMemUsgInstName,
           ibInstAddrMemUsgGrpIndex,
           ibInstAddrMemUsgGrpStartIP
         }
::= { ibInstAddrGrpMemberUsgTable 1 }

IbInstAddrGrpMemberUsgEntry ::= SEQUENCE
{
   ibInstAddrMemUsgInstName     OCTET STRING,
   ibInstAddrMemUsgGrpIndex     Unsigned32,
   ibInstAddrMemUsgGrpStartIP   IpAddress,
   ibInstAddrMemUsgGrpEndIP     IpAddress,
   ibInstAddrMemUsgInstIndex    Unsigned32,
   ibInstAddrMemUsgGrpUsage     Unsigned32,
   ibInstAddrMemUsgGrpIPMask    OCTET STRING
}

ibInstAddrMemUsgInstName OBJECT-TYPE
   SYNTAX OCTET STRING(SIZE (1..32))
   MAX-ACCESS not-accessible
   STATUS current
   DESCRIPTION
   "NAT instance name."
::= { ibInstAddrGrpMemberUsgEntry 1 }

ibInstAddrMemUsgGrpIndex OBJECT-TYPE
   SYNTAX Unsigned32(1..65536)
   MAX-ACCESS not-accessible
   STATUS current
   DESCRIPTION
   "NAT address group ID."
::= { ibInstAddrGrpMemberUsgEntry 2 }

ibInstAddrMemUsgGrpStartIP OBJECT-TYPE
   SYNTAX IpAddress
   MAX-ACCESS not-accessible
   STATUS current
   DESCRIPTION
   "NAT address group member start IP address."
::= { ibInstAddrGrpMemberUsgEntry 3 }

ibInstAddrMemUsgGrpEndIP OBJECT-TYPE
   SYNTAX IpAddress
   MAX-ACCESS read-only
   STATUS current
   DESCRIPTION
   "NAT address group member end IP address."
::= { ibInstAddrGrpMemberUsgEntry 4 }

ibInstAddrMemUsgInstIndex OBJECT-TYPE
   SYNTAX Unsigned32(1..127)
   MAX-ACCESS read-only
   STATUS current
   DESCRIPTION
   "NAT instance index."
::= { ibInstAddrGrpMemberUsgEntry 5 }

ibInstAddrMemUsgGrpUsage OBJECT-TYPE
   SYNTAX Unsigned32(0..100)
   UNITS "percent"
   MAX-ACCESS read-only
   STATUS current
   DESCRIPTION
   "The usage of address group member resources."
::= { ibInstAddrGrpMemberUsgEntry 6 }

ibInstAddrMemUsgGrpIPMask OBJECT-TYPE
   SYNTAX OCTET STRING ( SIZE(0..32) )
   MAX-ACCESS read-only
   STATUS current
   DESCRIPTION
   "NAT address mask."
::= { ibInstAddrGrpMemberUsgEntry 7 }

-- Describe objects for NAT Instance Address Group Usage Trap
ibInstAddrGrpUsageTraps OBJECT IDENTIFIER ::= { ibNATMibObjects 18 }

ibInstAddrGrpUsagePrefix OBJECT IDENTIFIER ::= { ibInstAddrGrpUsageTraps 0 }
ibInstAddrGrpUsageTrap NOTIFICATION-TYPE
OBJECTS
{
   ibInstAddrTrapInstName,
   ibInstAddrTrapGrpIndex,
   ibInstAddrTrapInstIndex,
   ibInstAddrTrapUsgThreshold
}
STATUS current
DESCRIPTION
"Send trap when ibInstAddrUsgGrpUsage reached the threshold."
::= { ibInstAddrGrpUsagePrefix 1 }

ibInstAddrGrpUsageRecovTrap NOTIFICATION-TYPE
OBJECTS
{
   ibInstAddrTrapInstName,
   ibInstAddrTrapGrpIndex,
   ibInstAddrTrapInstIndex
}
STATUS current
DESCRIPTION
"Send trap when dropped below the threshold."
::= { ibInstAddrGrpUsagePrefix 2 }

ibInstAddrGrpUsageTrapInfo OBJECT IDENTIFIER ::= { ibInstAddrGrpUsageTraps 1 }
ibInstAddrTrapInstName OBJECT-TYPE
   SYNTAX DisplayString(SIZE (1..32))
   MAX-ACCESS accessible-for-notify
   STATUS current
   DESCRIPTION
   "NAT instance name."
::= { ibInstAddrGrpUsageTrapInfo 1 }

ibInstAddrTrapGrpIndex OBJECT-TYPE
   SYNTAX Unsigned32(1..65536)
   MAX-ACCESS accessible-for-notify
   STATUS current
   DESCRIPTION
   "NAT address group ID."
::= { ibInstAddrGrpUsageTrapInfo 2 }

ibInstAddrTrapInstIndex OBJECT-TYPE
   SYNTAX Unsigned32(1..127)
   MAX-ACCESS accessible-for-notify
   STATUS current
   DESCRIPTION
   "NAT instance index."
::= { ibInstAddrGrpUsageTrapInfo 3 }

ibInstAddrTrapUsgThreshold OBJECT-TYPE
   SYNTAX Unsigned32(0..100)
   UNITS "percent"
   MAX-ACCESS accessible-for-notify
   STATUS current
   DESCRIPTION
   "NAT address group usage reached the threshold."
::= { ibInstAddrGrpUsageTrapInfo 4 }

-- Describe objects for NAT IP Pool Address Group Table
ibNatIPPoolGroupTable OBJECT-TYPE
   SYNTAX SEQUENCE OF IbNatIPPoolGroupEntry
   MAX-ACCESS not-accessible
   STATUS current
   DESCRIPTION "The usage of NAT IP pool address group resources."
::= { ibNATMibObjects 19 }

ibNatIPPoolGroupEntry OBJECT-TYPE
   SYNTAX IbNatIPPoolGroupEntry
   MAX-ACCESS not-accessible
   STATUS current
   DESCRIPTION
   "The resource usage info of an IP pool address group."
   INDEX {
           ibNatIPPoolName
         }
::= { ibNatIPPoolGroupTable 1 }

IbNatIPPoolGroupEntry ::= SEQUENCE
{
   ibNatIPPoolName        OCTET STRING,
   ibNatIPPoolAddrUsage   Unsigned32,
   ibNatIPPoolTotalCount  Unsigned32,
   ibNatIPPoolUsedCount   Unsigned32,
   ibNatIPPoolUnusedCount Unsigned32
}

ibNatIPPoolName OBJECT-TYPE
   SYNTAX OCTET STRING(SIZE (1..32))
   MAX-ACCESS not-accessible
   STATUS current
   DESCRIPTION
   "NAT IP pool name."
::= { ibNatIPPoolGroupEntry 1 }

ibNatIPPoolAddrUsage OBJECT-TYPE
   SYNTAX Unsigned32(0..100)
   MAX-ACCESS read-only
   STATUS current
   DESCRIPTION
   "The usage of NAT IP pool address group resources."
::= { ibNatIPPoolGroupEntry 2 }

ibNatIPPoolTotalCount OBJECT-TYPE
   SYNTAX Unsigned32(0..65536)
   MAX-ACCESS read-only
   STATUS current
   DESCRIPTION
   "The total number of NAT addresses."
::= { ibNatIPPoolGroupEntry 3 }

ibNatIPPoolUsedCount OBJECT-TYPE
   SYNTAX Unsigned32(0..65536)
   MAX-ACCESS read-only
   STATUS current
   DESCRIPTION
   "The number of NAT addresses used."
::= { ibNatIPPoolGroupEntry 4 }

ibNatIPPoolUnusedCount OBJECT-TYPE
   SYNTAX Unsigned32(0..65536)
   MAX-ACCESS read-only
   STATUS current
   DESCRIPTION
   "The number of NAT addresses not in use."
::= { ibNatIPPoolGroupEntry 5 }

-- Describe objects for NAT IP Pool Address Group Usage Trap
ibNatIPPoolAddrUsageExceedTraps OBJECT IDENTIFIER ::= { ibNATMibObjects 20 }

ibNatIPPoolAddrUsageExceedPrefix OBJECT IDENTIFIER ::= { ibNatIPPoolAddrUsageExceedTraps 0 }
ibNatIPPoolAddrUsageExceedTrap NOTIFICATION-TYPE
OBJECTS
{
   ibNatTrapIPPoolName,
   ibNatTrapIPPoolAddrUsage
}
STATUS current
DESCRIPTION
"Send trap when NatIPPoolAddrUsageExceed reached the threshold."
::= { ibNatIPPoolAddrUsageExceedPrefix 1 }

ibNatIPPoolAddrUsageRecoveryTrap NOTIFICATION-TYPE
OBJECTS
{
   ibNatTrapIPPoolName,
   ibNatTrapIPPoolAddrUsage
}
STATUS current
DESCRIPTION
"Send trap when dropped below the threshold."
::= { ibNatIPPoolAddrUsageExceedPrefix 2 }

ibNatIPPoolIpAllocFailTrap NOTIFICATION-TYPE
OBJECTS
{
   ibNatTrapIPPoolName
}
STATUS current
DESCRIPTION
"Send traps when IP addresses in a NAT IP pool are used up."
::= { ibNatIPPoolAddrUsageExceedPrefix 3 }

ibNatIPPoolIpAllocFailRecoveryTrap NOTIFICATION-TYPE
OBJECTS
{
   ibNatTrapIPPoolName
}
STATUS current
DESCRIPTION
"Send traps when IP addresses in a NAT IP pool become available."
::= { ibNatIPPoolAddrUsageExceedPrefix 4 }

ibNatIPPoolIpApplyFailTrap NOTIFICATION-TYPE
OBJECTS
{
   ibNatTrapIPPoolName,
   ibNatTrapIPPoolMemStartIP,
   ibNatTrapIPPoolMemIPMask,
   ibNatTrapIPPoolFailReason
}
STATUS current
DESCRIPTION
"Send trap when IP addresses apply failed."
::= { ibNatIPPoolAddrUsageExceedPrefix 5 }

ibNatIPPoolAddrUsageTrapExceed OBJECT IDENTIFIER ::= { ibNatIPPoolAddrUsageExceedTraps 1 }
ibNatTrapIPPoolName OBJECT-TYPE
   SYNTAX OCTET STRING(SIZE (1..32))
   MAX-ACCESS accessible-for-notify
   STATUS current
   DESCRIPTION
   "NAT IP pool name."
::= { ibNatIPPoolAddrUsageTrapExceed 1 }

ibNatTrapIPPoolAddrUsage OBJECT-TYPE
   SYNTAX Unsigned32(0..100)
   MAX-ACCESS accessible-for-notify
   STATUS current
   DESCRIPTION
   "NAT IP pool address usage."
::= { ibNatIPPoolAddrUsageTrapExceed 2 }

ibNatTrapIPPoolMemStartIP OBJECT-TYPE
   SYNTAX IpAddress
   MAX-ACCESS accessible-for-notify
   STATUS current
   DESCRIPTION
   "The start IP address of the address pool."
::= { ibNatIPPoolAddrUsageTrapExceed 3 }

ibNatTrapIPPoolMemIPMask OBJECT-TYPE
   SYNTAX OCTET STRING(SIZE (0..32))
   MAX-ACCESS accessible-for-notify
   STATUS current
   DESCRIPTION
   "IP address mask."
::= { ibNatIPPoolAddrUsageTrapExceed 4 }

ibNatTrapIPPoolFailReason OBJECT-TYPE
   SYNTAX OCTET STRING(SIZE (1..127))
   MAX-ACCESS accessible-for-notify
   STATUS current
   DESCRIPTION
   "IP address application failure reason."
::= { ibNatIPPoolAddrUsageTrapExceed 5 }

-- Describes objects for NAT port block traps
ibNatPortBlockTraps OBJECT IDENTIFIER ::= { ibNATMibObjects 21 }

ibNatPortBlockPrefix OBJECT IDENTIFIER ::= { ibNatPortBlockTraps 0 }
ibNatPortBlockAllocFailTrap NOTIFICATION-TYPE
OBJECTS
{
   ibNatTrapAddrGrpIndex,
   ibNatTrapAddrGrpChassis,
   ibNatTrapAddrGrpSlot,
   ibNatTrapAddrGrpCpu
}
STATUS current
DESCRIPTION
"Send trap when port blocks ran out."
::= { ibNatPortBlockPrefix 1 }

ibNatPortBlockAllocFailRecoveryTrap NOTIFICATION-TYPE
OBJECTS
{
   ibNatTrapAddrGrpIndex,
   ibNatTrapAddrGrpChassis,
   ibNatTrapAddrGrpSlot,
   ibNatTrapAddrGrpCpu
}
STATUS current
DESCRIPTION
"Send traps when port blocks become available."
::= { ibNatPortBlockPrefix 2 }

ibNatPortAllocFailTrap NOTIFICATION-TYPE
OBJECTS
{
   ibNatTrapAddrGrpIndex,
   ibNatTrapUserIPType,
   ibNatTrapUserIP,
   ibNatTrapUserID,
   ibNatTrapAddrGrpMemberIP,
   ibNatTrapMemberIPPortNums,
   ibNatTrapAddrGrpChassis,
   ibNatTrapAddrGrpSlot,
   ibNatTrapAddrGrpCpu
}
STATUS current
DESCRIPTION
"Send traps when port resources are used up."
::= { ibNatPortBlockPrefix 3 }

ibNatPortAllocFailRecoveryTrap NOTIFICATION-TYPE
OBJECTS
{
   ibNatTrapAddrGrpIndex,
   ibNatTrapUserIPType,
   ibNatTrapUserIP,
   ibNatTrapUserID,
   ibNatTrapAddrGrpMemberIP,
   ibNatTrapMemberIPPortNums,
   ibNatTrapAddrGrpChassis,
   ibNatTrapAddrGrpSlot,
   ibNatTrapAddrGrpCpu
}
STATUS current
DESCRIPTION
"Send traps when port resources become available."
::= { ibNatPortBlockPrefix 4 }

ibNatPortUsageTrap NOTIFICATION-TYPE
OBJECTS
{
   ibNatTrapAddrGrpIndex,
   ibNatTrapUserIPType,
   ibNatTrapUserIP,
   ibNatTrapUserID,
   ibNatTrapAddrGrpMemberIP,
   ibNatTrapMemberIPPortNums,
   ibNatTrapPortAllocMode,
   ibNatTrapPortUsgProtocol,
   ibNatTrapPortUsgThreshold,
   ibNatTrapAddrGrpChassis,
   ibNatTrapAddrGrpSlot,
   ibNatTrapAddrGrpCpu
}
STATUS current
DESCRIPTION
"Send traps when the ratio of assigned ports reaching the port usage threshold."
::= { ibNatPortBlockPrefix 5 }

ibNatPortUsageRecoveryTrap NOTIFICATION-TYPE
OBJECTS
{
   ibNatTrapAddrGrpIndex,
   ibNatTrapUserIPType,
   ibNatTrapUserIP,
   ibNatTrapUserID,
   ibNatTrapAddrGrpMemberIP,
   ibNatTrapMemberIPPortNums,
   ibNatTrapPortAllocMode,
   ibNatTrapPortUsgProtocol,
   ibNatTrapPortUsgThreshold,
   ibNatTrapAddrGrpChassis,
   ibNatTrapAddrGrpSlot,
   ibNatTrapAddrGrpCpu
}
STATUS current
DESCRIPTION
"Send traps when the ratio of assigned ports is below 87.5% of the port usage threshold."
::= { ibNatPortBlockPrefix 6 }

ibNatPortBlockTrapInfo OBJECT IDENTIFIER ::= { ibNatPortBlockTraps 1 }
ibNatTrapAddrGrpIndex OBJECT-TYPE
   SYNTAX Integer32 (1..65536)
   MAX-ACCESS accessible-for-notify
   STATUS current
   DESCRIPTION
   "Index of the address group."
::= { ibNatPortBlockTrapInfo 1 }

ibNatTrapUserIPType OBJECT-TYPE
   SYNTAX InetAddressType
   MAX-ACCESS accessible-for-notify
   STATUS current
   DESCRIPTION
   "The type of user IP address."
::= { ibNatPortBlockTrapInfo 2 }

ibNatTrapUserIP OBJECT-TYPE
   SYNTAX InetAddress
   MAX-ACCESS accessible-for-notify
   STATUS current
   DESCRIPTION
   "User IP address."
::= { ibNatPortBlockTrapInfo 3 }

ibNatTrapUserID OBJECT-TYPE
   SYNTAX Integer32
   MAX-ACCESS accessible-for-notify
   STATUS current
   DESCRIPTION
   "User ID."
::= { ibNatPortBlockTrapInfo 4 }

ibNatTrapAddrGrpMemberIP OBJECT-TYPE
   SYNTAX IpAddress
   MAX-ACCESS accessible-for-notify
   STATUS current
   DESCRIPTION
   "Public network address."
::= { ibNatPortBlockTrapInfo 5 }

ibNatTrapMemberIPPortNums OBJECT-TYPE
   SYNTAX Integer32 (1..65536)
   MAX-ACCESS accessible-for-notify
   STATUS current
   DESCRIPTION
   "IP port numbers."
::= { ibNatPortBlockTrapInfo 6 }

ibNatTrapPortAllocMode OBJECT-TYPE
   SYNTAX INTEGER {
      cdm(1),
      eim(2)
   }
   MAX-ACCESS accessible-for-notify
   STATUS current
   DESCRIPTION
   "Public IP address port allocation mode."
::= { ibNatPortBlockTrapInfo 7 }

ibNatTrapPortUsgProtocol OBJECT-TYPE
   SYNTAX Integer32 (0..255)
   MAX-ACCESS accessible-for-notify
   STATUS current
   DESCRIPTION
   "The protocol type of public IP address port usage."
::= { ibNatPortBlockTrapInfo 8 }

ibNatTrapPortUsgThreshold OBJECT-TYPE
   SYNTAX Integer32
   MAX-ACCESS accessible-for-notify
   STATUS current
   DESCRIPTION
   "Port usage threshold."
::= { ibNatPortBlockTrapInfo 9 }

ibNatTrapAddrGrpChassis OBJECT-TYPE
   SYNTAX Integer32 (0..65534)
   MAX-ACCESS accessible-for-notify
   STATUS current
   DESCRIPTION
   "Chassis ID."
::= { ibNatPortBlockTrapInfo 10 }

ibNatTrapAddrGrpSlot OBJECT-TYPE
   SYNTAX Integer32 (0..65534)
   MAX-ACCESS accessible-for-notify
   STATUS current
   DESCRIPTION
   "Slot ID."
::= { ibNatPortBlockTrapInfo 11 }

ibNatTrapAddrGrpCpu OBJECT-TYPE
   SYNTAX Integer32 (0..7)
   MAX-ACCESS accessible-for-notify
   STATUS current
   DESCRIPTION
   "CPU ID."
::= { ibNatPortBlockTrapInfo 12 }

--Describe objects for nat abrupt trap
ibNatMonitor OBJECT IDENTIFIER ::= { ibNat 3}

ibNatTrapObjects OBJECT IDENTIFIER ::= { ibNatMonitor 0 }

ibNat444PortBlockOverTrap NOTIFICATION-TYPE
    OBJECTS{
    ibNatTrapChassis,
    ibNatTrapSlot,
    ibNatTrapCpu,
    ibNatAddrNum,
    ibNat444PortBlockCount,
    ibNat444PortBlockUseCount,
    ibNat444PortBlockUsage
    }
    STATUS current
    DESCRIPTION
        "This notification is generated when the port-block reaches the upper threshold is generated."
    ::= { ibNatTrapObjects 1}
ibNat444PortBlockBelowTrap NOTIFICATION-TYPE
    OBJECTS{
    ibNatTrapChassis,
    ibNatTrapSlot,
    ibNatTrapCpu,
    ibNatAddrNum,
    ibNat444PortBlockCount,
    ibNat444PortBlockUseCount,
    ibNat444PortBlockUsage
    }
    STATUS current
    DESCRIPTION
        "This notification is generated when the port-block returns to the upper threshold is generated."
    ::= { ibNatTrapObjects 2}
ibNatEIMOverTrap NOTIFICATION-TYPE
    OBJECTS{
    ibNatTrapChassis,
    ibNatTrapSlot,
    ibNatTrapCpu,
    ibNatAddrNum
    }
    STATUS current
    DESCRIPTION
        "This notification is generated when the EIM mode address resource is insufficient."
    ::= { ibNatTrapObjects 3}
ibNatEIMBelowTrap NOTIFICATION-TYPE
    OBJECTS{
    ibNatTrapChassis,
    ibNatTrapSlot,
    ibNatTrapCpu,
    ibNatAddrNum
    }
    STATUS current
    DESCRIPTION
        "This notification is generated when the EIM address returns to adequate."
    ::= { ibNatTrapObjects 4}
ibNatNoPatOverTrap NOTIFICATION-TYPE
    OBJECTS{
    ibNatTrapChassis,
    ibNatTrapSlot,
    ibNatTrapCpu,
    ibNatAddrNum
    }
    STATUS current
    DESCRIPTION
        "This notification is generated when the nat no-pat address reaches the upper thresholdd is generated."
    ::= { ibNatTrapObjects 5}
ibNatNoPatBelowTrap NOTIFICATION-TYPE
    OBJECTS{
    ibNatTrapChassis,
    ibNatTrapSlot,
    ibNatTrapCpu,
    ibNatAddrNum
    }
    STATUS current
    DESCRIPTION
        "This notification is generated when the nat no-pat address returns to the upper threshold is generated."
    ::= { ibNatTrapObjects 6}
ibNatNqaTrap NOTIFICATION-TYPE
    OBJECTS{
    ibNatTrapChassis,
    ibNatTrapSlot,
    ibNatTrapCpu,
    ibNatAddrNum,
    ibNatNqaAddr
    }
    STATUS current
    DESCRIPTION
        "This notification is generated when when NQA detects an unhealthy IP and is discharged from the address pool is generated."
    ::= { ibNatTrapObjects 7}
ibNatNqaExcessiveTrap NOTIFICATION-TYPE
    OBJECTS{
    ibNatTrapChassis,
    ibNatTrapSlot,
    ibNatTrapCpu,
    ibNatAddrNum
    }
    STATUS current
    DESCRIPTION
        "This notification is generated when when too many address ran out is generated."
    ::= { ibNatTrapObjects 8}
ibNatNqaBelowTrap NOTIFICATION-TYPE
    OBJECTS{
    ibNatTrapChassis,
    ibNatTrapSlot,
    ibNatTrapCpu,
    ibNatAddrNum
    }
    STATUS current
    DESCRIPTION
        "This notification is generated when address become available is generated."
    ::= { ibNatTrapObjects 9}
ibNatPortSplitTrap NOTIFICATION-TYPE
    OBJECTS{
    ibNatTrapChassis,
    ibNatTrapSlot,
    ibNatTrapCpu,
    ibNatConflictVar
    }
    STATUS current
    DESCRIPTION
        "This notification is generated when port block is in split mode."
    ::= { ibNatTrapObjects 10}
ibNatPortRecycleTrap NOTIFICATION-TYPE
    OBJECTS{
    ibNatTrapChassis,
    ibNatTrapSlot,
    ibNatTrapCpu,
    ibNatConflictVar
    }
    STATUS current
    DESCRIPTION
        "This notification is generated when port block is in recycle mode."
    ::= { ibNatTrapObjects 11}

ibNatTrapValues OBJECT IDENTIFIER ::= { ibNatMonitor 1 }
ibNatTrapChassis OBJECT-TYPE
    SYNTAX      Unsigned32
    MAX-ACCESS  accessible-for-notify
    STATUS      current
    DESCRIPTION
        "An IRF member device ID."
    ::= { ibNatTrapValues 1}
ibNatTrapSlot OBJECT-TYPE
    SYNTAX      Unsigned32
    MAX-ACCESS  accessible-for-notify
    STATUS      current
    DESCRIPTION
        "The slot where the card resides."
    ::= { ibNatTrapValues 2 }
ibNatTrapCpu OBJECT-TYPE
    SYNTAX      Unsigned32
    MAX-ACCESS  accessible-for-notify
    STATUS      current
    DESCRIPTION
        "CPU ID."
    ::= { ibNatTrapValues 3 }
ibNatAddrNum OBJECT-TYPE
    SYNTAX Unsigned32 (0..65535)
    MAX-ACCESS accessible-for-notify
    STATUS current
    DESCRIPTION
        "The number of address-group."
    ::= { ibNatTrapValues 4 }
ibNat444PortBlockCount OBJECT-TYPE
    SYNTAX Unsigned32 (1..4294967295)
    MAX-ACCESS accessible-for-notify
    STATUS current
    DESCRIPTION
        "The number of address-group."
    ::= { ibNatTrapValues 5 }
ibNat444PortBlockUseCount OBJECT-TYPE
    SYNTAX Unsigned32 (1..4294967295)
    MAX-ACCESS accessible-for-notify
    STATUS current
    DESCRIPTION
        "The number of address-group."
    ::= { ibNatTrapValues 6 }
ibNat444PortBlockUsage OBJECT-TYPE
    SYNTAX Unsigned32 (0..100)
    MAX-ACCESS accessible-for-notify
    STATUS current
    DESCRIPTION
        "The number of address-group."
    ::= { ibNatTrapValues 7 }
ibNatNqaAddr OBJECT-TYPE
    SYNTAX IpAddress
    MAX-ACCESS accessible-for-notify
    STATUS current
    DESCRIPTION
        "The addresses of nqa excluded."
    ::= { ibNatTrapValues 8 }
ibNatConflictVar OBJECT-TYPE
    SYNTAX OCTET STRING(SIZE(0..256))
    MAX-ACCESS accessible-for-notify
    STATUS current
    DESCRIPTION
        "The string description port assignment status."
    ::= { ibNatTrapValues 9 }

END
