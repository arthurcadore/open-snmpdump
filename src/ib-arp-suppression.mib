-- ============================================================================
-- Copyright (C) 2023 Intelbras S.A. All rights reserved.
--
-- Description: The purpose of this MIB file is to provide the definition of
--              the ARP suppression feature.
-- Reference:
-- Version: V1.0
-- History:
-- V1.0 2022-02-08
--   Initial version, created by qiankangkang
-- ============================================================================

IB-ARP-SUPPRESSION-MIB DEFINITIONS ::= BEGIN

IMPORTS
        ibCommon
    FROM IB-OID-MIB
        IpAddress, Unsigned32, OBJECT-TYPE, MODULE-IDENTITY
    FROM SNMPv2-SMI
        DisplayString, MacAddress
    FROM SNMPv2-TC;

-- Node definitions
ibARPSuppression MODULE-IDENTITY
    LAST-UPDATED "202202071800Z"        -- FEB 07, 2022 at 18:00 GMT
    ORGANIZATION
        "Intelbras S.A. Industria de Telecomunicacao Eletronica Brasileria."
    CONTACT-INFO
        ""
    DESCRIPTION
        "This MIB file defines the ARP suppression feature only."
    REVISION "202202071800Z"
    DESCRIPTION
        "The initial version of this MIB file."
    ::= { ibCommon 220}

ibARPSuppressionVsiTable  OBJECT-TYPE
    SYNTAX      SEQUENCE OF IbARPSuppressionVsiEntry
    MAX-ACCESS  not-accessible
    STATUS      current
    DESCRIPTION
        "A table for ARP Vsi suppression."
    ::= { ibARPSuppression 1 }

ibARPSuppressionVsiEntry  OBJECT-TYPE
    SYNTAX      IbARPSuppressionVsiEntry
    MAX-ACCESS  not-accessible
    STATUS      current
    DESCRIPTION
        "The ARP Vsi suppression entry info."
    INDEX
    {
        ibARPSuppressionChassis,
        ibARPSuppressionSlot,
        ibARPSuppressionVsiName,
        ibARPSuppressionIpAddr
    }
    ::= { ibARPSuppressionVsiTable 1 }

IbARPSuppressionVsiEntry ::=
    SEQUENCE
    {
        ibARPSuppressionChassis           Unsigned32,
        ibARPSuppressionSlot              Unsigned32,
        ibARPSuppressionVsiName           DisplayString,
        ibARPSuppressionIpAddr            IpAddress,
        ibARPSuppressionMacAddr           MacAddress,
        ibARPSuppressionLinkID            Unsigned32,
        ibARPSuppressionAging             Unsigned32
    }


ibARPSuppressionChassis    OBJECT-TYPE
    SYNTAX      Unsigned32
    MAX-ACCESS  not-accessible
    STATUS      current
    DESCRIPTION
        "The chassis ID of ARP Vsi suppression.If the device is not a stacked device,
         the value is 65535.
        ."
    ::= { ibARPSuppressionVsiEntry 1 }

ibARPSuppressionSlot    OBJECT-TYPE
    SYNTAX      Unsigned32
    MAX-ACCESS  not-accessible
    STATUS      current
    DESCRIPTION
        "The slot ID of ARP Vsi suppression."
    ::= { ibARPSuppressionVsiEntry 2 }

ibARPSuppressionVsiName    OBJECT-TYPE
    SYNTAX      DisplayString(SIZE (1..32))
    MAX-ACCESS  not-accessible
    STATUS      current
    DESCRIPTION
        "The vsi name of ARP Vsi suppression."
    ::= { ibARPSuppressionVsiEntry 3 }

ibARPSuppressionIpAddr    OBJECT-TYPE
    SYNTAX      IpAddress
    MAX-ACCESS  not-accessible
    STATUS      current
    DESCRIPTION
        "The ip address of ARP Vsi suppression."
    ::= { ibARPSuppressionVsiEntry 4 }

ibARPSuppressionMacAddr    OBJECT-TYPE
    SYNTAX      MacAddress
    MAX-ACCESS  read-only
    STATUS      current
    DESCRIPTION
        "The mac address of ARP Vsi suppression."
    ::= { ibARPSuppressionVsiEntry 5 }

ibARPSuppressionLinkID    OBJECT-TYPE
    SYNTAX      Unsigned32
    MAX-ACCESS  read-only
    STATUS      current
    DESCRIPTION
        "The link ID of ARP Vsi suppression."
    ::= { ibARPSuppressionVsiEntry 6 }

ibARPSuppressionAging    OBJECT-TYPE
    SYNTAX      Unsigned32
    UNITS       "minutes"
    MAX-ACCESS  read-only
    STATUS      current
    DESCRIPTION
        "The aging time of ARP Vsi suppression."
    ::= { ibARPSuppressionVsiEntry 7 }

END
