-- =============================================================================
-- Copyright (C) 2023 Intelbras S.A. All rights reserved.
--
-- Description:
--   The file defines a MIB to provide spectrum analysis information.
-- Reference:
-- Version: V1.0
-- History:
--   V1.0 Created by Wang Lu
--     Initial version 2011-08-05
-- =============================================================================
IB-DOT11-SA-MIB DEFINITIONS ::= BEGIN

IMPORTS
        TruthValue,
        DateAndTime
    FROM SNMPv2-TC
        MODULE-IDENTITY,
        Integer32, Unsigned32, OBJECT-TYPE, NOTIFICATION-TYPE
    FROM SNMPv2-SMI
        ibDot11,
        IbDot11ChannelScopeType,
        IbDot11ObjectIDType,
        IbDot11RadioScopeType,
        IbDot11SaIntfDevType
    FROM IB-DOT11-REF-MIB;

ibDot11Sa MODULE-IDENTITY
    LAST-UPDATED "201108262000Z"        -- Aug 26, 2011 at 20:00 GMT
    ORGANIZATION
        "Intelbras S.A. Industria de Telecomunicacao Eletronica Brasileria."
    CONTACT-INFO
        ""
    DESCRIPTION
        "This MIB module provides spectrum analysis information.
        The initial revision of this MIB module.

        The spectrum analysis module on APs is able to examine the radio
        frequency (RF) environment in which the Wi-Fi network is operating,
        identify interference and classify its sources. An analysis of the
        results can then be used to quickly isolate issues with packet
        transmission, channel quality, and traffic congestion caused by
        contention with other devices operating in the same band or channel."
    REVISION "201108262000Z"
    DESCRIPTION
        "The initial revision of this MIB module."
    ::= { ibDot11 13 }

-- *****************************************************************************
-- *  Major sections
-- *****************************************************************************

ibDot11SaCfgGroup OBJECT IDENTIFIER  ::= { ibDot11Sa 1 }
ibDot11SaStatusGroup OBJECT IDENTIFIER  ::= { ibDot11Sa 2 }
ibDot11SaNotifyGroup OBJECT IDENTIFIER  ::= { ibDot11Sa 3 }

-- cfg table
ibDot11SaCfgTable OBJECT-TYPE
    SYNTAX SEQUENCE OF IbDot11SaCfgEntry
    MAX-ACCESS not-accessible
    STATUS current
    DESCRIPTION
        "This table is used to configure spectrum analysis."
    ::= { ibDot11SaCfgGroup 1 }

ibDot11SaCfgEntry OBJECT-TYPE
    SYNTAX IbDot11SaCfgEntry
    MAX-ACCESS not-accessible
    STATUS current
    DESCRIPTION
        "This entry contains the spectrum analysis configuration."
    INDEX { ibDot11SaCfgRadioType }
    ::= { ibDot11SaCfgTable 1 }

IbDot11SaCfgEntry ::= SEQUENCE
    {
        ibDot11SaCfgRadioType       INTEGER,
        ibDot11SaEnable             TruthValue,
        ibDot11SaRptDevType         BITS,
        ibDot11SaTrapDevEnable      TruthValue,
        ibDot11SaTrapDevType        BITS,
        ibDot11SaTrapAQEnable       TruthValue,
        ibDot11SaTrapAQThreshold    Integer32,
        ibDot11SaDrivenRRMEnable    TruthValue,
        ibDot11SaDrivenRRMSnt       INTEGER
    }

ibDot11SaCfgRadioType OBJECT-TYPE
    SYNTAX INTEGER
    {
        dot11bg(1),
        dot11a(2)
    }
    MAX-ACCESS not-accessible
    STATUS current
    DESCRIPTION
        "Represents the radio type of the configuration."
    ::= { ibDot11SaCfgEntry 1 }

ibDot11SaEnable OBJECT-TYPE
    SYNTAX TruthValue
    MAX-ACCESS read-write
    STATUS current
    DESCRIPTION
        "Represents whether spectrum analysis is enabled globally."
    ::= { ibDot11SaCfgEntry 2 }

ibDot11SaRptDevType OBJECT-TYPE
    SYNTAX BITS
        {
            microwave(0),
            microwaveInverter(1),
            bluetooth(2),
            fixedFreqOthers(3),
            fixedFreqCordlessPhone(4),
            fixedFreqVideo(5),
            fixedFreqAudio(6),
            freqHopperOthers(7),
            freqHopperCordlessBase(8),
            freqHopperCordlessNetwork(9),
            freqHopperXbox(10),
            genericInterferer(11)
        }
    MAX-ACCESS read-write
    STATUS current
    DESCRIPTION
        "Represents which types of interference devices should be reported."
    ::= { ibDot11SaCfgEntry 3 }

ibDot11SaTrapDevEnable OBJECT-TYPE
    SYNTAX TruthValue
    MAX-ACCESS read-write
    STATUS current
    DESCRIPTION
        "Represents whether the interference device trap is enabled."
    ::= { ibDot11SaCfgEntry 4 }

ibDot11SaTrapDevType OBJECT-TYPE
    SYNTAX BITS
        {
            microwave(0),
            microwaveInverter(1),
            bluetooth(2),
            fixedFreqOthers(3),
            fixedFreqCordlessPhone(4),
            fixedFreqVideo(5),
            fixedFreqAudio(6),
            freqHopperOthers(7),
            freqHopperCordlessBase(8),
            freqHopperCordlessNetwork(9),
            freqHopperXbox(10),
            genericInterferer(11)
        }
    MAX-ACCESS read-write
    STATUS current
    DESCRIPTION
        "Represents which types of interference device will send traps
         when the interference device trap is enabled."
    ::= { ibDot11SaCfgEntry 5 }

ibDot11SaTrapAQEnable OBJECT-TYPE
    SYNTAX TruthValue
    MAX-ACCESS read-write
    STATUS current
    DESCRIPTION
        "Represents whether the air quality trap is enabled."
    ::= { ibDot11SaCfgEntry 6 }

ibDot11SaTrapAQThreshold OBJECT-TYPE
    SYNTAX Integer32(1..100)
    MAX-ACCESS read-write
    STATUS current
    DESCRIPTION
        "Represents the air quality trap threshold.  When the air quality
        is below this value, the air quality trap will be sent."
    ::= { ibDot11SaCfgEntry 7 }

ibDot11SaDrivenRRMEnable OBJECT-TYPE
    SYNTAX TruthValue
    MAX-ACCESS read-write
    STATUS current
    DESCRIPTION
        "Configure whether to trigger RRM to run when an access point detects
         a certain level of interference."
    ::= { ibDot11SaCfgEntry 8 }

ibDot11SaDrivenRRMSnt OBJECT-TYPE
    SYNTAX INTEGER
    {
        low(1),
        medium(2),
        high(3)
    }
    MAX-ACCESS read-write
    STATUS current
    DESCRIPTION
        "Configure the threshold at which RRM will be triggered.  When the
         interference level for the access point rises above the threshold
         level, RRM initiates a local dynamic channel assignment (DCA) run
         and changes the channel of the affected access point radio if
         possible to improve network performance.  Low represents a decreased
         sensitivity to changes in the environment while high represents an
         increased sensitivity."
    ::= { ibDot11SaCfgEntry 9 }

-- fft table
ibDot11SaRtFFTDataTable OBJECT-TYPE
    SYNTAX SEQUENCE OF IbDot11SaRtFFTDataEntry
    MAX-ACCESS not-accessible
    STATUS current
    DESCRIPTION
        "This table contains the real-time FFT data for spectrum analysis."
    ::= { ibDot11SaStatusGroup 1 }

ibDot11SaRtFFTDataEntry OBJECT-TYPE
    SYNTAX IbDot11SaRtFFTDataEntry
    MAX-ACCESS not-accessible
    STATUS current
    DESCRIPTION
        "This entry contains the real-time FFT data for spectrum analysis."
    INDEX
        {
            ibDot11SaAPID,
            ibDot11SaRadioID,
            ibDot11SaRtDataGroupID,
            ibDot11SaFrequency
        }
    ::= { ibDot11SaRtFFTDataTable 1 }

IbDot11SaRtFFTDataEntry ::= SEQUENCE
    {
        ibDot11SaAPID               IbDot11ObjectIDType,
        ibDot11SaRadioID            IbDot11RadioScopeType,
        ibDot11SaRtDataGroupID      Integer32,
        ibDot11SaFrequency          Integer32,
        ibDot11SaRtFreqPower        Integer32,
        ibDot11SaRtFreqMaxPower     Integer32,
        ibDot11SaRtFreqDutyCycle    Integer32,
        ibDot11SaRtFreqDataSeqNo    Unsigned32
    }

ibDot11SaAPID OBJECT-TYPE
    SYNTAX IbDot11ObjectIDType
    MAX-ACCESS not-accessible
    STATUS current
    DESCRIPTION
        "Represents the serial ID of the AP."
    ::= { ibDot11SaRtFFTDataEntry 1 }

ibDot11SaRadioID OBJECT-TYPE
    SYNTAX IbDot11RadioScopeType
    MAX-ACCESS not-accessible
    STATUS current
    DESCRIPTION
        "Represents the ID of the radio."
    ::= { ibDot11SaRtFFTDataEntry 2 }

ibDot11SaRtDataGroupID OBJECT-TYPE
    SYNTAX Integer32
    MAX-ACCESS not-accessible
    STATUS current
    DESCRIPTION
        "Represents group ID of the collected data.  Maybe the device collects
         multiple groups of data at the collected interval."
    ::= { ibDot11SaRtFFTDataEntry 3 }

ibDot11SaFrequency OBJECT-TYPE
    SYNTAX Integer32
    MAX-ACCESS not-accessible
    STATUS current
    DESCRIPTION
        "Represents the frequency number in 100 Hz."
    ::= { ibDot11SaRtFFTDataEntry 4 }

ibDot11SaRtFreqPower OBJECT-TYPE
    SYNTAX Integer32
    MAX-ACCESS read-only
    STATUS current
    DESCRIPTION
        "Represents the power of the frequency point."
    ::= { ibDot11SaRtFFTDataEntry 5 }

ibDot11SaRtFreqMaxPower OBJECT-TYPE
    SYNTAX Integer32
    MAX-ACCESS read-only
    STATUS current
    DESCRIPTION
        "Represents the max power of the frequency point."
    ::= { ibDot11SaRtFFTDataEntry 6 }

ibDot11SaRtFreqDutyCycle OBJECT-TYPE
    SYNTAX Integer32
    MAX-ACCESS read-only
    STATUS current
    DESCRIPTION
        "Represents the duty cycle of the frequency point."
    ::= { ibDot11SaRtFFTDataEntry 7 }

ibDot11SaRtFreqDataSeqNo OBJECT-TYPE
    SYNTAX Unsigned32
    MAX-ACCESS read-only
    STATUS current
    DESCRIPTION
        "Represents the sequence number of the data."
    ::= { ibDot11SaRtFFTDataEntry 8 }

-- interfering device table
ibDot11SaIntfDevTable OBJECT-TYPE
    SYNTAX SEQUENCE OF IbDot11SaIntfDevEntry
    MAX-ACCESS not-accessible
    STATUS current
    DESCRIPTION
        "This table contains the information of the interfering devices."
    ::= { ibDot11SaStatusGroup 2 }

ibDot11SaIntfDevEntry OBJECT-TYPE
    SYNTAX IbDot11SaIntfDevEntry
    MAX-ACCESS not-accessible
    STATUS current
    DESCRIPTION
        "This entry contains the information of the interfering devices."
    INDEX
        {
            ibDot11SaAPID,
            ibDot11SaRadioID,
            ibDot11SaDevID
        }
    ::= { ibDot11SaIntfDevTable 1 }

IbDot11SaIntfDevEntry ::= SEQUENCE
    {
        ibDot11SaDevID              Integer32,
        ibDot11SaDevType            IbDot11SaIntfDevType,
        ibDot11SaDevSI              Integer32,
        ibDot11SaDevRSSI            Integer32,
        ibDot11SaDevDutyCycle       Integer32,
        ibDot11SaDevAffectedChls    OCTET STRING,
        ibDot11SaDevDetectedTime    DateAndTime
    }

ibDot11SaDevID OBJECT-TYPE
    SYNTAX Integer32
    MAX-ACCESS not-accessible
    STATUS current
    DESCRIPTION
        "Represents the device identification number that uniquely
         identified the interfering device."
    ::= { ibDot11SaIntfDevEntry 1 }

ibDot11SaDevType OBJECT-TYPE
    SYNTAX IbDot11SaIntfDevType
    MAX-ACCESS read-only
    STATUS current
    DESCRIPTION
        "Represents type of the interferer."
    ::= { ibDot11SaIntfDevEntry 2 }

ibDot11SaDevSI OBJECT-TYPE
    SYNTAX Integer32
    MAX-ACCESS read-only
    STATUS current
    DESCRIPTION
        "Represents severity index of the interfering device.  Severity index
         is calculated, a positive integer between 0 and 100(with 100 being the
         most severe)."
    ::= { ibDot11SaIntfDevEntry 3 }

ibDot11SaDevRSSI OBJECT-TYPE
    SYNTAX Integer32
    MAX-ACCESS read-only
    STATUS current
    DESCRIPTION
        "Represents receive signal strength indicator (RSSI) of interfering
         device."
    ::= { ibDot11SaIntfDevEntry 4 }

ibDot11SaDevDutyCycle OBJECT-TYPE
    SYNTAX Integer32
    MAX-ACCESS read-only
    STATUS current
    DESCRIPTION
        "Represents proportion of time in percentage during which the
         interfering device was active."
    ::= { ibDot11SaIntfDevEntry 5 }

ibDot11SaDevAffectedChls OBJECT-TYPE
    SYNTAX OCTET STRING
    MAX-ACCESS read-only
    STATUS current
    DESCRIPTION
        "Represents channels that the interfering device affects."
    ::= { ibDot11SaIntfDevEntry 6 }

ibDot11SaDevDetectedTime OBJECT-TYPE
    SYNTAX DateAndTime
    MAX-ACCESS read-only
    STATUS current
    DESCRIPTION
        "Represents time at which the interference was detected."
    ::= { ibDot11SaIntfDevEntry 7 }

-- air quality table
ibDot11SaAirQualityTable OBJECT-TYPE
    SYNTAX SEQUENCE OF IbDot11SaAirQualityEntry
    MAX-ACCESS not-accessible
    STATUS current
    DESCRIPTION
        "This table contains the air quality of the channels."
    ::= { ibDot11SaStatusGroup 3 }

ibDot11SaAirQualityEntry OBJECT-TYPE
    SYNTAX IbDot11SaAirQualityEntry
    MAX-ACCESS not-accessible
    STATUS current
    DESCRIPTION
        "This entry contains the air quality of the channels."
    INDEX
        {
            ibDot11SaAPID,
            ibDot11SaRadioID,
            ibDot11SaChlNum
        }
    ::= { ibDot11SaAirQualityTable 1 }

IbDot11SaAirQualityEntry ::= SEQUENCE
    {
        ibDot11SaChlNum             IbDot11ChannelScopeType,
        ibDot11SaAvgQuality         Integer32,
        ibDot11SaMinQuality         Integer32,
        ibDot11SaIntfDevNum         Integer32,
        ibDot11SaWiFiUtil           Integer32,
        ibDot11SaNonWiFiUtil        Integer32,
        ibDot11SaNoiseFloor         Integer32
    }

ibDot11SaChlNum OBJECT-TYPE
    SYNTAX IbDot11ChannelScopeType
    MAX-ACCESS not-accessible
    STATUS current
    DESCRIPTION
        "Represents the radio channel where the air quality is monitored."
    ::= { ibDot11SaAirQualityEntry 1 }

ibDot11SaAvgQuality OBJECT-TYPE
    SYNTAX Integer32
    MAX-ACCESS read-only
    STATUS current
    DESCRIPTION
        "Represents the average air quality for this radio channel."
    ::= { ibDot11SaAirQualityEntry 2 }

ibDot11SaMinQuality OBJECT-TYPE
    SYNTAX Integer32
    MAX-ACCESS read-only
    STATUS current
    DESCRIPTION
        "Represents the minimum air quality for this radio channel."
    ::= { ibDot11SaAirQualityEntry 3 }

ibDot11SaIntfDevNum OBJECT-TYPE
    SYNTAX Integer32
    MAX-ACCESS read-only
    STATUS current
    DESCRIPTION
        "Represents the number of interferers detected by the radios
         on the 802.11a/n or 802.11b/g/n radio band."
    ::= { ibDot11SaAirQualityEntry 4 }

ibDot11SaWiFiUtil OBJECT-TYPE
    SYNTAX Integer32
    MAX-ACCESS read-only
    STATUS current
    DESCRIPTION
        "Represents the percentage of the channel currently being
         used by Wi-Fi devices."
    ::= { ibDot11SaAirQualityEntry 5 }

ibDot11SaNonWiFiUtil OBJECT-TYPE
    SYNTAX Integer32
    MAX-ACCESS read-only
    STATUS current
    DESCRIPTION
        "Represents the percentage of the channel currently being
         used by non-Wi-Fi interference."
    ::= { ibDot11SaAirQualityEntry 6 }

ibDot11SaNoiseFloor OBJECT-TYPE
    SYNTAX Integer32
    MAX-ACCESS read-only
    STATUS current
    DESCRIPTION
        "Represents current noise floor recorded on the channel."
    ::= { ibDot11SaAirQualityEntry 7 }

--Notify Group
ibDot11SaTraps OBJECT IDENTIFIER  ::= { ibDot11SaNotifyGroup 0 }
ibDot11SaIntfDevDetected NOTIFICATION-TYPE
    OBJECTS
        {
            ibDot11SaTrapAPID,
            ibDot11SaTrapRadioID,
            ibDot11SaTrapDevID,
            ibDot11SaTrapIntfDevType,
            ibDot11APTrapDevSI,
            ibDot11SaTrapDevRSSI,
            ibDot11APTrapDevDC,
            ibDot11APTrapDevChls,
            ibDot11APTrapDevDctTime
        }
    STATUS current
    DESCRIPTION
        "Interfering device is detected."
    ::= { ibDot11SaTraps 1 }

ibDot11SaIntfDevDisappear NOTIFICATION-TYPE
    OBJECTS
        {
            ibDot11SaTrapAPID,
            ibDot11SaTrapRadioID,
            ibDot11SaTrapDevID,
            ibDot11SaTrapIntfDevType
        }
    STATUS current
    DESCRIPTION
        "Interfering device disappeared."
    ::= { ibDot11SaTraps 2 }

ibDot11SaChlQltLow NOTIFICATION-TYPE
    OBJECTS
        {
            ibDot11SaTrapAPID,
            ibDot11SaTrapRadioID,
            ibDot11SaTrapChlNum,
            ibDot11SaTrapChlQlt,
            ibDot11SaTrapChlIntfNum
        }
    STATUS current
    DESCRIPTION
        "The quality of the channel is below the specified threshold."
    ::= { ibDot11SaTraps 3 }

ibDot11SaChlQltRecover NOTIFICATION-TYPE
    OBJECTS
        {
            ibDot11SaTrapAPID,
            ibDot11SaTrapRadioID,
            ibDot11SaTrapChlNum,
            ibDot11SaTrapChlQlt,
            ibDot11SaTrapChlIntfNum
        }
    STATUS current
    DESCRIPTION
        "The quality of the channel recovered from low status."
    ::= { ibDot11SaTraps 4 }

ibDot11SaTrapVars OBJECT IDENTIFIER  ::= { ibDot11SaNotifyGroup 1 }

ibDot11SaTrapAPID OBJECT-TYPE
    SYNTAX      IbDot11ObjectIDType
    MAX-ACCESS  accessible-for-notify
    STATUS      current
    DESCRIPTION
        "Represents the identifier of the AP."
    ::= { ibDot11SaTrapVars 1 }

ibDot11SaTrapRadioID OBJECT-TYPE
    SYNTAX      IbDot11RadioScopeType
    MAX-ACCESS  accessible-for-notify
    STATUS      current
    DESCRIPTION
        "Represents the identifier of the radio."
    ::= { ibDot11SaTrapVars 2 }

ibDot11SaTrapDevID OBJECT-TYPE
    SYNTAX Integer32
    MAX-ACCESS accessible-for-notify
    STATUS current
    DESCRIPTION
        "Represents the device identification number that uniquely
         identified the interfering device."
    ::= { ibDot11SaTrapVars 3 }

ibDot11SaTrapIntfDevType OBJECT-TYPE
    SYNTAX IbDot11SaIntfDevType
    MAX-ACCESS accessible-for-notify
    STATUS current
    DESCRIPTION
        "Represents type of the interferer."
    ::= { ibDot11SaTrapVars 4 }

ibDot11APTrapDevSI OBJECT-TYPE
    SYNTAX Integer32
    MAX-ACCESS accessible-for-notify
    STATUS current
    DESCRIPTION
        "Represents severity index of the interfering device.  Severity index
         is calculated, a positive integer between 0 and 100(with 100 being the
         most severe)."
    ::= { ibDot11SaTrapVars 5 }

ibDot11SaTrapDevRSSI OBJECT-TYPE
    SYNTAX Integer32
    MAX-ACCESS accessible-for-notify
    STATUS current
    DESCRIPTION
        "Represents receive signal strength indicator (RSSI) of interfering
         device."
    ::= { ibDot11SaTrapVars 6 }

ibDot11APTrapDevDC OBJECT-TYPE
    SYNTAX Integer32
    MAX-ACCESS accessible-for-notify
    STATUS current
    DESCRIPTION
        "Represents proportion of time in percentage during which the
         interfering device was active."
    ::= { ibDot11SaTrapVars 7 }

ibDot11APTrapDevChls OBJECT-TYPE
    SYNTAX OCTET STRING
    MAX-ACCESS accessible-for-notify
    STATUS current
    DESCRIPTION
        "Represents channels that the interfering device affects."
    ::= { ibDot11SaTrapVars 8 }

ibDot11APTrapDevDctTime OBJECT-TYPE
    SYNTAX DateAndTime
    MAX-ACCESS accessible-for-notify
    STATUS current
    DESCRIPTION
        "Represents time at which the interference was detected."
    ::= { ibDot11SaTrapVars 9 }

ibDot11SaTrapChlNum OBJECT-TYPE
    SYNTAX IbDot11ChannelScopeType
    MAX-ACCESS accessible-for-notify
    STATUS current
    DESCRIPTION
        "Represents the radio channel where the air quality is monitored."
    ::= { ibDot11SaTrapVars 10 }

ibDot11SaTrapChlQlt OBJECT-TYPE
    SYNTAX Integer32
    MAX-ACCESS accessible-for-notify
    STATUS current
    DESCRIPTION
        "Represents the quality for this radio channel."
    ::= { ibDot11SaTrapVars 11 }

ibDot11SaTrapChlIntfNum OBJECT-TYPE
    SYNTAX Integer32
    MAX-ACCESS accessible-for-notify
    STATUS current
    DESCRIPTION
        "Represents the number of interferers detected by the radios
         on the 802.11a/n or 802.11b/g/n radio band."
    ::= { ibDot11SaTrapVars 12 }
END
