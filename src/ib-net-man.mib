-- ==========================================================================
-- Copyright (C) 2023 Intelbras S.A. All rights reserved.
--
-- Description: The purpose of this MIB file is to provide object definition
--              of network management parameters.
-- Reference:
-- Version: V1.0
-- History:
-- V1.0 2008-04-16 Initial version, created by Longyin
-- ==========================================================================
IB-NET-MAN-MIB DEFINITIONS ::= BEGIN

IMPORTS
        OBJECT-TYPE, MODULE-IDENTITY, NOTIFICATION-TYPE
    FROM SNMPv2-SMI
        OBJECT-GROUP, MODULE-COMPLIANCE, NOTIFICATION-GROUP
    FROM SNMPv2-CONF
        InetAddressType, InetAddress
    FROM INET-ADDRESS-MIB
        ibCommon
    FROM IB-OID-MIB;

ibNetMan MODULE-IDENTITY
    LAST-UPDATED "200804161700Z"
    ORGANIZATION
        "Intelbras S.A. Industria de Telecomunicacao Eletronica Brasileria."
    CONTACT-INFO
        ""
    DESCRIPTION
        "This MIB file is to provide the object definition of the network
        management parameters.  These parameters are used to identify devices.
        It is useful for devices management in a dynamic address assignment
        network."
    REVISION "200804161700Z"
    DESCRIPTION
        "The initial version of this MIB file."
    ::= { ibCommon 90 }

--
-- Object definitions
--
ibNMConfigObjects OBJECT IDENTIFIER ::= { ibNetMan 1 }

ibNMMonitorObjects OBJECT IDENTIFIER ::= { ibNetMan 2 }

ibNMNotify OBJECT IDENTIFIER ::= { ibNetMan 3 }

-- Scalar Objects for Notify
ibNMNotifyScalarObjects OBJECT IDENTIFIER ::= { ibNMNotify 1 }

ibNMIpAddressType OBJECT-TYPE
    SYNTAX      InetAddressType
    MAX-ACCESS  accessible-for-notify
    STATUS      current
    DESCRIPTION
        "The IP address type of specified interface on the device."
    ::= { ibNMNotifyScalarObjects 1 }

ibNMIpAddress OBJECT-TYPE
    SYNTAX      InetAddress
    MAX-ACCESS  accessible-for-notify
    STATUS      current
    DESCRIPTION
        "The IP address of specified interface on the device."
    ::= { ibNMNotifyScalarObjects 2 }

ibNMCustomBuildInfo OBJECT-TYPE
    SYNTAX      OCTET STRING(SIZE(0..64))
    MAX-ACCESS  read-only
    STATUS      current
    DESCRIPTION
        "The customer-required information of devices, for example,
        OUI (Organizational Unique Identifier)."
    ::= { ibNMNotifyScalarObjects 3 }

ibNMSerialNum OBJECT-TYPE
    SYNTAX      OCTET STRING(SIZE(0..64))
    MAX-ACCESS  accessible-for-notify
    STATUS      current
    DESCRIPTION
        "The serial number used by NMS (Network Management Station) for
        mapping IP address and device."
    ::= { ibNMNotifyScalarObjects 4 }

-- Notification Objects
ibNMNotifyObjects OBJECT IDENTIFIER ::= { ibNMNotify 2 }

ibNMNotifyObjectsPrefix OBJECT IDENTIFIER ::= { ibNMNotifyObjects 0 }

ibIpAddrChangeNotify NOTIFICATION-TYPE
    OBJECTS
        {
            ibNMIpAddressType,
            ibNMIpAddress,
            ibNMCustomBuildInfo,
            ibNMSerialNum
        }
    STATUS      current
    DESCRIPTION
        "This notification will be generated when the IP address of active
        management interface is changed.  The change maybe originate from NMS,
        DHCP server or administrator.

        The management interfaces are the interfaces that assigned by
        administrator, which can be used to manage device, but may be inactive
        for link fault or IP address (IPv4 or IPv6) missing.

        The active management interface means an active interface, the IP
        address of which can be used for network management.

        This notification announces useful management IP address change.  So it
        is triggered by significative IP address change.

        Suppose that two management interfaces on a device, Interface-A and
        Interface-B.  Initially both interfaces are down and assigned no IP
        address. Configure Interface-A as the primary monitored interface,
        Interface-B as the secondary.

        Significative IP address change in following cases:
        1. If Interface-A is assigned an IP address primarily, and it is linking
        up, then Interface-B will be ignored.  A notification will be triggered,
        appending IP address of Interface-A.

        2. If Interface-B is assigned an IP address primarily, and it is linking
        up, then Interface-A will be ignored.  A notification will be triggered,
        appending IP address of Interface-B.

        3. If IP address of that interface, which had its IP address announced
        to NMS, is changed since last notification triggered, then another
        notification will be sent to NMS.

        4. Suppore that Interface-A was linked up and assigned an IP address
        primarily.  If for some unknown reason, Interface-A is down or loses IP
        address, and Interface-B is assigned an IP address which is different
        with that announced to NMS before, then a notification will be
        triggered, appending the new IP address that Interface-B assigned.

        5. A notification appending new IP address that Interface-A assigned
        will be triggered, if 4 occurs to Interface-B."

    ::= { ibNMNotifyObjectsPrefix 1 }

-- Compliances Objects
ibNetManConformance OBJECT IDENTIFIER ::= { ibNetMan 4 }

ibNetManCompliances OBJECT IDENTIFIER ::= { ibNetManConformance 1 }

ibNetManCompliance MODULE-COMPLIANCE
    STATUS      current
    DESCRIPTION
        "The statement of compliance for those implementing
        the network management MIB."
    MODULE
        MANDATORY-GROUPS
        {
            ibNMMonitorGroup,
            ibNMNotificationGroup
        }
    ::= { ibNetManCompliances 1 }

ibNetManGroups OBJECT IDENTIFIER ::= { ibNetManConformance 2 }

ibNMMonitorGroup OBJECT-GROUP
    OBJECTS
        {
            ibNMIpAddressType,
            ibNMIpAddress,
            ibNMCustomBuildInfo,
            ibNMSerialNum
        }
    STATUS current
    DESCRIPTION
        "A collection of objects in net management monitor group."
    ::= { ibNetManGroups 1 }

ibNMNotificationGroup NOTIFICATION-GROUP
    NOTIFICATIONS
        {
            ibIpAddrChangeNotify
        }
    STATUS      current
    DESCRIPTION
         "A collection of objects in net management notification group."
    ::= { ibNetManGroups 2 }

END
