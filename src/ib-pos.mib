-- ==========================================================================
-- Copyright (C) 2023 Intelbras S.A. All rights reserved.
--
-- Description: The purpose of this MIB file is to provide the define of
--              POS MIB of serial router.
-- Reference:
-- Version: V1.1
-- History:
-- V1.0  The initial version, created by wangshijin 2004-07-02
-- V1.1  Refined this MIB which is completely conform with SMIv2.
--       Make the following changes:
--       1. Add MODULE-IDENTITY 
--       2. Remove default value for ibposAppHostIP, ibposAppSourceIp, ibposAppRecvPacCounter 
--       	ibposAppErrPacCouter, ibposAppDistrErrCounter, ibposAppBuffedCounter,
--       	ibposAppDiscardedCounter, ibposPosRecvPacCounter, ibposPosErrPacCounter,
--       	ibposPosMapErrCounter, ibposPosBuffedCounter, ibposPosDiscardedCounter                                                                                   
--       	ibposFCMConnectFailCounter and ibposFCMTimeoutCounter because their syntax is Counter32                                 
--       3. Modify ibposPosIfIndex, ibposAsyAppIfIndex, ibposFCMIfIndex, ibposPadIfIndex of INTEGER range
--       4. Modify ibposPosId of INTEGER range 
--       5. Add a new column object ibposPosInterType under ibposInterTable table	by caizibin  2004-10-11
--       6. Add an enumeration called pad(3) under the ibposAppConnectMode  by caizibin  2004-10-11
--       7. Add a new column object ibposAppX121Addr under ibposAppTable table	by caizibin  2004-10-11
--	 	 8. Add new object ibposPadWaitTime, ibposPadIdleTimeout, ibposPadPacType, ibposPadEnable, 
--	    ibposPadCheckSChar by caizibin  2004-10-11
--       9.Refine some object's descrption to make them more readable 
--	     10.Add ibposPadTable table 
-- ==========================================================================
IB-POS-MIB    DEFINITIONS ::= BEGIN

IMPORTS
	RowStatus  
        FROM SNMPv2-TC  
    OBJECT-TYPE, NOTIFICATION-TYPE, MODULE-IDENTITY, IpAddress, Counter32
        FROM SNMPv2-SMI
    ibmlsr
		FROM IB-OID-MIB;

ibpos     MODULE-IDENTITY 
        LAST-UPDATED "200410150000Z"
        ORGANIZATION
            "Intelbras S.A. Industria de Telecomunicacao Eletronica Brasileria."
        CONTACT-INFO
            ""
        DESCRIPTION 
                "The POS MIB module is used to manage 
                 POS-Access. " 
        REVISION	"200410120000Z"
        DESCRIPTION 
                "The lastest version of this MIB module."  
        REVISION	"200407020000Z"
        DESCRIPTION 
                "The initial version of this MIB module."         

		::= { ibmlsr 8 }   


ibposAppTable   OBJECT-TYPE
   SYNTAX    	SEQUENCE OF IbPOSAppEntry
   MAX-ACCESS   not-accessible
   STATUS    	current
   DESCRIPTION
             "The table to get and set the application informatin."
   ::= { ibpos 1 }

ibposAppEntry   OBJECT-TYPE
   SYNTAX    	IbPOSAppEntry
   MAX-ACCESS   not-accessible
   STATUS    	current
   DESCRIPTION
             "The content of ibposAppTable."
   INDEX     { ibposAppId }
   ::= { ibposAppTable 1 }


IbPOSAppEntry ::= SEQUENCE {
   ibposAppId
        INTEGER,
   ibposAppConnectMode
        INTEGER,
   ibposAppState
        INTEGER,     
   ibposAppIfIndex
        INTEGER,     
   ibposAppHostIP
        IpAddress,
   ibposAppPort
        INTEGER,
   ibposAppSourceIp
        IpAddress,  
   ibposAppRecvPacCounter     
        Counter32,
   ibposAppErrPacCounter
        Counter32,
   ibposAppDistrErrCounter
        Counter32,
   ibposAppBuffedCounter
        Counter32,
   ibposAppDiscardedCounter
        Counter32,
   ibposAppDebug
        INTEGER,
   ibposAppRowStatus
        RowStatus,     		
   ibposAppX121Addr
   	OCTET STRING
   }

ibposAppId   OBJECT-TYPE
   SYNTAX    	INTEGER(0..31)
   MAX-ACCESS   read-only
   STATUS    	current
   DESCRIPTION
             "The ID of application."
   ::= { ibposAppEntry 1 }

ibposAppConnectMode   OBJECT-TYPE
   SYNTAX    	INTEGER{
                        tcp(1),
                        flow(2),
                        pad(3)                        
                }
   MAX-ACCESS   read-create
   STATUS    	current
   DESCRIPTION
             "The connect mode of application.
             
             If the router and unix are connected by TCP protocol,
             the connect mode of application is tcp.
             
             If the router and unix are connected by async interface, 
             the connect mode of application is flow.
             
             If the router is used as POSPAD device, the connect mode of application 
             is pad."
   ::= { ibposAppEntry 2 }

ibposAppState   OBJECT-TYPE
   SYNTAX    	INTEGER{
                	noset(1),
                	down(2),
                	up(3),
                	ok(4),
                	kept(5),
                	linking(6),
                	linked(7) 
             	}
   MAX-ACCESS   read-only
   STATUS    	current
   DESCRIPTION
             "The state of application."
   DEFVAL  {1}          
   ::= { ibposAppEntry 3 }

ibposAppIfIndex   OBJECT-TYPE             
   SYNTAX    	INTEGER(0..2147483647)
   MAX-ACCESS   read-create
   STATUS    	current
   DESCRIPTION
             "The interface index of the application 
             whose connect mode is flow or pad."  
   REFERENCE  "ifIndex"          
   ::= { ibposAppEntry 4 }

ibposAppHostIP   OBJECT-TYPE
   SYNTAX    	IpAddress
   MAX-ACCESS   read-create
   STATUS    	current
   DESCRIPTION
             "The destination IP Address of application.
             Used for the application whose connect mode is tcp."
   ::= { ibposAppEntry 5 }

ibposAppPort   OBJECT-TYPE
   SYNTAX    	INTEGER(0..65535)
   MAX-ACCESS   read-create
   STATUS    	current
   DESCRIPTION
             "The destination port of application.
             Used for the application whose connect mode is tcp."
   ::= { ibposAppEntry 6 }

ibposAppSourceIp   OBJECT-TYPE
   SYNTAX    	IpAddress
   MAX-ACCESS   read-create
   STATUS    	current
   DESCRIPTION
             "The source IP Address of application.
             Used for the application whose connect mode is tcp."
   ::= { ibposAppEntry 7 }

ibposAppRecvPacCounter   OBJECT-TYPE
   SYNTAX    	Counter32
   MAX-ACCESS   read-only
   STATUS    	current
   DESCRIPTION
             "The number of packets received by the application."
   DEFVAL  {0}          
   ::= { ibposAppEntry 8 }

ibposAppErrPacCounter   OBJECT-TYPE
   SYNTAX    	Counter32
   MAX-ACCESS   read-only
   STATUS    	current
   DESCRIPTION
             "The number of error packets received by the application."
   DEFVAL  {0}          
   ::= { ibposAppEntry 9 }

ibposAppDistrErrCounter   OBJECT-TYPE
   SYNTAX    	Counter32
   MAX-ACCESS   read-only
   STATUS    	current
   DESCRIPTION
             "The number of packets that could not be sent to POS."
   DEFVAL  {0}          
   ::= { ibposAppEntry 10 }

ibposAppBuffedCounter   OBJECT-TYPE
   SYNTAX    	Counter32
   MAX-ACCESS   read-only
   STATUS    	current
   DESCRIPTION
             "The number of packets stored in the buffer of application."
   DEFVAL  {0}          
   ::= { ibposAppEntry 11 }

ibposAppDiscardedCounter   OBJECT-TYPE
   SYNTAX    	Counter32
   MAX-ACCESS   read-only
   STATUS    	current
   DESCRIPTION
             "The number of packets discarded by the application."
   DEFVAL  {0}          
   ::= { ibposAppEntry 12 }

ibposAppDebug   OBJECT-TYPE
   SYNTAX    	INTEGER{
                        close(1),
                        open(2)
                }
   MAX-ACCESS   read-create
   STATUS    	current
   DESCRIPTION
             "The debugging switch of application."
   ::= { ibposAppEntry 13 }

ibposAppRowStatus   OBJECT-TYPE
   SYNTAX    	RowStatus
   MAX-ACCESS   read-create
   STATUS    	current
   DESCRIPTION
             "The status of row. Only support active, CreateAndGo and destroy."
   ::= { ibposAppEntry 14 } 
   
ibposAppX121Addr OBJECT-TYPE
   SYNTAX    	OCTET STRING (SIZE(1..15))
   MAX-ACCESS   read-create
   STATUS    	current
   DESCRIPTION             
             "The destination X121 Address of application which is
             an octet string made up of numeric.
             Used for the application whose connect mode is pad."
   ::= { ibposAppEntry 15 }  

ibposInterTable   OBJECT-TYPE
   SYNTAX    	SEQUENCE OF IbPOSInterEntry
   MAX-ACCESS   not-accessible
   STATUS    	current
   DESCRIPTION
             "The table to get and set the POS-Interface informatin."
   ::= { ibpos 2 }

ibposInterEntry   OBJECT-TYPE
   SYNTAX    	IbPOSInterEntry
   MAX-ACCESS   not-accessible
   STATUS    	current
   DESCRIPTION
             "The content of ibposInterTable."
   INDEX     { ibposPosId }
   ::= { ibposInterTable 1 }


IbPOSInterEntry ::= SEQUENCE {
   ibposPosId
        INTEGER,
   ibposPosIfIndex
        INTEGER,
   ibposPosConnectState
        INTEGER,     
   ibposPosRecvPacCounter
        Counter32,     
   ibposPosErrPacCounter
        Counter32,
   ibposPosMapErrCounter
        Counter32,
   ibposPosBuffedCounter
        Counter32,  
   ibposPosDiscardedCounter     
        Counter32,
   ibposPosInterDebug
        INTEGER,
   ibposPosInterRowStatus
        RowStatus,
   ibposPosInterType
   	INTEGER  
   }

ibposPosId   OBJECT-TYPE
   SYNTAX    	INTEGER(0..255)
   MAX-ACCESS   read-only
   STATUS    	current
   DESCRIPTION
             "The ID of the POS-Interface."
   ::= { ibposInterEntry 1 }

ibposPosIfIndex   OBJECT-TYPE
   SYNTAX    	INTEGER(1..2147483647)
   MAX-ACCESS   read-create
   STATUS    	current
   DESCRIPTION
             "The interface index of the POS-Interface whose type is fcm, asy or pad-client."  
   REFERENCE  "ifIndex"
   ::= { ibposInterEntry 2 }

ibposPosConnectState   OBJECT-TYPE
   SYNTAX    	INTEGER{
                        noset(1),
                        down(2),
                        up(3),
                        ok(4)
                }
   MAX-ACCESS   read-only
   STATUS    	current
   DESCRIPTION
             "The state of the POS-Interface."
   DEFVAL  {1}          
   ::= { ibposInterEntry 3 }

ibposPosRecvPacCounter   OBJECT-TYPE
   SYNTAX    	Counter32
   MAX-ACCESS   read-only
   STATUS    	current
   DESCRIPTION
             "The number of packets received by the POS-Interface."
   DEFVAL  {0}          
   ::= { ibposInterEntry 4 }

ibposPosErrPacCounter   OBJECT-TYPE
   SYNTAX    	Counter32
   MAX-ACCESS   read-only
   STATUS    	current
   DESCRIPTION
             "The number of error packets received by the POS-Interface."
   DEFVAL  {0}          
   ::= { ibposInterEntry 5 }

ibposPosMapErrCounter   OBJECT-TYPE
   SYNTAX    	Counter32
   MAX-ACCESS   read-only
   STATUS    	current
   DESCRIPTION
             "The number of packets that could not be sent to application."
   DEFVAL  {0}          
   ::= { ibposInterEntry 6 }

ibposPosBuffedCounter   OBJECT-TYPE
   SYNTAX    	Counter32
   MAX-ACCESS   read-only
   STATUS    	current
   DESCRIPTION
             "The number of packets stored in the buffer of the POS-Interface."
   DEFVAL  {0}          
   ::= { ibposInterEntry 7 }

ibposPosDiscardedCounter   OBJECT-TYPE
   SYNTAX    	Counter32
   MAX-ACCESS   read-only
   STATUS    	current
   DESCRIPTION
             "The number of packets discarded by the POS-Interface."
   DEFVAL  {0}          
   ::= { ibposInterEntry 8 }

ibposPosInterDebug   OBJECT-TYPE
   SYNTAX    	INTEGER{
                        close(1),
                        open(2)
                }
   MAX-ACCESS   read-create
   STATUS    	current
   DESCRIPTION
             "The debugging switch of the POS-Interface."
   ::= { ibposInterEntry 9 }   

ibposPosInterRowStatus   OBJECT-TYPE
   SYNTAX    	RowStatus
   MAX-ACCESS   read-create
   STATUS    	current
   DESCRIPTION
             "The status of row. Only support active, CreateAndGo and destroy."
   ::= { ibposInterEntry 10 }   

ibposPosInterType   OBJECT-TYPE
   SYNTAX    	INTEGER{
                        fcm(1),
                        asy(2),
                        pad-client(3),
                        pad-server(4)
                }
   MAX-ACCESS   read-create
   STATUS    	current
   DESCRIPTION
             "The type of interface.
             
             The POS-Access mode has four types: FCM-Access, ASYNC-Access, 
             simulating POSPAD device, POSPAD-Access. 
             
             FCM-Access mode means POS and router are connected through PSTN.
             In this case, ibposPosInterType should be set to fcm.
             
             ASYNC-Access mode means POS and router are connected by asynchronous cable.
             In this case, ibposPosInterType should be set to asy.
             
             Simulating POSPAD device means router connects POS through asynchronous cable
             and connects another router whose connect mode is pad-server through X.25 network. 
             In this case, ibposPosInterType should be set to pad-client.  
              
             POSPAD-Access mode means router connects POSPAD device through X.25 network.
             In this case, ibposPosInterType is pad-server. The ibposPosInterType
             can't be set to pad-server. It is autogenerated when POSPAD device initiates
             a connection to the router.  
             "
   DEFVAL  {1}
   ::= { ibposInterEntry 11 }
   
ibposMapTable   OBJECT-TYPE            
   SYNTAX    	SEQUENCE OF IbPOSMapEntry
   MAX-ACCESS   not-accessible
   STATUS    	current
   DESCRIPTION
		"The table to get and set the informatin of mapping relation of destination and application."
   ::= { ibpos 3 }

ibposMapEntry   OBJECT-TYPE
   SYNTAX    	IbPOSMapEntry
   MAX-ACCESS   not-accessible
   STATUS    	current
   DESCRIPTION
             "The content of ibposMapTable."
   INDEX     { ibposMapDes }
   ::= { ibposMapTable 1 }


IbPOSMapEntry ::= SEQUENCE {
   ibposMapDes
        INTEGER,
   ibposMapAppNumber
        INTEGER,
   ibposMapRowStatus
        RowStatus
   }

ibposMapDes   OBJECT-TYPE
   SYNTAX    	INTEGER(-1..65535)
   MAX-ACCESS   read-create
   STATUS    	current
   DESCRIPTION
             "The destination code of the mapping item.
             If the value is -1, it is the default item of mapping relation."
   ::= { ibposMapEntry 1 }

ibposMapAppNumber   OBJECT-TYPE
   SYNTAX    	INTEGER(0..31)
   MAX-ACCESS   read-create
   STATUS    	current
   DESCRIPTION
             "The application index of the mapping item."

   ::= { ibposMapEntry 2 }

ibposMapRowStatus   OBJECT-TYPE
   SYNTAX    	RowStatus
   MAX-ACCESS   read-create
   STATUS    	current
   DESCRIPTION
             "The status of row. Only support active, CreateAndGo and destroy."
   ::= { ibposMapEntry 3 } 
   
ibposAsyAppTable   OBJECT-TYPE
   SYNTAX    	SEQUENCE OF IbPOSAsyAppEntry
   MAX-ACCESS   not-accessible
   STATUS    	current
   DESCRIPTION
             "The table to get and set the asynchronous-application interface information."
   ::= { ibpos 4 }

ibposAsyAppEntry   OBJECT-TYPE
   SYNTAX    	IbPOSAsyAppEntry
   MAX-ACCESS   not-accessible
   STATUS    	current
   DESCRIPTION
             "The content of ibposAsyAppTable."
   INDEX     { ibposAsyAppIfIndex }
   ::= { ibposAsyAppTable 1 }

IbPOSAsyAppEntry ::= SEQUENCE {
   ibposAsyAppIfIndex
        INTEGER,
   ibposAsyAppRowStatus
        RowStatus
   }

ibposAsyAppIfIndex   OBJECT-TYPE
   SYNTAX    	INTEGER(0..2147483647)
   MAX-ACCESS   read-only
   STATUS    	current
   DESCRIPTION
             "The interface index of asynchronous-application."
   REFERENCE  "ifIndex"
   ::= { ibposAsyAppEntry 1 }

ibposAsyAppRowStatus   OBJECT-TYPE
   SYNTAX    	RowStatus
   MAX-ACCESS   read-create
   STATUS    	current
   DESCRIPTION
             "The status of row. Only support active, CreateAndGo and destroy."
   ::= { ibposAsyAppEntry 2 }
      
   

ibposFCMTable   OBJECT-TYPE
   SYNTAX    	SEQUENCE OF IbPOSFCMEntry
   MAX-ACCESS   not-accessible
   STATUS    	current
   DESCRIPTION
             "The table to get the information of FCM interface."
   ::= { ibpos 5 }

ibposFCMEntry   OBJECT-TYPE
   SYNTAX    	IbPOSFCMEntry
   MAX-ACCESS   not-accessible
   STATUS    	current
   DESCRIPTION
             "The content of ibposFCMTable."
   INDEX     { ibposFCMIfIndex }
   ::= { ibposFCMTable 1 }


IbPOSFCMEntry ::= SEQUENCE {
   ibposFCMIfIndex
        INTEGER,
   ibposFCMTimeoutCounter
        Counter32,
   ibposFCMConnectFailCounter
        Counter32
   }

ibposFCMIfIndex   OBJECT-TYPE
   SYNTAX    	INTEGER(0..2147483647)
   MAX-ACCESS   read-only
   STATUS    	current
   DESCRIPTION
             "The index of FCM interface." 
   REFERENCE  "ifIndex"
   ::= { ibposFCMEntry 1 }

ibposFCMTimeoutCounter   OBJECT-TYPE
   SYNTAX    	Counter32
   MAX-ACCESS   read-only
   STATUS    	current
   DESCRIPTION
             "The number that modem was hung up for timeout."
   DEFVAL  {0}          
   ::= { ibposFCMEntry 3 }

ibposFCMConnectFailCounter   OBJECT-TYPE
   SYNTAX    	Counter32
   MAX-ACCESS   read-only
   STATUS    	current
   DESCRIPTION
             "The number that modem could not handshake successfully."
   DEFVAL  {0}          
   ::= { ibposFCMEntry 4 }
   
   

ibposAppSum   OBJECT-TYPE
   SYNTAX    	INTEGER(0..32)
   MAX-ACCESS   read-only
   STATUS    	current   
   DESCRIPTION
             "The total of configued applications."
   DEFVAL  {0}          
   ::= { ibpos 6 }



ibposInterSum   OBJECT-TYPE
   SYNTAX    	INTEGER(0..256)
   MAX-ACCESS   read-only
   STATUS    	current   
   DESCRIPTION
             "The total of configued POS-Interfaces."
   DEFVAL  {0}          
   ::= { ibpos 7 }



ibposEnable   OBJECT-TYPE
   SYNTAX    	INTEGER{
                        disable(1),
                        enable(2)
                }
   MAX-ACCESS   read-write
   STATUS    	current   
   DESCRIPTION
             "To enable or diable pos-server."
   DEFVAL  {1}          
   ::= { ibpos 8 }



ibposAppDebugAll   OBJECT-TYPE
   SYNTAX    	INTEGER{
                        close(1),
                        open(2)
                }
   MAX-ACCESS   read-write
   STATUS    	current   
   DESCRIPTION
             "To open or close the debugging switch of all applications."
   DEFVAL  {1}          
   ::= { ibpos 9 }



ibposPosDebugAll   OBJECT-TYPE
   SYNTAX    	INTEGER{
                        close(1),
                        open(2)
                }
   MAX-ACCESS   read-write
   STATUS    	current   
   DESCRIPTION
             "To open or close the debugging switch of all POS-Interfaces."
   DEFVAL  {1}          
   ::= { ibpos 10 }



ibposClearPacCounter   OBJECT-TYPE
   SYNTAX    	INTEGER{
                        clear(1),
                        counting(2)
                }
   MAX-ACCESS   read-write
   STATUS    	current   
   DESCRIPTION
             "To reset all packet counters of all applicaions and POS-Interfaces."
   DEFVAL  {2}          
   ::= { ibpos 11 } 
   
ibposClearFCMCounter   OBJECT-TYPE
   SYNTAX    	INTEGER{
                        clear(1),
                        counting(2)
                }
   MAX-ACCESS   read-write
   STATUS    	current   
   DESCRIPTION
             "To clear all counters of all FCM interfaces."
   DEFVAL  {2}          
   ::= { ibpos 12 }



ibposEnableTrap   OBJECT-TYPE
   SYNTAX    	INTEGER{
                        disable(1),
                        enable(2)
                }
   MAX-ACCESS   read-write
   STATUS    	current   
   DESCRIPTION
             "To enable or disable trap switch."
   DEFVAL  {1}          
   ::= { ibpos 13 }

ibposFCMAnswerTime   OBJECT-TYPE
   SYNTAX    	INTEGER(500..2000)
   MAX-ACCESS   read-write
   STATUS    	current   
   DESCRIPTION
             "FCM answer time, unit:ms."
   DEFVAL  {500}      
      ::= { ibpos 14 } 
      
ibposFCMTradeTime   OBJECT-TYPE
   SYNTAX    	INTEGER(30000..1200000)
   MAX-ACCESS   read-write
   STATUS    	current   
   DESCRIPTION
             "FCM trade time, unit:ms."
   DEFVAL  {60000}          
   ::= { ibpos 15 }

ibposFCMPacketInterval   OBJECT-TYPE
   SYNTAX    	INTEGER(3500..10000)
   MAX-ACCESS   read-write
   STATUS    	current   
   DESCRIPTION
             "FCM packet interval time, unit:ms."
   DEFVAL  {5000}          
   ::= { ibpos 16 }

ibposPadWaitTime  OBJECT-TYPE 	
   SYNTAX        INTEGER (100..10000)
   MAX-ACCESS    read-write
   STATUS        current
   DESCRIPTION
	    "The time that POS-Interface needs to wait to receive another packet, unit:ms.
	    It may be configured when router is used as POSPAD device. In other cases,
	    It is useless."
   ::= { ibpos 18 }

ibposPadIdleTimeout OBJECT-TYPE 	
   SYNTAX          INTEGER (0..600)
   MAX-ACCESS      read-write
   STATUS          current
   DESCRIPTION
		"If these is no packet transmitting through the time, 
		the connection of POSPAD device and router whose connect mode 
		is pad-server will be cut off. Unit:s."
   ::= { ibpos 19 }

ibposPadPacType	 OBJECT-TYPE	
    SYNTAX        INTEGER { 
    				       syn(1),
    				       asy(2)
                         }
    MAX-ACCESS    read-write
    STATUS        current
    DESCRIPTION
	  	"The type of packet.Between POSPAD device and router whose connect mode 
		is pad-server, there are two types of packet. One is synchronous, 
		the other is asynchronous."
    DEFVAL  {1}
    ::= { ibpos 20 }

ibposPadCheckSChar  OBJECT-TYPE
   SYNTAX    	INTEGER {
                    disable(1),
                    enable(2)                   
		        }
   MAX-ACCESS   read-write
   STATUS    	current   
   DESCRIPTION
             "To enable or disable the checking of 10 04 characters in packet.
             It is used for the router which is used as POSPAD device.
             
             When the value is disable, it will check packet that just includes 10 04 charaters.
             If there are 10 04 packet, the router which is used as POSPAD device
             will disconnect from POSPAD-access router.
             
             When the value is enable, it will check 10 04 characters in packet. 
             If there are 10 04 characters in packet, the router which is used as POSPAD 
             device will disconnect from POSPAD-access router."
   DEFVAL  {2}          
   ::= { ibpos 21 }

ibposPadTable   OBJECT-TYPE            
   SYNTAX    	SEQUENCE OF IbPOSPadEntry
   MAX-ACCESS   not-accessible
   STATUS    	current
   DESCRIPTION
		"The table to enable or disable POSPAD-Access function under serial interface."
   ::= { ibpos 22 }

ibposPadEntry   OBJECT-TYPE
   SYNTAX    	IbPOSPadEntry
   MAX-ACCESS   not-accessible
   STATUS    	current
   DESCRIPTION
             "The content of ibposPadTable."
   INDEX     { ibposPadIfIndex }
   ::= { ibposPadTable 1 }


IbPOSPadEntry ::= SEQUENCE {
   ibposPadIfIndex
        INTEGER,
   ibposPadRowStatus
        RowStatus
   }

ibposPadIfIndex   OBJECT-TYPE
   SYNTAX    	INTEGER(1..2147483647)
   MAX-ACCESS   not-accessible
   STATUS    	current
   DESCRIPTION
             "The index of serial interface."  
   REFERENCE  "ifIndex"
   ::= { ibposPadEntry 1 }

ibposPadRowStatus   OBJECT-TYPE
   SYNTAX    	RowStatus
   MAX-ACCESS   read-create
   STATUS    	current
   DESCRIPTION
             "The status of row. Only support active, CreateAndGo and destroy."
   ::= { ibposPadEntry 2 }  

ibposTrap        OBJECT IDENTIFIER ::= { ibpos 17 }

ibposAppNotReadyTrap NOTIFICATION-TYPE
   OBJECTS 	{ ibposAppId }
   STATUS  	current
   DESCRIPTION
             "The agent will send a trap when the application whose state is linked
             isn't ready to send or receive data.
             Only used for the application whose connect mode is tcp."
   ::= { ibposTrap 1 }



ibposAppConnectFailTrap NOTIFICATION-TYPE
   OBJECTS 	{ ibposAppId }
   STATUS  	current
   DESCRIPTION
             "The agent will send a trap if router can not connect to the application."
   ::= { ibposTrap 2 }
   


ibposAppStateChangeTrap NOTIFICATION-TYPE
   OBJECTS 	{ ibposAppId, ibposAppState }
   STATUS  	current
   DESCRIPTION
             "The agent will send a trap when the state of the application is changed to down or kept."
   ::= { ibposTrap 3 }
   


ibposAppNotConfigedTrap NOTIFICATION-TYPE
   OBJECTS 	{ ibposAppId }
   STATUS  	current
   DESCRIPTION
             "The agent will send a trap if the application isn't configured."
   ::= { ibposTrap 4 }
   


ibposAppBuffOverFlowTrap NOTIFICATION-TYPE
   OBJECTS 	{ ibposAppId }
   STATUS  	current
   DESCRIPTION
             "The agent will send a trap if the application buffer is overflowed."
   ::= { ibposTrap 5 }
   


ibposAppDebugOpenTrap NOTIFICATION-TYPE
   OBJECTS 	{ ibposAppId }
   STATUS  	current
   DESCRIPTION
             "The agent will send a trap if the debugging switch of application is open."
   ::= { ibposTrap 6 }
   


ibposAppDebugAllOpenTrap NOTIFICATION-TYPE
   STATUS  	current
   DESCRIPTION
             "The agent will send a trap if the all debugging switches of application are open."
   ::= { ibposTrap 7 }



ibposInterBuffOverFlowTrap NOTIFICATION-TYPE
   STATUS  	current
   DESCRIPTION
             "The agent will send a trap if the distributing buffer is overflowed."
   ::= { ibposTrap 8 }
   


ibposInterStateChangeTrap NOTIFICATION-TYPE
   OBJECTS 	{ ibposPosId, ibposPosConnectState }
   STATUS  	current
   DESCRIPTION
             "The agent will send a trap if the state of POS-Interface is changed to down."
   ::= { ibposTrap 9 }
   


ibposInterDebugOpenTrap NOTIFICATION-TYPE
   OBJECTS 	{ ibposPosId }
   STATUS  	current
   DESCRIPTION
             "The agent will send a trap if the debug of POS-Interface is open."
   ::= { ibposTrap 10 }
   


ibposInterDebugAllOpenTrap NOTIFICATION-TYPE
   STATUS  	current
   DESCRIPTION
             "The agent will send a trap if the all debugs of POS-Interface are open."
   ::= { ibposTrap 11 }



ibposFCMTimeoutTrap NOTIFICATION-TYPE
   OBJECTS 	{ ibposFCMIfIndex }
   STATUS  	current
   DESCRIPTION
             "The agent will send a trap if the modem is hung up for timeout."
   ::= { ibposTrap 12 }
   


ibposFCMConnectFailTrap NOTIFICATION-TYPE
   OBJECTS 	{ ibposFCMIfIndex }
   STATUS  	current
   DESCRIPTION
             "The agent will send a trap if the handshaking of modems is not successful."
   ::= { ibposTrap 13 }
   
   
   
ibposClearPacketCounter NOTIFICATION-TYPE
   STATUS  	current
   DESCRIPTION
             "The agent will send a trap when the packet counter of 
             the POS application and interface is cleared."
   ::= { ibposTrap 14 }



ibposClearFcmCounter NOTIFICATION-TYPE
   STATUS  	current
   DESCRIPTION
             "The agent will send a trap when the FCM counter is cleared."
   ::= { ibposTrap 15 }
   
END
