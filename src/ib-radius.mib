-- =================================================================
-- Copyright (C) 2023 Intelbras S.A. All rights reserved.
--
-- Description:
--
-- A configuration management and statistical MIB, includes configuration of
-- RADIUS Server, and statistics about accounting server which complements
-- the IETF standard MIB as described in RFC2620.  In addition, there are four
-- traps supported to notify client the RADIUS Server's down and up state.
--
-- Reference: RFC2866, RADIUS-AUTH-CLIENT-MIB, RADIUS-ACC-CLIENT-MIB
-- Version: V2.9
-- History:
--  V1.0 Initial version 2004-07-13
--  V1.1 2004-10-12 Updated by gaolong
--       Set the size of DisplayString from 0 to 255.
--  V1.2 2005-03-10 Updated by xulei
--       Modified the description of this MIB.
--       Modified the max access to nodes in ibRdInfoTable.
--       Modified the descriptions of nodes in ibRdInfoTable.
--       Added nodes to ibRdInfoTable.
--       Added ibRdAccInfoTable.
--       Added ibRadiusAccServerTable.
--       Added traps.
--  V1.3 2005-05-08 Updated by xulei
--       Modified the max access to ibRdPrimAccState and ibRdSecAccState.
--  V1.4 2005-06-03 Updated by xulei
--       Modified the SYNTAX and DESCRIPTION of ibRdAccPacketUnit.
--  V1.5 2008-05-19 Updated by yangxu
--       Added nodes to ibRdAccInfoTable.
--       Added node ibRdAcctOnEnable.
--       Added node ibRdAcctOnSendTimes.
--       Added node ibRdAcctOnSendInterval.
--  V1.6 2008-07-18 Updated by d04528
--       Added nodes to table ibRadiusAuthenticating.
--       Added node ibRadiusAuthClient.
--       Added node ibRadiusAuthServerTable.
--       Added node ibRadiusAuthServerEntry.
--       Added node ibRadiusAuthFailureTimes.
--       Added node ibRadiusAuthTimeoutTimes.
--       Added node ibRadiusAuthRejectTimes.
--  V1.7 2009-04-30 Update by h02978
--       Added node ibRdSecKey.
--       Added node ibRdSecAccKey.
--       Added node ibRadiusAuthServerUpTrap.
--       Added node ibRadiusAccServerUpTrap.
--  V1.8 2009-08-05 Update by h02978
--       Added node ibRadiusAuthErrThreshold.
--       Added node ibRadiusAuthErrTrap.
--  V1.9 2010-03-29 Updated by x04730
--       Modified the SYNTAX of ibRdAccRealTime.
--       2010-07-14 Updated by x04730
--       Modified the SYNTAX of ibRdQuietTime.
--       Modified the SYNTAX of ibRdAccQuietTime.
--       2010-08-26 Update by y06401
--       Added ibRadiusSchAuthTable.
--       Added ibRadiusSchAccTable.
--  V2.0 2010-03-29 Updated by y07111
--       Added nodes to table ibRadiusStatistic.
--       Added node ibRadiusStatAccReq.
--       Added node ibRadiusStatAccAck.
--       Added node ibRadiusStatLogoutReq.
--       Added node ibRadiusStatLogoutAck.
--  V2.1 2011-11-28, Updated by xuyonggang
--       Added node ibRadiusServerTrapVarObjects.
--       2012-02-28 Updated by y002965
--       Added table ibRdSecondaryAuthServerTable.
--       Added table ibRdSecondaryAcctServerTable.
--       Added node ibRdPrimVpnName.
--       Added node ibRdSecVpnName.
--       Added node ibRdAuthNasIpAddrType.
--       Added node ibRdAuthNasIpAddr.
--       Added node ibRdPrimAccVpnName.
--       Added node ibRdSecAccVpnName.
--       Added node ibRdAccNasIpAddrType.
--       Added node ibRdAccNasIpAddr.
--       Changed the length of ibRdSecAccKey.
--       Changed the length of ibRdAccKey.
--       Changed the length of ibRdSecKey.
--       Changed the length of ibRdKey.
--  V2.2 2012-10-11, Updated by liubo
--       Added node ibRdAuthNasIpv6Addr.
--       Added node ibRdAccNasIpv6Addr.
--       Modified the length of ibRdSecAccKey.
--       Modified the length of ibRdAccKey.
--       Modified the length of ibRdSecKey.
--       Modified the length of ibRdKey.
--       Modified the length of ibRdPrimVpnName.
--       Modified the length of ibRdSecVpnName.
--       Modified the length of ibRdPrimAccVpnName.
--       Modified the length of ibRdSecAccVpnName.
--       Modified the length of ibRdSecondaryAuthVpnName.
--       Modified the length of ibRdSecondaryAccVpnName.
--       Modified the length of ibRdSecondaryAuthKey.
--       Modified the length of ibRdSecondaryAccKey.
--       Modified the default value and description of ibRdAcctOnSendTimes.
--  V2.3 2013-03-30, Updated by luyu
--       Modified the description of ibRdSecondaryAccUdpPort.
--       Modified the default value and description of ibRadiusSchAccPrimUdpPort.
--       Modified the default value and description of ibRadiusSchAccSecUdpPort.
--  V2.4 2014-06-07, Updated by liubo
--       Modified the description of ibRdSecondaryAuthRowStatus.
--       Modified the description of ibRdSecondaryAccRowStatus.
--  V2.5 2016-11-03, Updated by yemingxia
--       Modified the value range of ibRdAccRealTime.
--       Added node ibRdAccRealTimeUnit.
--  V2.6 2019-01-12, Updated by yuhua
--       Added node ibRadiusAuthenticationServerUpTrap.
--       Added node ibRadiusAccountingServerUpTrap.
--       Added node ibRadiusAuthenticationServerDownTrap.
--       Added node ibRadiusAccountingServerDownTrap.
--  V2.7 2021-09-06, Updated by jinyu
--       Added node ibRdAccStopPktTimeResend.
--       Modified the properties of ibRdGroupName.
--       Modified the properties of ibRdAccGroupName.
--  V2.8 2021-12-13 Updated by zhanghang
--       Added node ibRadiusAccCachePacketTrap.
--       Added node ibRadiusAccCacheVarObjects.
--       Added node ibRadiusAccCacheNotifications.
--       Added node ibRadiusAccCacheMaxPackets.
--       Added node ibRadiusAccCacheUpperValue.
--       Added node ibRadiusAccCacheLowerValue.
--       Added node ibRadiusAccCacheMemoryUsage.
--       Added node ibRadiusAccCachePackets.
--       Added node ibRadiusAccCacheAlarm.
--       Added node ibRadiusAccCacheResume.
--       Added node ibRadiusAccCachePacketDiscard.
--  V2.9 2022-3-3 Updated by zhanghang
--       Modified node ibRadiusAccCachePackets.
-- =================================================================
IB-RADIUS-MIB DEFINITIONS ::= BEGIN
    IMPORTS
        ibCommon
            FROM IB-OID-MIB
        IpAddress, Integer32, Counter32, OBJECT-TYPE, MODULE-IDENTITY, NOTIFICATION-TYPE,
        Unsigned32,Counter64, TimeTicks
            FROM SNMPv2-SMI
        RowStatus, TruthValue, DisplayString
            FROM SNMPv2-TC
        InetAddressType, InetAddress
            FROM INET-ADDRESS-MIB
        Ipv6Address
            FROM IPV6-TC
        radiusAuthServerIndex, radiusAuthServerAddress, radiusAuthClientServerPortNumber
            FROM RADIUS-AUTH-CLIENT-MIB
        radiusAccServerIndex, radiusAccServerAddress, radiusAccClientServerPortNumber
            FROM RADIUS-ACC-CLIENT-MIB;

    ibRadius MODULE-IDENTITY
    LAST-UPDATED "202203031800Z"            -- March 3, 2022 at 18:00 GMT
    ORGANIZATION
        "Intelbras S.A. Industria de Telecomunicacao Eletronica Brasileria."
    CONTACT-INFO
        ""
    DESCRIPTION
        "The IB-RADIUS-MIB contains objects to
        Manage configuration and Monitor running state
        for RADIUS feature."
    REVISION "202203031800Z"        -- March 3, 2022 at 18:00 GMT
    DESCRIPTION
         "Modified node ibRadiusAccCachePackets."
    REVISION "202112131800Z"        -- December 13 2021 at 18:00 GMT
    DESCRIPTION
         "Added node ibRadiusAccCachePacketTrap.
         Added node ibRadiusAccCacheVarObjects.
         Added node ibRadiusAccCacheNotifications.
         Added node ibRadiusAccCacheMaxPackets.
         Added node ibRadiusAccCacheUpperValue.
         Added node ibRadiusAccCacheLowerValue.
         Added node ibRadiusAccCacheMemoryUsage.
         Added node ibRadiusAccCachePackets.
         Added node ibRadiusAccCacheAlarm.
         Added node ibRadiusAccCacheResume.
         Added node ibRadiusAccCachePacketDiscard."
    REVISION "202109061800Z"        -- Sept 06, 2021 at 18:00 GMT
    DESCRIPTION
         "Added node ibRdAccStopPktTimeResend.
         Modified the properties of ibRdGroupName.
         Modified the properties of ibRdAccGroupName."
    REVISION "201901121800Z"        -- January 12, 2019 at 18:00 GMT
    DESCRIPTION
        "Added node ibRadiusAuthenticationServerUpTrap.
         Added node ibRadiusAccountingServerUpTrap.
         Added node ibRadiusAuthenticationServerDownTrap.
         Added node ibRadiusAccountingServerDownTrap."
    REVISION "201611031800Z"        -- November 3, 2016 at 18:00 GMT
    DESCRIPTION
        "Modified the value range of ibRdAccRealTime.
        Added node ibRdAccRealTimeUnit."
    REVISION "201406071800Z"        -- June 7, 2014 at 18:00 GMT
    DESCRIPTION
        "Modified the description of ibRdSecondaryAuthRowStatus.
        Modified the description of ibRdSecondaryAccRowStatus."
    ::= { ibCommon 13 }

    ibRdObjects OBJECT IDENTIFIER ::= { ibRadius 1 }

    ibRdInfoTable  OBJECT-TYPE
        SYNTAX SEQUENCE OF IbRdInfoEntry
        MAX-ACCESS not-accessible
        STATUS current
        DESCRIPTION
        "The (conceptual) table listing RADIUS authentication servers."
    ::= { ibRdObjects 1 }

    ibRdInfoEntry OBJECT-TYPE
        SYNTAX IbRdInfoEntry
        MAX-ACCESS not-accessible
        STATUS current
        DESCRIPTION
        "An entry (conceptual row) representing a RADIUS authentication server."
        INDEX { ibRdGroupName }
    ::= { ibRdInfoTable 1 }

    IbRdInfoEntry ::= SEQUENCE {
        ibRdGroupName          DisplayString,
        ibRdPrimAuthIp         IpAddress,
        ibRdPrimUdpPort        Integer32,
        ibRdPrimState          INTEGER,
        ibRdSecAuthIp          IpAddress,
        ibRdSecUdpPort         Integer32,
        ibRdSecState           INTEGER,
        ibRdKey                DisplayString,
        ibRdRetry              Integer32,
        ibRdTimeout            Integer32,
        ibRdPrimAuthIpAddrType InetAddressType,
        ibRdPrimAuthIpAddr     InetAddress,
        ibRdSecAuthIpAddrType  InetAddressType,
        ibRdSecAuthIpAddr      InetAddress,
        ibRdServerType         INTEGER,
        ibRdQuietTime          Integer32,
        ibRdUserNameFormat     INTEGER,
        ibRdRowStatus          RowStatus,
        ibRdSecKey             DisplayString,
        ibRdPrimVpnName        DisplayString,
        ibRdSecVpnName         DisplayString,
        ibRdAuthNasIpAddrType  InetAddressType,
        ibRdAuthNasIpAddr      IpAddress,
        ibRdAuthNasIpv6Addr    Ipv6Address
        }

    ibRdGroupName OBJECT-TYPE
        SYNTAX DisplayString(SIZE (1..32))
        MAX-ACCESS read-only
        STATUS current
        DESCRIPTION
        "The name of the RADIUS authentication group referred to in this table
        entry."
    ::= { ibRdInfoEntry 1 }


    ibRdPrimAuthIp OBJECT-TYPE
        SYNTAX IpAddress
        MAX-ACCESS read-create
        STATUS deprecated
        DESCRIPTION
        "The IP address of primary RADIUS authentication server."
    ::= { ibRdInfoEntry 2 }

    ibRdPrimUdpPort OBJECT-TYPE
        SYNTAX Integer32
        MAX-ACCESS read-create
        STATUS current
        DESCRIPTION
        "The UDP port the client is using to send requests to
        primary RADIUS authentication server.  Default value is 1812."
    ::= { ibRdInfoEntry 3 }

    ibRdPrimState OBJECT-TYPE
        SYNTAX INTEGER
        {
            active(1),
            block(2)
        }
        MAX-ACCESS read-create
        STATUS current
        DESCRIPTION
        "The state of the primary RADIUS authentication server.
        1 (active) The primary authentication server is in active state.
        2 (block)  The primary authentication server is in block state."
    ::= { ibRdInfoEntry 4 }

    ibRdSecAuthIp OBJECT-TYPE
        SYNTAX IpAddress
        MAX-ACCESS read-create
        STATUS deprecated
        DESCRIPTION
        "The IP address of secondary RADIUS authentication server."
    ::= { ibRdInfoEntry 5 }

    ibRdSecUdpPort OBJECT-TYPE
        SYNTAX Integer32
        MAX-ACCESS read-create
        STATUS current
        DESCRIPTION
        "The UDP port the client is using to send requests to
        secondary RADIUS authentication server.  Default value is 1812."
    ::= { ibRdInfoEntry 6 }

    ibRdSecState OBJECT-TYPE
        SYNTAX INTEGER
        {
            active(1),
            block(2)
        }
        MAX-ACCESS read-create
        STATUS current
        DESCRIPTION
        "The state of the secondary RADIUS authentication server.
        1 (active) The secondary authentication server is in active state.
        2 (block)  The secondary authentication server is in block state."
    ::= { ibRdInfoEntry 7 }

    ibRdKey OBJECT-TYPE
        SYNTAX DisplayString(SIZE (0..64))
        MAX-ACCESS read-create
        STATUS current
        DESCRIPTION
        "The secret shared between the RADIUS client and RADIUS
        authentication server used in encoding and decoding
        sensitive data.
        When read, ibRdKey always returns an Octet String of length zero."
    ::= { ibRdInfoEntry 8 }

    ibRdRetry OBJECT-TYPE
        SYNTAX Integer32
        MAX-ACCESS read-create
        STATUS current
        DESCRIPTION
        "The number of attempts the client will make when trying to send
        requests to a server before it will consider the attempt failed.
        Default value is 3."
    ::= { ibRdInfoEntry 9 }

    ibRdTimeout OBJECT-TYPE
        SYNTAX Integer32
        MAX-ACCESS read-create
        STATUS current
        DESCRIPTION
        "The timeout value the client will use when sending requests to a server.
        The unit is second.  Default value is 3."
    ::= { ibRdInfoEntry 10 }

    ibRdPrimAuthIpAddrType OBJECT-TYPE
        SYNTAX InetAddressType
        MAX-ACCESS read-create
        STATUS current
        DESCRIPTION
        "The IP addresses type (IPv4 or IPv6) of primary RADIUS authentication
        server."
    ::= { ibRdInfoEntry 11 }

    ibRdPrimAuthIpAddr OBJECT-TYPE
        SYNTAX InetAddress
        MAX-ACCESS read-create
        STATUS current
        DESCRIPTION
        "The IP address of primary RADIUS authentication server."
    ::= { ibRdInfoEntry 12 }

    ibRdSecAuthIpAddrType OBJECT-TYPE
        SYNTAX InetAddressType
        MAX-ACCESS read-create
        STATUS current
        DESCRIPTION
        "The IP addresses type (IPv4 or IPv6) of secondary RADIUS authentication
        server."
    ::= { ibRdInfoEntry 13 }

    ibRdSecAuthIpAddr OBJECT-TYPE
        SYNTAX InetAddress
        MAX-ACCESS read-create
        STATUS current
        DESCRIPTION
        "The IP address of secondary RADIUS authentication server."
    ::= { ibRdInfoEntry 14 }

    ibRdServerType OBJECT-TYPE
        SYNTAX INTEGER
        {
            standard(1),
            iphotel(2),
            portal(3),
            extended(4)
        }
        MAX-ACCESS read-create
        STATUS current
        DESCRIPTION
        "Specify the type of RADIUS server.
        1 (standard) - Server based on RFC protocol(s).
        2 (iphotel) - Server for IP-Hotel or 201+ system.
        3 (portal) - Server for iTellin Portal system.
        4 (extended) - Server based on RADIUS extensions.
        Default type is standard."
    ::= { ibRdInfoEntry 15 }

    ibRdQuietTime OBJECT-TYPE
        SYNTAX Integer32 (0..255)
        MAX-ACCESS read-create
        STATUS current
        DESCRIPTION
        "The time for server returning active.  The unit is minute.
         When the value is 0, the server state retains active.  Default value is 5."
    ::= { ibRdInfoEntry 16 }

    ibRdUserNameFormat OBJECT-TYPE
        SYNTAX INTEGER
        {
            withoutdomain(1),
            withdomain(2),
            keeporignal(3)
        }
        MAX-ACCESS read-create
        STATUS current
        DESCRIPTION
        "Specify the user-name format that is sent to RADIUS server.
        1 (withoutdomain) - send the user-name without domain.
        2 (withdomain) - send the user-name with domain.
        3 (keeporignal) - send the user-name as it is entered.
        Default format is withdomain."
    ::= { ibRdInfoEntry 17 }


    ibRdRowStatus   OBJECT-TYPE
        SYNTAX   RowStatus
        MAX-ACCESS  read-create
        STATUS   current
        DESCRIPTION
        "This object is responsible for managing the creation, deletion and
        modification of rows, which support active status and CreateAndGo,
        Destroy operation.  To create a new row, ibRdGroupName must be specified.
        To destroy an existent row, the ibRdGroupName MUST NOT be referred by
        ibDomainTable in ibDomainRadiusGroupName column."
    ::= { ibRdInfoEntry 18 }


    ibRdSecKey OBJECT-TYPE
        SYNTAX DisplayString(SIZE (0..64))
        MAX-ACCESS read-create
        STATUS current
        DESCRIPTION
        "The secret shared between the RADIUS client and the secondary RADIUS
        authentication server used in encoding and decoding
        sensitive data.
        When read, ibRdSecKey always returns an Octet String of length zero."
    ::= { ibRdInfoEntry 19 }

    ibRdPrimVpnName OBJECT-TYPE
        SYNTAX DisplayString(SIZE (0..31))
        MAX-ACCESS  read-create
        STATUS current
        DESCRIPTION
        "The human-readable name of the VPN in which the primary RADIUS
        authentication server is placed."
    ::= { ibRdInfoEntry 20 }

    ibRdSecVpnName OBJECT-TYPE
        SYNTAX DisplayString(SIZE (0..31))
        MAX-ACCESS  read-create
        STATUS current
        DESCRIPTION
        "The human-readable name of the VPN in which the secondary RADIUS
        authentication server is placed."
    ::= { ibRdInfoEntry 21 }

    ibRdAuthNasIpAddrType OBJECT-TYPE
        SYNTAX InetAddressType
        MAX-ACCESS read-create
        STATUS current
        DESCRIPTION
        "The type (IPv4 or IPv6) of the source IP used to communicate with
        RADIUS authentication server."
    ::= { ibRdInfoEntry 22 }

    ibRdAuthNasIpAddr OBJECT-TYPE
        SYNTAX IpAddress
        MAX-ACCESS read-create
        STATUS current
        DESCRIPTION
        "The source IPv4 address used to communicate with the RADIUS authentication
        server."
    ::= { ibRdInfoEntry 23 }

    ibRdAuthNasIpv6Addr OBJECT-TYPE
        SYNTAX Ipv6Address
        MAX-ACCESS read-create
        STATUS current
        DESCRIPTION
        "The source IPv6 address used to communicate with the RADIUS authentication
        server."
    ::= { ibRdInfoEntry 24 }

-- ***********************************************************************
--
--  Accounting Server Table
--
-- ***********************************************************************
    ibRdAccInfoTable  OBJECT-TYPE
        SYNTAX SEQUENCE OF IbRdAccInfoEntry
        MAX-ACCESS not-accessible
        STATUS current
        DESCRIPTION
        "The (conceptual) table listing RADIUS accounting servers."
    ::= { ibRdObjects 2 }

    ibRdAccInfoEntry OBJECT-TYPE
        SYNTAX IbRdAccInfoEntry
        MAX-ACCESS not-accessible
        STATUS current
        DESCRIPTION
        "An entry (conceptual row) representing a RADIUS accounting server."
        INDEX { ibRdAccGroupName }
    ::= { ibRdAccInfoTable 1 }


    IbRdAccInfoEntry ::= SEQUENCE {
        ibRdAccGroupName           DisplayString,
        ibRdPrimAccIpAddrType      InetAddressType,
        ibRdPrimAccIpAddr          InetAddress,
        ibRdPrimAccUdpPort         Integer32,
        ibRdPrimAccState           INTEGER,
        ibRdSecAccIpAddrType       InetAddressType,
        ibRdSecAccIpAddr           InetAddress,
        ibRdSecAccUdpPort          Integer32,
        ibRdSecAccState            INTEGER,
        ibRdAccKey                 DisplayString,
        ibRdAccRetry               Integer32,
        ibRdAccTimeout             Integer32,
        ibRdAccServerType          INTEGER,
        ibRdAccQuietTime           Integer32,
        ibRdAccFailureAction       INTEGER,
        ibRdAccRealTime            Integer32,
        ibRdAccRealTimeRetry       Integer32,
        ibRdAccSaveStopPktEnable   TruthValue,
        ibRdAccStopRetry           Integer32,
        ibRdAccDataFlowUnit        INTEGER,
        ibRdAccPacketUnit          INTEGER,
        ibRdAccRowStatus           RowStatus,
        ibRdAcctOnEnable           TruthValue,
        ibRdAcctOnSendTimes        Integer32,
        ibRdAcctOnSendInterval     Integer32,
        ibRdSecAccKey              DisplayString,
        ibRdPrimAccVpnName         DisplayString,
        ibRdSecAccVpnName          DisplayString,
        ibRdAccNasIpAddrType       InetAddressType,
        ibRdAccNasIpAddr           IpAddress,
        ibRdAccNasIpv6Addr         Ipv6Address,
        ibRdAccRealTimeUnit        INTEGER,
        ibRdAccStopPktTimeResend   Integer32
        }

    ibRdAccGroupName OBJECT-TYPE
        SYNTAX DisplayString(SIZE (1..32))
        MAX-ACCESS read-only
        STATUS current
        DESCRIPTION
        "The name of the RADIUS group referred to in this table entry."
    ::= { ibRdAccInfoEntry 1 }

    ibRdPrimAccIpAddrType OBJECT-TYPE
        SYNTAX      InetAddressType
        MAX-ACCESS  read-create
        STATUS      current
        DESCRIPTION
        "The IP addresses type (IPv4 or IPv6) of primary RADIUS accounting server."
    ::= { ibRdAccInfoEntry 2 }

    ibRdPrimAccIpAddr OBJECT-TYPE
        SYNTAX      InetAddress
        MAX-ACCESS  read-create
        STATUS      current
        DESCRIPTION
        "The IP address of primary RADIUS accounting server."
    ::= { ibRdAccInfoEntry 3 }

    ibRdPrimAccUdpPort OBJECT-TYPE
        SYNTAX      Integer32
        MAX-ACCESS  read-create
        STATUS      current
        DESCRIPTION
        "The UDP port the client is using to send requests to primary
        RADIUS accounting server.  Default value is 1813."
    ::= { ibRdAccInfoEntry 4 }

    ibRdPrimAccState OBJECT-TYPE
        SYNTAX INTEGER
        {
            active(1),
            block(2)
        }
        MAX-ACCESS  read-create
        STATUS      current
        DESCRIPTION
        "The state of the primary RADIUS accounting server.
        1 (active) The primary accounting server is in active state.
        2 (block)  The primary accounting server is in block state."
    ::= { ibRdAccInfoEntry 5 }

    ibRdSecAccIpAddrType OBJECT-TYPE
        SYNTAX      InetAddressType
        MAX-ACCESS  read-create
        STATUS      current
        DESCRIPTION
        "The IP addresses type (IPv4 or IPv6) of secondary RADIUS accounting
        server."
    ::= { ibRdAccInfoEntry 6 }

    ibRdSecAccIpAddr OBJECT-TYPE
        SYNTAX      InetAddress
        MAX-ACCESS  read-create
        STATUS      current
        DESCRIPTION
        "The IP address of secondary RADIUS accounting server."
    ::= { ibRdAccInfoEntry 7 }

    ibRdSecAccUdpPort OBJECT-TYPE
        SYNTAX      Integer32
        MAX-ACCESS  read-create
        STATUS      current
        DESCRIPTION
        "The UDP port the client is using to send requests to secondary
        RADIUS accounting server.  Default value is 1813."
    ::= { ibRdAccInfoEntry 8 }

    ibRdSecAccState OBJECT-TYPE
        SYNTAX INTEGER
        {
            active(1),
            block(2)
        }
        MAX-ACCESS  read-create
        STATUS      current
        DESCRIPTION
        "The state of the secondary RADIUS accounting server.
        1 (active) The secondary accounting server is in active state.
        2 (block)  The secondary accounting server is in block state."
    ::= { ibRdAccInfoEntry 9 }

    ibRdAccKey OBJECT-TYPE
        SYNTAX DisplayString(SIZE (0..64))
        MAX-ACCESS read-create
        STATUS current
        DESCRIPTION
        "The secret shared between the RADIUS client and RADIUS
        accounting server used in encoding and decoding sensitive data.
        When read, ibRdAccKey always returns an Octet String of length zero."
    ::= { ibRdAccInfoEntry 10 }


    ibRdAccRetry OBJECT-TYPE
        SYNTAX Integer32
        MAX-ACCESS read-create
        STATUS current
        DESCRIPTION
        "The number of attempt the client will make when trying to send
        requests to a server before it will consider the attempt failed.
        Default value is 3."
    ::= { ibRdAccInfoEntry 11 }

    ibRdAccTimeout OBJECT-TYPE
        SYNTAX Integer32
        MAX-ACCESS read-create
        STATUS current
        DESCRIPTION
        "The timeout value the client will use when sending requests to a server.
        The unit is second.  Default value is 3."
    ::= { ibRdAccInfoEntry 12 }

    ibRdAccServerType OBJECT-TYPE
        SYNTAX INTEGER
        {
            standard(1),
            iphotel(2),
            portal(3),
            extended(4)
        }
        MAX-ACCESS read-create
        STATUS current
        DESCRIPTION
        "Specify the type of RADIUS server.
        1 (standard) - Server based on RFC protocol(s).
        2 (iphotel) - Server for IP-Hotel or 201+ system.
        3 (portal) - Server for iTellin Portal system.
        4 (extended) - Server based on RADIUS extensions.
        Default type is standard."
    ::= { ibRdAccInfoEntry 13 }

    ibRdAccQuietTime OBJECT-TYPE
        SYNTAX Integer32 (0..255)
        MAX-ACCESS read-create
        STATUS current
        DESCRIPTION
        "The time for server returning active.  The unit is minute.
         When the value is 0, the server state retains active.  Default value is 5."
    ::= { ibRdAccInfoEntry 14 }

    ibRdAccFailureAction OBJECT-TYPE
        SYNTAX INTEGER
        {
            ignore(1),
            reject(2)
        }
        MAX-ACCESS read-create
        STATUS current
        DESCRIPTION
        "Defines the action that authentication should take if
        authentication succeeds but the associated accounting start
        fails.
        1 (ignore) - treat as authentication success; ignore
            accounting start failure.
        2 (reject) - treat as authentication failed if
            corresponding accounting start fails.
        Default value is 1(reject)."
    ::= { ibRdAccInfoEntry 15 }

    ibRdAccRealTime OBJECT-TYPE
        SYNTAX Integer32 (0..71582)
        MAX-ACCESS read-create
        STATUS current
        DESCRIPTION
        "Interval of realtime-accounting packets.
        The unit is defined by ibRdAccRealTimeUnit.
        When the value is 0, the device doesn't send realtime-accounting
        packets.  Default value is 12 minutes."
    ::= { ibRdAccInfoEntry 16 }

    ibRdAccRealTimeRetry OBJECT-TYPE
        SYNTAX Integer32 (1..255)
        MAX-ACCESS read-create
        STATUS current
        DESCRIPTION
        "The number of attempt the client will make when trying to send
        realtime-accounting packet to accounting server before it will
        consider the attempt failed.  Default value is 5."
        DEFVAL { 5 }
    ::= { ibRdAccInfoEntry 17 }

    ibRdAccSaveStopPktEnable OBJECT-TYPE
        SYNTAX TruthValue
        MAX-ACCESS read-create
        STATUS current
        DESCRIPTION
        "The control of whether save stop-accounting packet in local buffer
        and resend later when the accounting server doesn't respond.  When
        SaveStopPktEnable is set to false, the value of AccStopRetry will be
        ignored.  Default value is true."
    ::= { ibRdAccInfoEntry 18 }

    ibRdAccStopRetry OBJECT-TYPE
        SYNTAX Integer32 (10..65535)
        MAX-ACCESS read-create
        STATUS current
        DESCRIPTION
        "The number of attempt the client will make when trying to send
        stop-accounting packet to accounting server.  Default value is 500."
    ::= { ibRdAccInfoEntry 19 }

    ibRdAccDataFlowUnit OBJECT-TYPE
        SYNTAX INTEGER
        {
            byte(1),
            kiloByte(2),
            megaByte(3),
            gigaByte(4)
        }
        MAX-ACCESS read-create
        STATUS current
        DESCRIPTION
        "Specify data flow format that is sent to RADIUS server.  The value
        SHOULD be set the same as the value of corresponding server.
        1 (byte) -  Specify 'byte' as the unit of data flow.
        2 (kiloByte) - Specify 'kilo-byte' as the unit of data flow.
        3 (megaByte) - Specify 'mega-byte' as the unit of data flow.
        4 (gigaByte) - Specify 'giga-byte' as the unit of data flow.
        Default value is 1."
    ::= { ibRdAccInfoEntry 20 }

    ibRdAccPacketUnit OBJECT-TYPE
        SYNTAX INTEGER
        {
            onePacket(1),
            kiloPacket(2),
            megaPacket(3),
            gigaPacket(4)
        }
        MAX-ACCESS read-create
        STATUS current
        DESCRIPTION
        "Specify packet format that is sent to RADIUS server.  The value
        SHOULD be set the same as the value of corresponding server.
        1 (onePacket)  - Specify 'one-packet' as the unit of packet.
        2 (kiloPacket) - Specify 'kilo-packet' as the unit of packet.
        3 (megaPacket) - Specify 'mega-packet' as the unit of packet.
        4 (gigaPacket) - Specify 'giga-packet' as the unit of packet.
        Default value is 1."
    ::= { ibRdAccInfoEntry 21 }

    ibRdAccRowStatus   OBJECT-TYPE
        SYNTAX   RowStatus
        MAX-ACCESS  read-create
        STATUS   current
        DESCRIPTION
        "This object is responsible for managing the creation, deletion and
        modification of rows, which support active status and CreateAndGo,
        Destroy operation.  To create a new row, ibRdAccGroupName must be specified.
        To destroy an existent row, the ibRdAccGroupName MUST NOT be referred by
        ibDomainTable in ibDomainRadiusGroupName column."
    ::= { ibRdAccInfoEntry 22 }

    ibRdAcctOnEnable OBJECT-TYPE
        SYNTAX TruthValue
        MAX-ACCESS read-create
        STATUS current
        DESCRIPTION
        "The control of Accounting-On function.  The Accounting-On function is
        used by the client to mark the start of accounting (for example, upon
        booting) by sending Accounting-On packets and to mark the end of
        accounting (for example, just before a scheduled reboot) by sending
        Accounting-Off packets.  Default value is false."
    ::= { ibRdAccInfoEntry 23 }

    ibRdAcctOnSendTimes OBJECT-TYPE
        SYNTAX Integer32
        MAX-ACCESS read-create
        STATUS current
        DESCRIPTION
        "The number of Accounting-On packets the client will send before it
        considers the accounting server failed.  Default value is 50."
        DEFVAL { 50 }
    ::= { ibRdAccInfoEntry 24 }

    ibRdAcctOnSendInterval OBJECT-TYPE
        SYNTAX Integer32
        MAX-ACCESS read-create
        STATUS current
        DESCRIPTION
        "Interval of Accounting-On packets.  The unit is second.
        Default value is 3."
        DEFVAL { 3 }
    ::= { ibRdAccInfoEntry 25 }


    ibRdSecAccKey OBJECT-TYPE
        SYNTAX DisplayString(SIZE (0..64))
        MAX-ACCESS read-create
        STATUS current
        DESCRIPTION
        "The secret shared between the RADIUS client and the secondary RADIUS
        accounting server used in encoding and decoding sensitive data.
        When read, ibRdSecAccKey always returns an Octet String of length zero."
    ::= { ibRdAccInfoEntry 26 }

    ibRdPrimAccVpnName OBJECT-TYPE
        SYNTAX DisplayString(SIZE (0..31))
        MAX-ACCESS  read-create
        STATUS current
        DESCRIPTION
        "The human-readable name of the VPN in which the primary RADIUS
        accounting server is placed."
    ::= { ibRdAccInfoEntry 27 }

    ibRdSecAccVpnName OBJECT-TYPE
        SYNTAX DisplayString(SIZE (0..31))
        MAX-ACCESS  read-create
        STATUS current
        DESCRIPTION
        "The human-readable name of the VPN in which the secondary RADIUS
        accounting server is placed."
    ::= { ibRdAccInfoEntry 28 }

    ibRdAccNasIpAddrType OBJECT-TYPE
        SYNTAX InetAddressType
        MAX-ACCESS read-create
        STATUS current
        DESCRIPTION
        "The type (IPv4 or IPv6) of the source IP used to communicate with
        RADIUS accounting server."
    ::= { ibRdAccInfoEntry 29 }

    ibRdAccNasIpAddr OBJECT-TYPE
        SYNTAX IpAddress
        MAX-ACCESS read-create
        STATUS current
        DESCRIPTION
        "The source IPv4 address used to communicate with the RADIUS accounting
        server."
    ::= { ibRdAccInfoEntry 30 }

    ibRdAccNasIpv6Addr OBJECT-TYPE
        SYNTAX Ipv6Address
        MAX-ACCESS read-create
        STATUS current
        DESCRIPTION
        "The source IPv6 address used to communicate with the RADIUS accounting
        server."
    ::= { ibRdAccInfoEntry 31 }

    ibRdAccRealTimeUnit OBJECT-TYPE
        SYNTAX INTEGER
        {
            minute(0),
            second(1)
        }
        MAX-ACCESS read-create
        STATUS current
        DESCRIPTION
        "The interval unit of realtime-accounting packets.
        0  - minute.
        1  - second."
        DEFVAL { minute }
    ::= { ibRdAccInfoEntry 32 }

    ibRdAccStopPktTimeResend OBJECT-TYPE
        SYNTAX Integer32
        MAX-ACCESS read-only
        STATUS current
        DESCRIPTION
        "Interval of Stop-Accounting packets.
         0 - Not support."
    ::= { ibRdAccInfoEntry 33 }


-- ***********************************************************************
--
--  Global configurations
--
-- ***********************************************************************
    ibRadiusGlobalConfig OBJECT IDENTIFIER ::= { ibRdObjects 3 }

    ibRadiusAuthErrThreshold OBJECT-TYPE
        SYNTAX Unsigned32 (1..100)
        UNITS "percentage"
        MAX-ACCESS read-write
        STATUS current
        DESCRIPTION
            "The threshold of authentication failure trap.  A trap will be sent
            when the percent of the unsuccessful authentication exceeds this threshold."
        DEFVAL { 30 }
        ::= { ibRadiusGlobalConfig 1 }


-- ***********************************************************************
--
--  Secondary Authentication Server Table
--
-- ***********************************************************************
    ibRdSecondaryAuthServerTable  OBJECT-TYPE
        SYNTAX SEQUENCE OF IbRdSecondaryAuthServerEntry
        MAX-ACCESS not-accessible
        STATUS current
        DESCRIPTION
        "The (conceptual) table listing RADIUS secondary authentication servers."
    ::= { ibRdObjects 4 }

    ibRdSecondaryAuthServerEntry OBJECT-TYPE
        SYNTAX IbRdSecondaryAuthServerEntry
        MAX-ACCESS not-accessible
        STATUS current
        DESCRIPTION
        "An entry (conceptual row) representing a RADIUS secondary authentication server."
        INDEX { ibRdGroupName, ibRdSecondaryAuthIpAddrType, ibRdSecondaryAuthIpAddr,
                ibRdSecondaryAuthVpnName, ibRdSecondaryAuthUdpPort }
    ::= { ibRdSecondaryAuthServerTable 1 }

    IbRdSecondaryAuthServerEntry ::= SEQUENCE {
        ibRdSecondaryAuthIpAddrType       InetAddressType,
        ibRdSecondaryAuthIpAddr           InetAddress,
        ibRdSecondaryAuthVpnName          DisplayString,
        ibRdSecondaryAuthUdpPort          Integer32,
        ibRdSecondaryAuthState            INTEGER,
        ibRdSecondaryAuthKey              DisplayString,
        ibRdSecondaryAuthRowStatus        RowStatus
        }

    ibRdSecondaryAuthIpAddrType OBJECT-TYPE
        SYNTAX      InetAddressType
        MAX-ACCESS  not-accessible
        STATUS      current
        DESCRIPTION
        "The IP addresses type (IPv4 or IPv6) of secondary RADIUS authentication server."
    ::= { ibRdSecondaryAuthServerEntry 1 }

    ibRdSecondaryAuthIpAddr OBJECT-TYPE
        SYNTAX      InetAddress
        MAX-ACCESS  not-accessible
        STATUS      current
        DESCRIPTION
        "The IP address of secondary RADIUS authentication server."
    ::= { ibRdSecondaryAuthServerEntry 2 }

    ibRdSecondaryAuthVpnName OBJECT-TYPE
        SYNTAX DisplayString(SIZE (0..31))
        MAX-ACCESS  not-accessible
        STATUS current
        DESCRIPTION
        "The human-readable name of the VPN in which the secondary RADIUS
        authentication server is placed."
    ::= { ibRdSecondaryAuthServerEntry 3 }

    ibRdSecondaryAuthUdpPort OBJECT-TYPE
        SYNTAX      Integer32(1..65535)
        MAX-ACCESS  not-accessible
        STATUS      current
        DESCRIPTION
        "The UDP port the client is using to send requests to secondary
        RADIUS authentication server.  Default value is 1812."
    ::= { ibRdSecondaryAuthServerEntry 4 }

    ibRdSecondaryAuthState OBJECT-TYPE
        SYNTAX INTEGER
        {
            active(1),
            block(2)
        }
        MAX-ACCESS  read-create
        STATUS      current
        DESCRIPTION
        "The state of the secondary RADIUS authentication server.
        1 (active) The secondary authentication server is in active state.
        2 (block)  The secondary authentication server is in block state."
    ::= { ibRdSecondaryAuthServerEntry 5 }

    ibRdSecondaryAuthKey OBJECT-TYPE
        SYNTAX DisplayString(SIZE (0..64))
        MAX-ACCESS read-create
        STATUS current
        DESCRIPTION
        "The secret shared between the RADIUS client and the secondary RADIUS
        authentication server used in encoding and decoding sensitive data.
        When read, ibRdSecondaryAuthKey always returns an Octet String of length zero."
    ::= { ibRdSecondaryAuthServerEntry 6 }

    ibRdSecondaryAuthRowStatus   OBJECT-TYPE
        SYNTAX   RowStatus
        MAX-ACCESS  read-create
        STATUS   current
        DESCRIPTION
        "This object is responsible for managing the creation, deletion and
        modification of rows, which support active status and CreateAndGo,
        Destroy operation.  To create a new row, ibRdGroupName must be specified.
        The number of rows with the same ibRdGroupName can't be more than 16."
    ::= { ibRdSecondaryAuthServerEntry 7 }

-- ***********************************************************************
--
--  Secondary Accounting Server Table
--
-- ***********************************************************************
    ibRdSecondaryAccServerTable  OBJECT-TYPE
        SYNTAX SEQUENCE OF IbRdSecondaryAccServerEntry
        MAX-ACCESS not-accessible
        STATUS current
        DESCRIPTION
        "The (conceptual) table listing RADIUS secondary accounting servers."
    ::= { ibRdObjects 5 }

    ibRdSecondaryAccServerEntry OBJECT-TYPE
        SYNTAX IbRdSecondaryAccServerEntry
        MAX-ACCESS not-accessible
        STATUS current
        DESCRIPTION
        "An entry (conceptual row) representing a RADIUS secondary accounting server."
        INDEX { ibRdAccGroupName, ibRdSecondaryAccIpAddrType, ibRdSecondaryAccIpAddr,
                ibRdSecondaryAccVpnName, ibRdSecondaryAccUdpPort }
    ::= { ibRdSecondaryAccServerTable 1 }

    IbRdSecondaryAccServerEntry ::= SEQUENCE {
        ibRdSecondaryAccIpAddrType       InetAddressType,
        ibRdSecondaryAccIpAddr           InetAddress,
        ibRdSecondaryAccVpnName          DisplayString,
        ibRdSecondaryAccUdpPort          Integer32,
        ibRdSecondaryAccState            INTEGER,
        ibRdSecondaryAccKey              DisplayString,
        ibRdSecondaryAccRowStatus        RowStatus
        }

    ibRdSecondaryAccIpAddrType OBJECT-TYPE
        SYNTAX      InetAddressType
        MAX-ACCESS  not-accessible
        STATUS      current
        DESCRIPTION
        "The IP addresses type (IPv4 or IPv6) of secondary RADIUS accounting server."
    ::= { ibRdSecondaryAccServerEntry 1 }

    ibRdSecondaryAccIpAddr OBJECT-TYPE
        SYNTAX      InetAddress
        MAX-ACCESS  not-accessible
        STATUS      current
        DESCRIPTION
        "The IP address of secondary RADIUS accounting server."
    ::= { ibRdSecondaryAccServerEntry 2 }

    ibRdSecondaryAccVpnName OBJECT-TYPE
        SYNTAX DisplayString(SIZE (0..31))
        MAX-ACCESS  not-accessible
        STATUS current
        DESCRIPTION
        "The human-readable name of the VPN in which the secondary RADIUS
        accounting server is placed."
    ::= { ibRdSecondaryAccServerEntry 3 }

    ibRdSecondaryAccUdpPort OBJECT-TYPE
        SYNTAX      Integer32(1..65535)
        MAX-ACCESS  not-accessible
        STATUS      current
        DESCRIPTION
        "The UDP port the client is using to send requests to secondary
        RADIUS accounting server.  Default value is 1813."
    ::= { ibRdSecondaryAccServerEntry 4 }

    ibRdSecondaryAccState OBJECT-TYPE
        SYNTAX INTEGER
        {
            active(1),
            block(2)
        }
        MAX-ACCESS  read-create
        STATUS      current
        DESCRIPTION
        "The state of the secondary RADIUS accounting server.
        1 (active) The secondary accounting server is in active state.
        2 (block)  The secondary accounting server is in block state."
    ::= { ibRdSecondaryAccServerEntry 5 }

    ibRdSecondaryAccKey OBJECT-TYPE
        SYNTAX DisplayString(SIZE (0..64))
        MAX-ACCESS read-create
        STATUS current
        DESCRIPTION
        "The secret shared between the RADIUS client and the secondary RADIUS
        accounting server used in encoding and decoding sensitive data.
        When read, ibRdSecondaryAccKey always returns an Octet String of length zero."
    ::= { ibRdSecondaryAccServerEntry 6 }

    ibRdSecondaryAccRowStatus   OBJECT-TYPE
        SYNTAX   RowStatus
        MAX-ACCESS  read-create
        STATUS   current
        DESCRIPTION
        "This object is responsible for managing the creation, deletion and
        modification of rows, which support active status and CreateAndGo,
        Destroy operation.  To create a new row, ibRdAccGroupName must be specified.
        The number of rows with the same ibRdAccGroupName can't be more than 16."
    ::= { ibRdSecondaryAccServerEntry 7 }


-- ***********************************************************************
--
--  Supplement to RFC2620 RADIUS-ACC-CLIENT-MIB
--
-- ***********************************************************************

    ibRadiusAccounting OBJECT IDENTIFIER ::= { ibRadius 2 }

    ibRadiusAccClient OBJECT IDENTIFIER ::= { ibRadiusAccounting 1 }

    ibRadiusAccServerTable OBJECT-TYPE
        SYNTAX  SEQUENCE OF IbRadiusAccServerEntry
        MAX-ACCESS  not-accessible
        STATUS  current
        DESCRIPTION
        "The (conceptual) table listing the RADIUS accounting
        servers with which the client shares a secret."
    ::= { ibRadiusAccClient 1 }

    ibRadiusAccServerEntry OBJECT-TYPE
        SYNTAX  IbRadiusAccServerEntry
        MAX-ACCESS  not-accessible
        STATUS  current
        DESCRIPTION
        "An entry (conceptual row) representing a RADIUS accounting
        server with which a client shares a secret."
        INDEX { radiusAccServerIndex }
    ::= { ibRadiusAccServerTable 1 }

    IbRadiusAccServerEntry ::= SEQUENCE {
        ibRadiusAccClientStartRequests         Counter32,
        ibRadiusAccClientStartResponses        Counter32,
        ibRadiusAccClientInterimRequests       Counter32,
        ibRadiusAccClientInterimResponses      Counter32,
        ibRadiusAccClientStopRequests          Counter32,
        ibRadiusAccClientStopResponses         Counter32 }

    ibRadiusAccClientStartRequests   OBJECT-TYPE
        SYNTAX  Counter32
        MAX-ACCESS  read-only
        STATUS  current
        DESCRIPTION
        "The number of RADIUS accounting start request sent to this
        server."
    ::= { ibRadiusAccServerEntry  1 }

    ibRadiusAccClientStartResponses   OBJECT-TYPE
        SYNTAX  Counter32
        MAX-ACCESS  read-only
        STATUS  current
        DESCRIPTION
        "The number of RADIUS accounting start response received
        from this server."
    ::= { ibRadiusAccServerEntry  2 }

    ibRadiusAccClientInterimRequests   OBJECT-TYPE
        SYNTAX  Counter32
        MAX-ACCESS  read-only
        STATUS  current
        DESCRIPTION
        "The number of RADIUS interim accounting request sent to
        this server."
    ::= { ibRadiusAccServerEntry  3 }

    ibRadiusAccClientInterimResponses   OBJECT-TYPE
        SYNTAX  Counter32
        MAX-ACCESS  read-only
        STATUS  current
        DESCRIPTION
        "The number of RADIUS interim accounting response received
        from this server."
    ::= { ibRadiusAccServerEntry  4 }

    ibRadiusAccClientStopRequests   OBJECT-TYPE
        SYNTAX  Counter32
        MAX-ACCESS  read-only
        STATUS  current
        DESCRIPTION
        "The number of RADIUS stop accounting request sent to
        this RADIUS server."
    ::= { ibRadiusAccServerEntry  5 }

    ibRadiusAccClientStopResponses   OBJECT-TYPE
        SYNTAX  Counter32
        MAX-ACCESS  read-only
        STATUS  current
        DESCRIPTION
        "The number of RADIUS stop accounting response received
        from this server."
    ::= { ibRadiusAccServerEntry  6 }

--------------------------------------------------------------
-- Traps
--------------------------------------------------------------

-- All trap definitions should be placed under this object.
    ibRadiusServerTrap OBJECT IDENTIFIER ::= { ibRadius 3 }

    ibRadiusAuthServerDownTrap NOTIFICATION-TYPE
        OBJECTS     { radiusAuthServerAddress,
                     radiusAuthClientServerPortNumber,
                     ibRadiusServerFirstTrapTime}
        STATUS      obsolete
        DESCRIPTION
        "This trap is generated when the authentication RADIUS server
        does not respond to the client's requests for a period of time.
        This node is replaced by ibRadiusAuthenticationServerDownTrap."
    ::= { ibRadiusServerTrap 1 }

    ibRadiusAccServerDownTrap NOTIFICATION-TYPE
        OBJECTS     { radiusAccServerAddress,
                     radiusAccClientServerPortNumber,
                     ibRadiusServerFirstTrapTime}
        STATUS      obsolete
        DESCRIPTION
        "This trap is generated when the accounting RADIUS server
        does not respond to the client's requests for a period of time.
        This node is replaced by ibRadiusAccountingServerDownTrap."
    ::= { ibRadiusServerTrap 2 }

    ibRadiusServerTrapPrefix OBJECT IDENTIFIER ::= { ibRadiusServerTrap 0 }

    ibRadiusAuthServerUpTrap NOTIFICATION-TYPE
        OBJECTS     { radiusAuthServerAddress,
                     radiusAuthClientServerPortNumber,
                     ibRadiusServerFirstTrapTime }
        STATUS      obsolete
        DESCRIPTION
        "This trap is generated when the device finds that the state of the
        RADIUS authentication server changes from unreachable to reachable.
        This node is replaced by ibRadiusAuthenticationServerUpTrap."
    ::= { ibRadiusServerTrapPrefix 1 }

    ibRadiusAccServerUpTrap NOTIFICATION-TYPE
        OBJECTS     { radiusAccServerAddress,
                     radiusAccClientServerPortNumber,
                     ibRadiusServerFirstTrapTime }
        STATUS      obsolete
        DESCRIPTION
        "This trap is generated when the device finds that the state of the
        RADIUS accounting server changes from unreachable to unreachable.
        This node is replaced by ibRadiusAccountingServerUpTrap."
    ::= { ibRadiusServerTrapPrefix 2 }

    ibRadiusAuthErrTrap NOTIFICATION-TYPE
        OBJECTS     { radiusAuthServerAddress,
                      radiusAuthClientServerPortNumber }
        STATUS      current
        DESCRIPTION
        "This trap is generated when the device finds that the percent of
        unsuccessful authentication exceeds a threshold, and the threshold
        is the value of node ibRadiusAuthErrThreshold."
    ::= { ibRadiusServerTrapPrefix 3 }

    ibRadiusAuthenticationServerUpTrap NOTIFICATION-TYPE
        OBJECTS     { radiusAuthServerAddress,
                     radiusAuthClientServerPortNumber,
                     ibRadiusServerFirstTrapTime }
        STATUS      current
        DESCRIPTION
        "This trap is generated when the device finds that the state of the
        RADIUS authentication server changes from unreachable to reachable.
        The node replaces ibRadiusAuthServerUpTrap."
    ::= { ibRadiusServerTrapPrefix 4 }

    ibRadiusAccountingServerUpTrap NOTIFICATION-TYPE
        OBJECTS     { radiusAccServerAddress,
                     radiusAccClientServerPortNumber,
                     ibRadiusServerFirstTrapTime }
        STATUS      current
        DESCRIPTION
        "This trap is generated when the device finds that the state of the
        RADIUS accounting server changes from unreachable to reachable.
        The node replaces ibRadiusAccServerUpTrap."
    ::= { ibRadiusServerTrapPrefix 5 }

    ibRadiusAuthenticationServerDownTrap NOTIFICATION-TYPE
        OBJECTS     { radiusAuthServerAddress,
                     radiusAuthClientServerPortNumber,
                     ibRadiusServerFirstTrapTime}
        STATUS      current
        DESCRIPTION
        "This trap is generated when the authentication RADIUS server
        does not respond to the client's requests for a period of time.
        The node replaces ibRadiusAuthServerDownTrap."
    ::= { ibRadiusServerTrapPrefix 6 }

    ibRadiusAccountingServerDownTrap NOTIFICATION-TYPE
        OBJECTS     { radiusAccServerAddress,
                     radiusAccClientServerPortNumber,
                     ibRadiusServerFirstTrapTime}
        STATUS      current
        DESCRIPTION
        "This trap is generated when the accounting RADIUS server
        does not respond to the client's requests for a period of time.
        The node replaces ibRadiusAccServerDownTrap."
    ::= { ibRadiusServerTrapPrefix 7 }

-- ***********************************************************************
--
--  Supplement to RFC2618 RADIUS-AUTH-CLIENT-MIB
--
-- ***********************************************************************

    ibRadiusAuthenticating OBJECT IDENTIFIER ::= { ibRadius 4 }

    ibRadiusAuthClient OBJECT IDENTIFIER ::= { ibRadiusAuthenticating 1 }

    ibRadiusAuthServerTable OBJECT-TYPE
        SYNTAX  SEQUENCE OF IbRadiusAuthServerEntry
        MAX-ACCESS  not-accessible
        STATUS  current
        DESCRIPTION
        "The (conceptual) table listing the RADIUS authenticating
        servers with which the client shares a secret."
    ::= { ibRadiusAuthClient 1 }

    ibRadiusAuthServerEntry OBJECT-TYPE
        SYNTAX  IbRadiusAuthServerEntry
        MAX-ACCESS  not-accessible
        STATUS  current
        DESCRIPTION
        "An entry (conceptual row) representing a RADIUS authenticating
        server with which a client shares a secret."
        INDEX { radiusAuthServerIndex }
    ::= { ibRadiusAuthServerTable 1 }

    IbRadiusAuthServerEntry ::= SEQUENCE {
        ibRadiusAuthFailureTimes         Counter32,
        ibRadiusAuthTimeoutTimes        Counter32,
        ibRadiusAuthRejectTimes       Counter32}

    ibRadiusAuthFailureTimes   OBJECT-TYPE
        SYNTAX  Counter32
        MAX-ACCESS  read-only
        STATUS  current
        DESCRIPTION
        "The number of RADIUS authenticating failed to this server."
    ::= { ibRadiusAuthServerEntry  1 }

    ibRadiusAuthTimeoutTimes   OBJECT-TYPE
        SYNTAX  Counter32
        MAX-ACCESS  read-only
        STATUS  current
        DESCRIPTION
        "The number of RADIUS authenticating timeout to this server."
    ::= { ibRadiusAuthServerEntry  2 }

    ibRadiusAuthRejectTimes   OBJECT-TYPE
        SYNTAX  Counter32
        MAX-ACCESS  read-only
        STATUS  current
        DESCRIPTION
        "The number of RADIUS authenticating rejected to this server."
    ::= { ibRadiusAuthServerEntry  3 }


-- ***********************************************************************
--
--  Radius Extend
--
-- ***********************************************************************
    ibRadiusExtend OBJECT IDENTIFIER ::= { ibRadius 5 }

    ibRadiusExtendObjects OBJECT IDENTIFIER ::= { ibRadiusExtend 1 }
    ibRadiusExtendTables OBJECT IDENTIFIER ::= { ibRadiusExtend 2 }
    ibRadiusExtendTraps OBJECT IDENTIFIER ::= { ibRadiusExtend 3 }

-- ***********************************************************************
--
--  Radius Scheme Authentication Table
--
-- ***********************************************************************
    ibRadiusSchAuthTable OBJECT-TYPE
        SYNTAX SEQUENCE OF IbRadiusSchAuthEntry
        MAX-ACCESS not-accessible
        STATUS current
        DESCRIPTION
        "The (conceptual) table listing RADIUS authentication servers."
    ::= { ibRadiusExtendTables 1 }

    ibRadiusSchAuthEntry OBJECT-TYPE
        SYNTAX IbRadiusSchAuthEntry
        MAX-ACCESS not-accessible
        STATUS current
        DESCRIPTION
        "An entry (conceptual row) representing RADIUS authentication servers."
        INDEX { ibRadiusSchAuthGroupName}
    ::= { ibRadiusSchAuthTable 1 }

    IbRadiusSchAuthEntry ::= SEQUENCE {
        ibRadiusSchAuthGroupName           DisplayString,
        ibRadiusSchAuthPrimIpAddr          IpAddress,
        ibRadiusSchAuthPrimUdpPort         Integer32,
        ibRadiusSchAuthPrimKey             DisplayString,
        ibRadiusSchAuthSecIpAddr           IpAddress,
        ibRadiusSchAuthSecUdpPort          Integer32,
        ibRadiusSchAuthSecKey              DisplayString,
        ibRadiusSchAuthRowStatus           RowStatus
        }

    ibRadiusSchAuthGroupName OBJECT-TYPE
        SYNTAX DisplayString
        MAX-ACCESS not-accessible
        STATUS current
        DESCRIPTION
        "The name of the RADIUS authentication server group referred to in this table entry."
    ::= { ibRadiusSchAuthEntry 1 }

    ibRadiusSchAuthPrimIpAddr OBJECT-TYPE
        SYNTAX      IpAddress
        MAX-ACCESS  read-create
        STATUS      current
        DESCRIPTION
        "The IP address of primary RADIUS authenticaiton server."
    ::= { ibRadiusSchAuthEntry 2 }

    ibRadiusSchAuthPrimUdpPort OBJECT-TYPE
        SYNTAX      Integer32
        MAX-ACCESS  read-create
        STATUS      current
        DESCRIPTION
        "The UDP port the client is using to send requests to primary
        RADIUS authentication server.  Default value is 1812."
        DEFVAL { 1812 }
    ::= { ibRadiusSchAuthEntry 3 }

    ibRadiusSchAuthPrimKey OBJECT-TYPE
        SYNTAX DisplayString
        MAX-ACCESS read-create
        STATUS current
        DESCRIPTION
        "The secret shared between the RADIUS client and the primary RADIUS
        authentication server used in encoding and decoding sensitive data."
    ::= { ibRadiusSchAuthEntry 4 }

    ibRadiusSchAuthSecIpAddr OBJECT-TYPE
        SYNTAX      IpAddress
        MAX-ACCESS  read-create
        STATUS      current
        DESCRIPTION
        "The IP address of secondary RADIUS authenticaiton server."
    ::= { ibRadiusSchAuthEntry 5 }

    ibRadiusSchAuthSecUdpPort OBJECT-TYPE
        SYNTAX      Integer32
        MAX-ACCESS  read-create
        STATUS      current
        DESCRIPTION
        "The UDP port the client is using to send requests to secondary
        RADIUS authentication server.  Default value is 1812."
        DEFVAL { 1812 }
    ::= { ibRadiusSchAuthEntry 6 }

    ibRadiusSchAuthSecKey OBJECT-TYPE
        SYNTAX DisplayString
        MAX-ACCESS read-create
        STATUS current
        DESCRIPTION
        "The secret shared between the RADIUS client and the secondary RADIUS
        authentication server used in encoding and decoding sensitive data."
    ::= { ibRadiusSchAuthEntry 7 }

    ibRadiusSchAuthRowStatus   OBJECT-TYPE
        SYNTAX   RowStatus
        MAX-ACCESS  read-create
        STATUS   current
        DESCRIPTION
        "This object is responsible for managing the creation, deletion and
        modification of rows, which support active status and CreateAndGo,
        Destroy operation.
        To create a new row, ibRadiusSchAuthGroupName must be specified,
        and this action will create a corresponding domain that
        ibDomainRadiusGroupName is the same as ibRadiusSchAuthGroupName.
        To destroy an existent row, the ibRadiusSchAuthGroupName MUST NOT be
        referred by ibDomainTable in ibDomainRadiusGroupName column."
    ::= { ibRadiusSchAuthEntry 8 }


-- ***********************************************************************
--
--  Radius Scheme Accounting Table
--
-- ***********************************************************************
    ibRadiusSchAccTable OBJECT-TYPE
        SYNTAX SEQUENCE OF IbRadiusSchAccEntry
        MAX-ACCESS not-accessible
        STATUS current
        DESCRIPTION
        "The (conceptual) table listing RADIUS accounting servers."
    ::= { ibRadiusExtendTables 2 }

    ibRadiusSchAccEntry OBJECT-TYPE
        SYNTAX IbRadiusSchAccEntry
        MAX-ACCESS not-accessible
        STATUS current
        DESCRIPTION
        "An entry (conceptual row) representing RADIUS accounting servers."
        INDEX { ibRadiusSchAccGroupName}
    ::= { ibRadiusSchAccTable 1 }

    IbRadiusSchAccEntry ::= SEQUENCE {
        ibRadiusSchAccGroupName           DisplayString,
        ibRadiusSchAccPrimIpAddr          IpAddress,
        ibRadiusSchAccPrimUdpPort         Integer32,
        ibRadiusSchAccPrimKey             DisplayString,
        ibRadiusSchAccSecIpAddr           IpAddress,
        ibRadiusSchAccSecUdpPort          Integer32,
        ibRadiusSchAccSecKey              DisplayString,
        ibRadiusSchAccRowStatus           RowStatus
        }

    ibRadiusSchAccGroupName OBJECT-TYPE
        SYNTAX DisplayString
        MAX-ACCESS not-accessible
        STATUS current
        DESCRIPTION
        "The name of the RADIUS accounting server group referred to in this table entry."
    ::= { ibRadiusSchAccEntry 1 }

    ibRadiusSchAccPrimIpAddr OBJECT-TYPE
        SYNTAX      IpAddress
        MAX-ACCESS  read-create
        STATUS      current
        DESCRIPTION
        "The IP address of primary RADIUS accounting server."
    ::= { ibRadiusSchAccEntry 2 }

    ibRadiusSchAccPrimUdpPort OBJECT-TYPE
        SYNTAX      Integer32
        MAX-ACCESS  read-create
        STATUS      current
        DESCRIPTION
        "The UDP port the client is using to send requests to primary
        RADIUS accounting server.  Default value is 1813."
        DEFVAL { 1813 }
    ::= { ibRadiusSchAccEntry 3 }

    ibRadiusSchAccPrimKey OBJECT-TYPE
        SYNTAX DisplayString
        MAX-ACCESS read-create
        STATUS current
        DESCRIPTION
        "The secret shared between the RADIUS client and the primary RADIUS
        accounting server used in encoding and decoding sensitive data."
    ::= { ibRadiusSchAccEntry 4 }

    ibRadiusSchAccSecIpAddr OBJECT-TYPE
        SYNTAX      IpAddress
        MAX-ACCESS  read-create
        STATUS      current
        DESCRIPTION
        "The IP address of secondary RADIUS accounting server."
    ::= { ibRadiusSchAccEntry 5 }

    ibRadiusSchAccSecUdpPort OBJECT-TYPE
        SYNTAX      Integer32
        MAX-ACCESS  read-create
        STATUS      current
        DESCRIPTION
        "The UDP port the client is using to send requests to secondary
        RADIUS accounting server.  Default value is 1813."
        DEFVAL { 1813 }
    ::= { ibRadiusSchAccEntry 6 }

    ibRadiusSchAccSecKey OBJECT-TYPE
        SYNTAX DisplayString
        MAX-ACCESS read-create
        STATUS current
        DESCRIPTION
        "The secret shared between the RADIUS client and the secondary RADIUS
        accounting server used in encoding and decoding sensitive data."
    ::= { ibRadiusSchAccEntry 7 }

    ibRadiusSchAccRowStatus   OBJECT-TYPE
        SYNTAX   RowStatus
        MAX-ACCESS  read-create
        STATUS   current
        DESCRIPTION
        "This object is responsible for managing the creation, deletion and
        modification of rows, which support active status and CreateAndGo,
        Destroy operation.
        To create a new row, ibRadiusSchAccGroupName must be specified,
        and this action will create a corresponding domain that
        ibDomainRadiusGroupName is the same as ibRadiusSchAccGroupName.
        To destroy an existent row, the ibRadiusSchAccGroupName MUST NOT be
        referred by ibDomainTable in ibDomainRadiusGroupName column."
    ::= { ibRadiusSchAccEntry 8 }
-- ***********************************************************************
--
-- RADIUS ACCOUNT STATISTIC
--
-- ***********************************************************************
ibRadiusStatistic OBJECT IDENTIFIER ::= { ibRadius 6 }

ibRadiusStatAccReq OBJECT-TYPE
    SYNTAX      Counter64
    MAX-ACCESS  read-only
    STATUS      current
    DESCRIPTION
        "It shows the number of radius account request to the
        radius server."
    ::= { ibRadiusStatistic 1 }

ibRadiusStatAccAck OBJECT-TYPE
    SYNTAX      Counter64
    MAX-ACCESS  read-only
    STATUS      current
    DESCRIPTION
        "It shows the number of radius account response from the
         radius server."
    ::= { ibRadiusStatistic 2 }

ibRadiusStatLogoutReq OBJECT-TYPE
    SYNTAX      Counter64
    MAX-ACCESS  read-only
    STATUS      current
    DESCRIPTION
        "It shows the number of logout request to the radius server."
    ::= { ibRadiusStatistic 3 }

ibRadiusStatLogoutAck OBJECT-TYPE
    SYNTAX      Counter64
    MAX-ACCESS  read-only
    STATUS      current
    DESCRIPTION
        "It shows the number of logout response from the radius server."
    ::= { ibRadiusStatistic 4 }

ibRadiusServerTrapVarObjects OBJECT IDENTIFIER ::= { ibRadius 7 }

ibRadiusServerFirstTrapTime OBJECT-TYPE
    SYNTAX      TimeTicks
    MAX-ACCESS  accessible-for-notify
    STATUS      current
    DESCRIPTION
        "Represents the first trap time."
    ::= { ibRadiusServerTrapVarObjects 1 }

-- ***********************************************************************
--
-- RADIUS STOP-ACCOUNTING CACHE TRAP
--
-- ***********************************************************************
ibRadiusAccCachePacketTrap OBJECT IDENTIFIER ::= { ibRadius 8 }

ibRadiusAccCacheNotifications OBJECT IDENTIFIER ::= { ibRadiusAccCachePacketTrap 0 }

ibRadiusAccCacheAlarm NOTIFICATION-TYPE
    OBJECTS     { ibRadiusAccCacheMaxPackets,
                 ibRadiusAccCacheUpperValue}
    STATUS      current
    DESCRIPTION
        "This trap is generated when the ratio of the number of buffered
         RADIUS stop-accounting packets to the maximum number reaches
         the upper threshold."
    ::= { ibRadiusAccCacheNotifications 1 }

ibRadiusAccCacheResume NOTIFICATION-TYPE
    OBJECTS     { ibRadiusAccCacheMaxPackets,
                 ibRadiusAccCacheLowerValue}
    STATUS      current
    DESCRIPTION
        "This trap is generated when the ratio of the number of buffered
         RADIUS stop-accounting packets to the maximum number drops below
         the lower threshold."
    ::= { ibRadiusAccCacheNotifications 2 }

ibRadiusAccCachePacketDiscard NOTIFICATION-TYPE
    OBJECTS     { ibRadiusAccCacheMemoryUsage,
                 ibRadiusAccCachePackets}
    STATUS      current
    DESCRIPTION
        "This trap is generated when the device discards
         RADIUS stop-accounting packets because the memory usage
         has reached the minor alarm threshold."
    ::= { ibRadiusAccCacheNotifications 3 }

ibRadiusAccCacheVarObjects OBJECT IDENTIFIER ::= { ibRadiusAccCachePacketTrap 1 }

ibRadiusAccCacheMaxPackets OBJECT-TYPE
    SYNTAX Integer32 (256..2147483647)
    MAX-ACCESS accessible-for-notify
    STATUS current
    DESCRIPTION
        "Maximum number of RADIUS stop-accounting packets that can be buffered."
    ::= { ibRadiusAccCacheVarObjects 1 }

ibRadiusAccCacheUpperValue OBJECT-TYPE
    SYNTAX Integer32 (1..100)
    MAX-ACCESS accessible-for-notify
    STATUS current
    DESCRIPTION
        "Upper threshold for the ratio of the number of buffered
         RADIUS stop-accounting packets to the maximum number of
         RADIUS stop-accounting packets that can be buffered."
    ::= { ibRadiusAccCacheVarObjects 2 }

ibRadiusAccCacheLowerValue OBJECT-TYPE
    SYNTAX Integer32 (0..99)
    MAX-ACCESS accessible-for-notify
    STATUS current
    DESCRIPTION
        "Lower threshold for the ratio of the number of buffered
         RADIUS stop-accounting packets to the maximum number of
         RADIUS stop-accounting packets that can be buffered."
    ::= { ibRadiusAccCacheVarObjects 3 }

ibRadiusAccCacheMemoryUsage OBJECT-TYPE
    SYNTAX Integer32 (0..100)
    MAX-ACCESS accessible-for-notify
    STATUS current
    DESCRIPTION
        "Current memory usage of the device."
    ::= { ibRadiusAccCacheVarObjects 4 }

ibRadiusAccCachePackets OBJECT-TYPE
    SYNTAX Integer32 (0..2147483647)
    MAX-ACCESS accessible-for-notify
    STATUS current
    DESCRIPTION
        "Current number of buffered RADIUS stop-accounting packets."
    ::= { ibRadiusAccCacheVarObjects 5 }

END
