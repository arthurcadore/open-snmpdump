-- =================================================================
-- Copyright (C) 2023 Intelbras S.A. All rights reserved.
--
-- Description: Resilient Controllable Routing MIB
-- Reference:
-- Version: V1.1
-- History:
--   V1.0 2005-04-06 created by ZhangQiang
--     Initial version
--   V1.1 2005-06-28 modified by TanZhi and DaiRuiqiang
--     Rewrite the whole MIB
-- =================================================================
IB-RCR-MIB DEFINITIONS ::= BEGIN

    IMPORTS
        ibCommon
            FROM IB-OID-MIB
        InterfaceIndex
            FROM IF-MIB
        InetAddressType, InetAddress
            FROM INET-ADDRESS-MIB
        Integer32, OBJECT-TYPE, MODULE-IDENTITY, NOTIFICATION-TYPE
            FROM SNMPv2-SMI;

    ibRcr MODULE-IDENTITY
        LAST-UPDATED "200506281936Z"        -- June 28, 2005 at 19:36 GMT
        ORGANIZATION
            "Intelbras S.A. Industria de Telecomunicacao Eletronica Brasileria."
        CONTACT-INFO
            ""
        DESCRIPTION
            "This MIB is applicable to router-devices. It's made for RCR
            (Resilient Controllable Routing).
            RCR provides an effective resolution which can dynamically auto-adjust
            outbound traffic to the optimal external interface by monitoring the 
            performance and traffic load of each external interface. It provides 
            the functions of intelligentized traffic load distribution and the optimal external interface
            selection. This can optimally utilize the external interfaces. Furthermore,
            RCR realized the function which can select the optimal external interface
            based on different classes of operation flow."
        REVISION "200506281936Z"        -- June 28, 2005 at 19:36 GMT
        DESCRIPTION
            "The modified revision of this MIB module. Rewrite the whole MIB."
        ::= { ibCommon 48 }
--
-- Node definitions
--


-- The member router-device(MR) information is defined here.
    ibRcrMR OBJECT IDENTIFIER ::= { ibRcr 1 }

-- Scalar MIB objects, which are considered as global variables
-- to all member router-devices, are defined in this section.
-- This group contains global variables of all member router-devices which
-- are controlled by RCR.

    ibRcrMRGroup OBJECT IDENTIFIER ::= {   ibRcrMR 1  }

    ibRcrMRAllMaxUsedBandRate OBJECT-TYPE
        SYNTAX Integer32 (1..100)
        UNITS "%"
        MAX-ACCESS read-write
        STATUS current
        DESCRIPTION
            "The max used band rate of all external interfaces on member
            router-devices(MRs) which are controlled by RCR."
        ::= { ibRcrMRGroup 1 }

    ibRcrMRAllMinUsedBandRate OBJECT-TYPE
        SYNTAX Integer32 (0..100)
        UNITS "%"
        MAX-ACCESS read-write
        STATUS current
        DESCRIPTION
            "The min used band rate of all external interfaces on MRs
            which are controlled by RCR."
        ::= { ibRcrMRGroup 2 }


    ibRcrMRListenTime OBJECT-TYPE
        SYNTAX Integer32 (1..1440)
        UNITS "minute"
        MAX-ACCESS read-write
        STATUS current
        DESCRIPTION
            "The persistent time of a probe on member router-device(MR) which is
            controlled by RCR."
        ::= { ibRcrMRGroup 3 }


    ibRcrMRStateTable OBJECT-TYPE
        SYNTAX SEQUENCE OF IbRcrMRStateEntry
        MAX-ACCESS not-accessible
        STATUS current
        DESCRIPTION
            "This table contains state information of each MR
            which is controlled by RCR."
        ::= { ibRcrMR 2 }

    ibRcrMRStateEntry OBJECT-TYPE
        SYNTAX IbRcrMRStateEntry
        MAX-ACCESS not-accessible
        STATUS current
        DESCRIPTION
            "Entry items"
        INDEX { ibRcrMRName }
        ::= { ibRcrMRStateTable 1 }

    IbRcrMRStateEntry ::=
        SEQUENCE {
            ibRcrMRName
                OCTET STRING,
            ibRcrMRState
                INTEGER,
            ibRcrMRAuthType
                INTEGER,
            ibRcrMRAuthPwd
                OCTET STRING
                 }

    ibRcrMRName OBJECT-TYPE
        SYNTAX OCTET STRING (SIZE(1..32))
        MAX-ACCESS not-accessible
        STATUS current
        DESCRIPTION
            "The name of MR which is controlled by RCR."
        ::= { ibRcrMRStateEntry 1 }

    ibRcrMRState OBJECT-TYPE
        SYNTAX INTEGER
            {
            down(1),
            up(2),
            controlled(3)
            }
        MAX-ACCESS read-only
        STATUS current
        DESCRIPTION
            "The state of MR where identified on the controller
            router-device(CR).
            down: The MR has been enabled but has not connected
                  to the CR with TCP connection.
            up: The MR has already successfully connected to
                the CR but has not been ready for adjusting
                route.
            controlled: The MR has already passed the
                        consultation with the CR and could
                        be controlled by it."
        ::= { ibRcrMRStateEntry 2 }

     ibRcrMRAuthType OBJECT-TYPE
        SYNTAX INTEGER
            {
            simple(1),
            md5(2)
            }
        MAX-ACCESS read-write
        STATUS current
        DESCRIPTION
            "The authentication type of communication packet between CR and MR."
        ::= { ibRcrMRStateEntry 3 }

    ibRcrMRAuthPwd OBJECT-TYPE
        SYNTAX OCTET STRING
        MAX-ACCESS read-write
        STATUS current
        DESCRIPTION
            "The authentication password of communication packet between CR
            and MR.
            Reading this object always results in an OCTET STRING of length zero;
            authentication may not be bypassed by reading the MIB object."
        ::= { ibRcrMRStateEntry 4 }

    ibRcrMROutIfStateTable OBJECT-TYPE
        SYNTAX SEQUENCE OF IbRcrMROutIfStateEntry
        MAX-ACCESS not-accessible
        STATUS current
        DESCRIPTION
            "This table contains the external interface states of each MR
            which is controlled by RCR."
        ::= { ibRcrMR 3 }

    ibRcrMROutIfStateEntry OBJECT-TYPE
        SYNTAX IbRcrMROutIfStateEntry
        MAX-ACCESS not-accessible
        STATUS current
        DESCRIPTION
            "Entry items"
        INDEX { ibRcrMRName, ibRcrMROutIfName }
        ::= { ibRcrMROutIfStateTable 1 }

    IbRcrMROutIfStateEntry ::=
        SEQUENCE {
            ibRcrMROutIfName
                OCTET STRING,
            ibRcrMROutIfState
                INTEGER,
            ibRcrMROutIfMaxUsedBandRate
                Integer32,
            ibRcrMROutIfMinUsedBandRate
                Integer32,
            ibRcrMROutIfUsedBandRate
                Integer32
                 }

    ibRcrMROutIfName OBJECT-TYPE
        SYNTAX OCTET STRING (SIZE(1..48))
        MAX-ACCESS not-accessible
        STATUS current
        DESCRIPTION
            "The name of external interface on each MR."
        ::= { ibRcrMROutIfStateEntry 1 }

    ibRcrMROutIfState OBJECT-TYPE
        SYNTAX INTEGER
            {
            down(1),
            up(2),
            notExist(3)
            }
        MAX-ACCESS read-only
        STATUS current
        DESCRIPTION
            "The state of external interface on each MR."
        ::= { ibRcrMROutIfStateEntry 2 }

    ibRcrMROutIfMaxUsedBandRate OBJECT-TYPE
        SYNTAX Integer32 (1..100)
        UNITS "%"
        MAX-ACCESS read-write
        STATUS current
        DESCRIPTION
            "The max spendable bandwidth rate on external interface."
        ::= { ibRcrMROutIfStateEntry 3 }

    ibRcrMROutIfMinUsedBandRate OBJECT-TYPE
        SYNTAX Integer32 (0..100)
        UNITS "%"
        MAX-ACCESS read-write
        STATUS current
        DESCRIPTION
            "The min spendable bandwidth rate on external interface."
        ::= { ibRcrMROutIfStateEntry 4 }

    ibRcrMROutIfUsedBandRate  OBJECT-TYPE
        SYNTAX Integer32 (0..100)
        UNITS "%"
        MAX-ACCESS read-only
        STATUS current
        DESCRIPTION
            "The used bandwidth rate on external interface."
        ::= { ibRcrMROutIfStateEntry 5 }

-- The controller router-device information are defined here.
   ibRcrCR OBJECT IDENTIFIER ::= { ibRcr 2 }

-- Scalar MIB objects, which are considered as global variables
-- to all member router-devices, are defined in this section.
    ibRcrCRGroup OBJECT IDENTIFIER ::= {   ibRcrCR 1  }

    ibRcrCRState OBJECT-TYPE
        SYNTAX INTEGER
            {
            down(1),
            init(2),
            active(3)
            }
        MAX-ACCESS read-only
        STATUS current
        DESCRIPTION
            "The state of the CR which is controlled
            by RCR.
            down: The CR has been enabled but has not
                  started a TCP connection server.
            init: The CR has started a TCP connection
                  server and has been waiting for MR
                  connection, but has not been ready for adjusting route.
            active: The CR is ready for adjusting route."
        ::= { ibRcrCRGroup 1 }

    ibRcrCRPortNum OBJECT-TYPE
        SYNTAX Integer32
        MAX-ACCESS read-write
        STATUS current
        DESCRIPTION
            "The communication port number between CR and MR."
        ::= { ibRcrCRGroup 2 }

     ibRcrCRCtrlMode OBJECT-TYPE
        SYNTAX INTEGER
            {
            control(1),
            observe(2)
            }
        MAX-ACCESS read-write
        STATUS current
        DESCRIPTION

            "The observe mode or control mode is configured to operate in the CR.
             observe: The CR monitors prefixes and external interfaces based on default
                      and user-defined policies and then reports the status of
                      the network and the decisions that should be made but does
                      not implement any changes.
             controlled: The CR monitors prefixes and external interfaces based on default
                         and user-defined policies and then reports the status
                         of the network and the decisions that should be made
                         and implement any changes."
       ::= { ibRcrCRGroup 3 }

    ibRcrCRChooseMode OBJECT-TYPE
        SYNTAX INTEGER
        {
        good(1),
        best(2)
        }
        MAX-ACCESS read-write
        STATUS current
        DESCRIPTION
            "The algorithm used to choose an alternative external interface for a prefix.
             good: The first external interface that conforms to the policy is selected as
                   the new external interface.
             best: Information is collected from all external interfaces and the best one
                   is selected even though the best external interface may not be in-policy."
        ::= { ibRcrCRGroup 4 }

    ibRcrCRKeepaliveTime OBJECT-TYPE
        SYNTAX Integer32 (1..1000)
        UNITS "second"
        MAX-ACCESS read-write
        STATUS current
        DESCRIPTION
            "The interval time of the transmission of the keepalive communication
             packet between CR and MR."
        ::= { ibRcrCRGroup 5 }


    ibRcrCRPolicyMode OBJECT-TYPE
        SYNTAX INTEGER
            {
            prefix(1),
            operation(2),
            study(3)
            }
        MAX-ACCESS read-write
        STATUS current
        DESCRIPTION
            "The chosen policy mode which decides to change what prefix.
            prefix: An RCR policy is designed to select IP prefixes or to
                     select RCR learn policies using a match clause and then to
                     apply RCR policy configurations using a set clause.
            operation: To deside to adjusted prefixes based on operation
                        which user configured.
            study: To learn and optimize prefixes based on the highest
                    throughput or the highest delay."
        ::= { ibRcrCRGroup 6 }

    ibRcrCRStudyMode OBJECT-TYPE
        SYNTAX INTEGER
            {
            maxThoughout(1),
            maxDelay(2)
            }
        MAX-ACCESS read-write
        STATUS current
        DESCRIPTION
            "The mode of collecting prefix in studying configuration mode.
            It's to collect either the prefix of max thoughtout or the prefix
            of max delay time. It doesn't have a value when CR isn't in studying
            configuration mode."
        ::= { ibRcrCRGroup 7 }

    ibRcrCRStudyIpPrefixNum OBJECT-TYPE
        SYNTAX Integer32 (1..2500)
        MAX-ACCESS read-write
        STATUS current
        DESCRIPTION
            "The max number of collecting prefix in studying configuration mode."
        ::= { ibRcrCRGroup 8 }

	ibRcrCRIpPrefixLen OBJECT-TYPE
        SYNTAX Integer32 (1..32)
        MAX-ACCESS read-write
        STATUS current
        DESCRIPTION
            "The mask length of collecting prefix in configuration mode."
        DEFVAL { 24 }
        ::= { ibRcrCRGroup 9 }

--RCR policy table is defined here.
    ibRcrCRRcrPolicyTable OBJECT-TYPE
        SYNTAX SEQUENCE OF IbRcrCRRcrPolicyEntry
        MAX-ACCESS not-accessible
        STATUS current
        DESCRIPTION
            "This table contains objects to get statistic information
            of interfaces on a device."
        ::= { ibRcrCR 2 }

    ibRcrCRRcrPolicyEntry OBJECT-TYPE
        SYNTAX IbRcrCRRcrPolicyEntry
        MAX-ACCESS not-accessible
        STATUS current
        DESCRIPTION
            "Entry items"
        INDEX { ibRcrCRRcrPlyID }
        ::= { ibRcrCRRcrPolicyTable 1 }

    IbRcrCRRcrPolicyEntry ::=
        SEQUENCE {
            ibRcrCRRcrPlyID
                Integer32,
            ibRcrCRRcrPlyMatchIPListName
                OCTET STRING,
            ibRcrCRRcrPlyMatchStudyEnable
                INTEGER,
            ibRcrCRRcrPlyMatchOperPlyName
                OCTET STRING,
            ibRcrCRRcrAclNumber
                Integer32,
            ibRcrCRRcrPlyDelayTime
                Integer32,
            ibRcrCRRcrPlyLossRate
                Integer32
                  }

    ibRcrCRRcrPlyID OBJECT-TYPE
        SYNTAX Integer32
        MAX-ACCESS not-accessible
        STATUS current
        DESCRIPTION
            "The ID of RCR policy which the user has configured."
        ::= { ibRcrCRRcrPolicyEntry 1 }

    ibRcrCRRcrPlyMatchIPListName OBJECT-TYPE
        SYNTAX OCTET STRING  (SIZE(1..19))
        MAX-ACCESS read-write
        STATUS current
        DESCRIPTION
            "The matched IP prefix list name of RCR policy which the user has
            configured."
        ::= { ibRcrCRRcrPolicyEntry 2 }

    ibRcrCRRcrPlyMatchStudyEnable OBJECT-TYPE
        SYNTAX INTEGER
            {
            disable(1),
            enable(2)
            }
        MAX-ACCESS read-write
        STATUS current
        DESCRIPTION
            "Whether the RCR policy which the user has configured is matched
            for studying prefix mode."
        ::= { ibRcrCRRcrPolicyEntry 3 }

    ibRcrCRRcrPlyMatchOperPlyName OBJECT-TYPE
        SYNTAX OCTET STRING  (SIZE(1..19))
        MAX-ACCESS read-write
        STATUS current
        DESCRIPTION
            "The matched operation policy name of RCR policy which the user
            has configured."
        ::= { ibRcrCRRcrPolicyEntry 4 }

   ibRcrCRRcrAclNumber OBJECT-TYPE
        SYNTAX Integer32 (3000..3999)
        MAX-ACCESS read-write
        STATUS current
        DESCRIPTION
            "The matched acl number of RCR operation policy which the user
            has configured."
        ::= { ibRcrCRRcrPolicyEntry 5 }

    ibRcrCRRcrPlyDelayTime OBJECT-TYPE
        SYNTAX Integer32  (1..10000)
        UNITS "millisecond"
        MAX-ACCESS read-write
        STATUS current
        DESCRIPTION
            "The absolute maximum delay time. The range of values that can be
            configured is from 1 to 10000."
        ::= { ibRcrCRRcrPolicyEntry 6 }

    ibRcrCRRcrPlyLossRate OBJECT-TYPE
        SYNTAX Integer32 (1..100)
        UNITS "%"
        MAX-ACCESS read-write
        STATUS current
        DESCRIPTION
            "The packet loss percent of prefix which the CR concerns."
        ::= { ibRcrCRRcrPolicyEntry 7 }

--Matched prefix performance table define
    ibRcrCRMatPrefixPerfTable OBJECT-TYPE
        SYNTAX SEQUENCE OF IbRcrCRMatPrefixPerfEntry
        MAX-ACCESS not-accessible
        STATUS current
        DESCRIPTION
            "This table contains the matched prefix performance
            information."
        ::= { ibRcrCR 3 }

    ibRcrCRMatPrefixPerfEntry OBJECT-TYPE
        SYNTAX IbRcrCRMatPrefixPerfEntry
        MAX-ACCESS not-accessible
        STATUS current
        DESCRIPTION
            "Entry items"
        INDEX { ibRcrCRMatPrefPerfAddrType, ibRcrCRMatPrefPerfDestIPAddr,
                ibRcrCRMatPrefPerfDestMaskLen }
        ::= { ibRcrCRMatPrefixPerfTable 1 }

    IbRcrCRMatPrefixPerfEntry ::=
        SEQUENCE {
            ibRcrCRMatPrefPerfAddrType
                InetAddressType,
            ibRcrCRMatPrefPerfDestIPAddr
                InetAddress,
            ibRcrCRMatPrefPerfDestMaskLen
                Integer32,
            ibRcrCRMatPrefPerfDelayTime
                Integer32,
            ibRcrCRMatPrefPerfLossRate
                Integer32,
            ibRcrCRMatPrefPerfThroughput
                Integer32
                    }

    ibRcrCRMatPrefPerfAddrType OBJECT-TYPE
        SYNTAX InetAddressType
        MAX-ACCESS not-accessible
        STATUS current
        DESCRIPTION
            "The destination IP addresses type of matched prefix which the CR
            wants (IPv4 or IPv6)."
        ::= { ibRcrCRMatPrefixPerfEntry 1 }

    ibRcrCRMatPrefPerfDestIPAddr OBJECT-TYPE
        SYNTAX InetAddress
        MAX-ACCESS not-accessible
        STATUS current
        DESCRIPTION
            "The destination IP address of matched prefix which the CR wants."
        ::= { ibRcrCRMatPrefixPerfEntry 2 }

    ibRcrCRMatPrefPerfDestMaskLen OBJECT-TYPE
        SYNTAX Integer32 (0..32)
        MAX-ACCESS not-accessible
        STATUS current
        DESCRIPTION
            "The destination IP address mask length of matched prefix which
            the CR wants."
        ::= { ibRcrCRMatPrefixPerfEntry 3 }

    ibRcrCRMatPrefPerfDelayTime OBJECT-TYPE
        SYNTAX Integer32  (1..10000)
        UNITS "second"
        MAX-ACCESS read-only
        STATUS current
        DESCRIPTION
            "The absolute maximum delay time of prefix which the CR has
            configured."
        ::= { ibRcrCRMatPrefixPerfEntry 4 }

    ibRcrCRMatPrefPerfLossRate OBJECT-TYPE
        SYNTAX Integer32 (1..100)
        UNITS "%"
        MAX-ACCESS read-only
        STATUS current
        DESCRIPTION
            "The packet loss percent of prefix which the CR has configured."
        ::= { ibRcrCRMatPrefixPerfEntry 5 }

    ibRcrCRMatPrefPerfThroughput OBJECT-TYPE
        SYNTAX Integer32
        UNITS "kb"
        MAX-ACCESS read-only
        STATUS current
        DESCRIPTION
            "The bandwidth of prefix which the CR has monitored."
        ::= { ibRcrCRMatPrefixPerfEntry 6 }

--Adjusted prefix table define
    ibRcrCRAdjustPrefixTable OBJECT-TYPE
        SYNTAX SEQUENCE OF IbRcrCRAdjustPrefixEntry
        MAX-ACCESS not-accessible
        STATUS current
        DESCRIPTION
            "This table contains objects to get adjusted prefix information
            which the CR controlled."
        ::= { ibRcrCR 4 }

    ibRcrCRAdjustPrefixEntry OBJECT-TYPE
        SYNTAX IbRcrCRAdjustPrefixEntry
        MAX-ACCESS not-accessible
        STATUS current
        DESCRIPTION
            "Entry items"
        INDEX { ibRcrCRAdjuPrefDestAddrType, ibRcrCRAdjuPrefDestAddr,
        	   ibRcrCRAdjuPrefMaskLen, ibRcrCRAdjuPrefPreMRName,
        	   ibRcrCRAdjuPrefPreOutIfName }
        ::= { ibRcrCRAdjustPrefixTable 1 }

    IbRcrCRAdjustPrefixEntry ::=
        SEQUENCE {
            ibRcrCRAdjuPrefDestAddrType
                InetAddressType,
            ibRcrCRAdjuPrefDestAddr
                InetAddress,
            ibRcrCRAdjuPrefMaskLen
                Integer32,
            ibRcrCRAdjuPrefPreMRName
                OCTET STRING,
            ibRcrCRAdjuPrefPreOutIfName
                OCTET STRING,
            ibRcrCRAdjuPrefCurMRName
                OCTET STRING,
            ibRcrCRAdjuPrefCurOutIfName
                OCTET STRING,
            ibRcrCRAdjuPrefPersistTime
                Integer32,
            ibRcrCRAdjuPrefAgeTime
                Integer32
                    }

    ibRcrCRAdjuPrefDestAddrType OBJECT-TYPE
        SYNTAX InetAddressType
        MAX-ACCESS not-accessible
        STATUS current
        DESCRIPTION
            "The IP address type of the adjusted prefix which CR controlled
            (IPv4 or IPv6)."
        ::= { ibRcrCRAdjustPrefixEntry 1 }

    ibRcrCRAdjuPrefDestAddr OBJECT-TYPE
        SYNTAX InetAddress
        MAX-ACCESS not-accessible
        STATUS current
        DESCRIPTION
            "The IP address of the adjusted prefix which CR controlled."
        ::= { ibRcrCRAdjustPrefixEntry 2 }

    ibRcrCRAdjuPrefMaskLen OBJECT-TYPE
        SYNTAX Integer32  (0..32)
        MAX-ACCESS not-accessible
        STATUS current
        DESCRIPTION
            "The IP address mask length of the adjusted prefix which CR
            controlled."
        ::= { ibRcrCRAdjustPrefixEntry 3 }

    ibRcrCRAdjuPrefPreMRName OBJECT-TYPE
        SYNTAX OCTET STRING   (SIZE(1..32))
        MAX-ACCESS not-accessible
        STATUS current
        DESCRIPTION
            "The name of the MR which the previous outbound traffic
            flows through."
        ::= { ibRcrCRAdjustPrefixEntry 4 }

    ibRcrCRAdjuPrefPreOutIfName OBJECT-TYPE
        SYNTAX OCTET STRING (SIZE(1..48))
        MAX-ACCESS not-accessible
        STATUS current
        DESCRIPTION
            "The name of the external interface on the MR which the previous
            outbound traffic flows through."
        ::= { ibRcrCRAdjustPrefixEntry 5 }

    ibRcrCRAdjuPrefCurMRName OBJECT-TYPE
        SYNTAX OCTET STRING   (SIZE(1..32))
        MAX-ACCESS read-only
        STATUS current
        DESCRIPTION
            "The name of the MR which the current outbound traffic flows through."
        ::= { ibRcrCRAdjustPrefixEntry 6 }

    ibRcrCRAdjuPrefCurOutIfName OBJECT-TYPE
        SYNTAX OCTET STRING
        MAX-ACCESS read-only
        STATUS current
        DESCRIPTION
            "The name of the external interface on the MR which the current outbound
            traffic flows through."
        ::= { ibRcrCRAdjustPrefixEntry 7 }

    ibRcrCRAdjuPrefPersistTime OBJECT-TYPE
        SYNTAX Integer32
        UNITS "second"
        MAX-ACCESS read-only
        STATUS current
        DESCRIPTION
            "The persisting time from the time which the adjusted outbound
            traffic has been adjusted by CR to now."
        ::= { ibRcrCRAdjustPrefixEntry 8 }

    ibRcrCRAdjuPrefAgeTime OBJECT-TYPE
        SYNTAX Integer32
        UNITS "second"
        MAX-ACCESS read-only
        STATUS current
        DESCRIPTION
            "The time which the adjusted prefix remains."
        ::= { ibRcrCRAdjustPrefixEntry 9 }
END
