-- ====================================================================
-- Copyright (C) 2023 Intelbras S.A. All rights reserved.
--
-- Description: DLSW Specific Features MIB
-- Reference: RFC2024
-- Version: V1.0
-- History:
--  V1.0  2005-07-20, LiuYingquan
--    Initial version
-- ====================================================================
IB-SNA-DLSW-EXT-MIB    DEFINITIONS ::= BEGIN
IMPORTS
    MODULE-IDENTITY,
    OBJECT-TYPE,
    TimeTicks,
    Integer32,
    Counter32
        FROM SNMPv2-SMI
    RowStatus
        FROM SNMPv2-TC
    ifIndex
        FROM RFC1213-MIB
    InetAddress,
    InetAddressType
        FROM INET-ADDRESS-MIB
    dlswTConnConfigEntry,
    dlswTConnOperEntry,
    dlswTConnTcpConfigEntry,
    MacAddressNC,
    LFSize,
    TAddress
        FROM DLSW-MIB

    ibCommon
        FROM IB-OID-MIB;

ibDlswExt MODULE-IDENTITY
    LAST-UPDATED "200507201900Z"        -- Jul 20, 2005 at 19:00 GMT
    ORGANIZATION
        "Intelbras S.A. Industria de Telecomunicacao Eletronica Brasileria."
    CONTACT-INFO
        ""
    DESCRIPTION
        "The MIB module for management of specific Data Link
         Switching protocol enhancements. DLSw is described in
         RFC 1795, RFC 2024 and RFC2166."
    REVISION "200507201900Z"   -- Jul 20, 2005 at 19:00 GMT
    DESCRIPTION
            "Initial version of this MIB module."
    ::= { ibCommon 62 }

ibDlswExtMIBObjects OBJECT IDENTIFIER ::= { ibDlswExt 1 }

ibdeNode           OBJECT IDENTIFIER ::= { ibDlswExtMIBObjects 1 }
ibdeTConn          OBJECT IDENTIFIER ::= { ibDlswExtMIBObjects 2 }
ibdeBridge         OBJECT IDENTIFIER ::= { ibDlswExtMIBObjects 3 }
ibdeQllc           OBJECT IDENTIFIER ::= { ibDlswExtMIBObjects 4 }
ibdeSdlc           OBJECT IDENTIFIER ::= { ibDlswExtMIBObjects 5 }
ibdeLlc2           OBJECT IDENTIFIER ::= { ibDlswExtMIBObjects 6 }
ibdeReachableCache OBJECT IDENTIFIER ::= { ibDlswExtMIBObjects 7 }
ibdeEthernetBackup OBJECT IDENTIFIER ::= { ibDlswExtMIBObjects 8 }


-- ====================================================================
-- DLSw Extension Node Objects
-- ====================================================================

ibdeNodeVendorID OBJECT-TYPE
    SYNTAX      OCTET STRING (SIZE (3))
    MAX-ACCESS  read-write
    STATUS      current
    DESCRIPTION
        "The value identifies the manufacturer's IEEE-assigned
        Organizationally Unique Identifier (OUI) of this DLSw.
        This information is reported in DLSw Capabilities
        Exchange."
    REFERENCE
        "DLSW: Switch-to-Switch Protocol RFC 1795."
    ::= { ibdeNode 1 }

ibdeNodeIpAddrType OBJECT-TYPE
    SYNTAX      InetAddressType
    MAX-ACCESS  read-write
    STATUS      current
    DESCRIPTION
        "The type of ip address: IPv4 or IPv6."
    ::= { ibdeNode 2 }

ibdeNodeLocalAddr OBJECT-TYPE
    SYNTAX      InetAddress
    MAX-ACCESS  read-write
    STATUS      current
    DESCRIPTION
        "Local peer ip address. This ip address must have been
        configured for a port on the router. If no local peer
        ip address is configured, then this object will be the
        empty string."
    DEFVAL     { ''H }    -- the empty string
    ::= { ibdeNode 3 }

ibdeNodePriority OBJECT-TYPE
    SYNTAX      Integer32 (1..5 | 65535)
    MAX-ACCESS  read-write
    STATUS      current
    DESCRIPTION
        "Peer priority advertised to remote peers in the DLSw Capabilities
        Exchange. If an end station can reach through more
        than one peer, the priority of each peer will be considered when
        a circuit is established.
        A lower priority indicates that peer will be the
        preferred choice if there are more than one path to the
        destination. A value of 65535 indicates the value is meaningless."
    DEFVAL      { 3 }
    ::= { ibdeNode 4 }

ibdeNodeInitPacingWindow OBJECT-TYPE
    SYNTAX      Integer32 (1..2000 | 65535)
    UNITS       "packets"
    MAX-ACCESS  read-write
    STATUS      current
    DESCRIPTION
        "Initial pacing window size. This is the starting size of the
        pacing window. DLSw uses an adaptive pacing flow control
        algorithm that automatically adjusts to congestion levels in
        the network. Pacing windows are used to control how many packets
        may be sent to a peer before acknowlegement.
        A value of 65535 indicates the value is meaningless."
    DEFVAL      { 40 }
    ::= { ibdeNode 5 }

ibdeNodeMaxPacingWindow OBJECT-TYPE
    SYNTAX      Integer32 (1..2000 | 65535)
    UNITS       "packets"
    MAX-ACCESS  read-write
    STATUS      current
    DESCRIPTION
        "Maximum pacing window size. This is the largest size that
        the pacing window will grow to. DLSw uses an adaptive pacing
        flow control algorithm that automatically adjusts to congestion
        levels in the network. Pacing windows are used to control
        how many packets may be sent to a peer before acknowlegement."
    DEFVAL      { 50 }
    ::= { ibdeNode 6 }

ibdeNodeKeepAliveInterval OBJECT-TYPE
    SYNTAX      Integer32 (0..2000 | 65535)
    UNITS       "seconds"
    MAX-ACCESS  read-write
    STATUS      current
    DESCRIPTION
        "Default remote peer keepalive interval in seconds.
        The keepalive parameter refers to how often DLSw peers
        send peer keep alives to each other. These periodic messages
        allow DLSw to keep track of the state of all peers.
        If set to zero, no keepalives are sent.
        A value of 65535 indicates the value is meaningless."
    DEFVAL      { 30 }
    ::= { ibdeNode 7 }

ibdeNodePermitDynamic OBJECT-TYPE
    SYNTAX      INTEGER
                {
                permitDynamic(1),
                forbidDynamic(2),
                unknown(65535)
                }
    MAX-ACCESS  read-write
    STATUS      current
    DESCRIPTION
        "To accept connections from non-configured remote peer when
        permitDynamic is specified."
    DEFVAL      { forbidDynamic }
    ::= { ibdeNode 8 }

ibdeNodeConnTimeout OBJECT-TYPE
    SYNTAX      Integer32 (1..65535)
    UNITS       "seconds"
    MAX-ACCESS  read-write
    STATUS      current
    DESCRIPTION
        "Define connected state timer."
    DEFVAL      { 300 }
    ::= { ibdeNode 9 }

ibdeNodeLocalPendTimeout OBJECT-TYPE
    SYNTAX      Integer32 (1..65535)
    UNITS       "seconds"
    MAX-ACCESS  read-write
    STATUS      current
    DESCRIPTION
        "Define connected state timer."
    DEFVAL      { 30 }
    ::= { ibdeNode 10 }

ibdeNodeRemotePendTimeout OBJECT-TYPE
    SYNTAX      Integer32 (1..65535)
    UNITS       "seconds"
    MAX-ACCESS  read-write
    STATUS      current
    DESCRIPTION
        "Define connected state timer."
    DEFVAL      { 30 }
    ::= { ibdeNode 11 }

ibdeNodeSnaCacheTimeout OBJECT-TYPE
    SYNTAX      Integer32 (1..65535)
    UNITS       "seconds"
    MAX-ACCESS  read-write
    STATUS      current
    DESCRIPTION
        "Define connected state timer."
    DEFVAL      { 120 }
    ::= { ibdeNode 12 }

ibdeNodeExplorerTimeout OBJECT-TYPE
    SYNTAX      Integer32 (1..65535)
    UNITS       "seconds"
    MAX-ACCESS  read-write
    STATUS      current
    DESCRIPTION
        "Define explorer timer."
    DEFVAL      { 30 }
    ::= { ibdeNode 13 }

ibdeNodeExplorerWaitTimeout OBJECT-TYPE
    SYNTAX      Integer32 (1..65535)
    UNITS       "seconds"
    MAX-ACCESS  read-write
    STATUS      current
    DESCRIPTION
        "Define explorer waiting timer."
    DEFVAL      { 30 }
    ::= { ibdeNode 14 }

ibdeNodeConfigSapList OBJECT-TYPE
    SYNTAX      OCTET STRING (SIZE (16))
    MAX-ACCESS  read-write
    STATUS      current
    DESCRIPTION
        "The SAP list indicates which SAPs are allowed.
        Only SAPs with even numbers are represented,
        in the form of the most significant bit of the first
        octet representing the SAP 0, the next most significant
        bit representing the SAP 2, to the least significant
        bit of the last octet representing the SAP 254. Data
        link switching is allowed for those SAPs which have
        one in its corresponding bit, not allowed otherwise.
        The whole SAP list has to be changed together. Changing
        the SAP list affects only new circuit establishments
        and has no effect on established circuits.

        This list can be used to restrict specific partners
        from knowing about all the SAPs used by DLSw on all its
        interfaces (these are represented in ibdeIfSapList for
        each interface). For instance, one may want to run NetBIOS
        with some partners but not others.

        If a node supports sending run-time capabilities exchange
        messages, changes to this object should cause that action.
        When to start the run-time capabilities exchange is
        implementation-specific.

        The DEFVAL below indicates support for SAPs 0, 2, 4, 6, 8, A, C and E."
    DEFVAL      { 'FF000000000000000000000000000000'h }
    ::= { ibdeNode 15 }

ibdeNodeMaxTransmission OBJECT-TYPE
    SYNTAX      Integer32 (1..10)
    MAX-ACCESS  read-write
    STATUS      current
    DESCRIPTION
        "The maximum retry times for TCP packet.
        Default value is 5."
    DEFVAL      { 5 }
    ::= { ibdeNode 16 }

ibdeNodeMulticastStatus OBJECT-TYPE
    SYNTAX      INTEGER
                {
                enabled(1),
                disabled(2)
                }
    MAX-ACCESS  read-write
    STATUS      current
    DESCRIPTION
        "Multicast support status. It is disabled by default."
    DEFVAL      { disabled }
    ::= { ibdeNode 17 }

ibdeNodeMulticastAddress OBJECT-TYPE
    SYNTAX      InetAddress
    MAX-ACCESS  read-write
    STATUS      current
    DESCRIPTION
        "Multicast address. Default is 224.0.10.0.
        When the ibdeNodeMulticastStatus is disabled,
        the multicast address is reset to 0.0.0.0."
    ::= { ibdeNode 18 }

ibdeNodeResetTcpAll OBJECT-TYPE
    SYNTAX      INTEGER
                {
                reset(1)
                }
    MAX-ACCESS  read-write
    STATUS      current
    DESCRIPTION
        "Reset all TCP circuit switch.
        Any return value is meaningless."
    ::= { ibdeNode 19 }

ibdeNodeStCapTcpNum OBJECT-TYPE
    SYNTAX      Integer32 (0..255)
    MAX-ACCESS  read-write
    STATUS      current
    DESCRIPTION
        "Tcp number reported in DLSw Capabilities Exchange."
    ::= { ibdeNode 20 }

ibdeNodeTcpQueueMax OBJECT-TYPE
    SYNTAX      Integer32
    MAX-ACCESS  read-write
    STATUS      current
    DESCRIPTION
        "The max length of TCP queue."
    DEFVAL      { 200 }
    ::= { ibdeNode 21 }


-- ====================================================================
-- DLSw Extension Transport Connection Configuration Table
-- ====================================================================
ibdeTConnConfigTable OBJECT-TYPE
    SYNTAX      SEQUENCE OF IbdeTConnConfigEntry
    MAX-ACCESS  not-accessible
    STATUS      current
    DESCRIPTION
        "This table defines the peer transport connections
        that will be initiated or accepted by this DLSw.

        This table augments dlswTConnConfigTable."
    ::= { ibdeTConn 1 }

ibdeTConnConfigEntry OBJECT-TYPE
    SYNTAX      IbdeTConnConfigEntry
    MAX-ACCESS  not-accessible
    STATUS      current
    DESCRIPTION
        "A list of objects that define specific configuration for
        a DLSw peer transport connection."
    AUGMENTS    { dlswTConnConfigEntry }
    ::= { ibdeTConnConfigTable 1 }

IbdeTConnConfigEntry ::=
    SEQUENCE {
        ibdeTConnConfigVersion              OCTET STRING,
        ibdeTConnConfigPriority             Integer32,
        ibdeTConnConfigLfSize               LFSize,
        ibdeTConnConfigKeepaliveIntval    Integer32,
        ibdeTConnConfigBackup               INTEGER,
        ibdeTConnConfigBackupTAddr          TAddress,
        ibdeTConnConfigBackupLinger         Integer32
    }

ibdeTConnConfigVersion OBJECT-TYPE
    SYNTAX      OCTET STRING (SIZE (2))
    MAX-ACCESS  read-create
    STATUS      current
    DESCRIPTION
        "This value identifies which version (first octet) and release
        (second octet) of the DLSw standard is supported by this
        partner DLSw. This information is obtained from a DLSw
        Capabilities Exchange message received from the partner DLSw.
        A string of zero length is returned before a Capabilities
        Exchange message is received, or if one is never received.
        A conceptual row with a ibdeTConnOperState of 'connected' but
        a zero length partner version indicates that the partner is
        a non-standard DLSw partner.

        If an implementation chooses to keep ibdeTConnOperEntrys in
        the 'disconnected' state, this value should remain unchanged."
    ::= { ibdeTConnConfigEntry 1 }

ibdeTConnConfigPriority OBJECT-TYPE
    SYNTAX      Integer32 (1..5)
    MAX-ACCESS  read-create
    STATUS      current
    DESCRIPTION
        "The priority for remote peer."
    DEFVAL      { 3 }
    ::= { ibdeTConnConfigEntry 2 }

ibdeTConnConfigLfSize OBJECT-TYPE
    SYNTAX      LFSize
    MAX-ACCESS  read-create
    STATUS      current
    DESCRIPTION
        "The largest frame size."
    ::= { ibdeTConnConfigEntry 3 }

ibdeTConnConfigKeepaliveIntval OBJECT-TYPE
    SYNTAX      Integer32 (1..1200)
    UNITS       "seconds"
    MAX-ACCESS  read-create
    STATUS      current
    DESCRIPTION
        "The keepalive interval value."
    DEFVAL      { 30 }
    ::= { ibdeTConnConfigEntry 4 }

ibdeTConnConfigBackup OBJECT-TYPE
    SYNTAX      INTEGER
                {
                yes(1),
                no(2)
                }
    MAX-ACCESS  read-create
    STATUS      current
    DESCRIPTION
        "The current remote peer is configured as the
        backup of another configured remote peer."
    DEFVAL      { no }
    ::= { ibdeTConnConfigEntry 5 }

ibdeTConnConfigBackupTAddr OBJECT-TYPE
    SYNTAX      TAddress
    MAX-ACCESS  read-create
    STATUS      current
    DESCRIPTION
        "It is the ip address of a configured remote peer of which
        the current remote peer is configrued as backup."
    ::= { ibdeTConnConfigEntry 6 }

ibdeTConnConfigBackupLinger OBJECT-TYPE
    SYNTAX      Integer32 (0..1440)
    UNITS       "minutes"
    MAX-ACCESS  read-create
    STATUS      current
    DESCRIPTION
        "Backup peer linger."
    DEFVAL      { 5 }
    ::= { ibdeTConnConfigEntry 7 }

-- ====================================================================
-- DLSw Extension Transport Connection Operation Table
-- ====================================================================
ibdeTConnOperTable OBJECT-TYPE
    SYNTAX      SEQUENCE OF IbdeTConnOperEntry
    MAX-ACCESS  not-accessible
    STATUS      current
    DESCRIPTION
        "A list of peer transport connections.
        Each connected peer will create a conceptual row in the table.
        When the peer disconnects, the row will be deleted from the table.

        This table augments dlswTConnOperTable."
    ::= { ibdeTConn 2 }

ibdeTConnOperEntry OBJECT-TYPE
    SYNTAX      IbdeTConnOperEntry
    MAX-ACCESS  not-accessible
    STATUS      current
    DESCRIPTION
        "A list of objects that contain spefific operational
        information for a DLSw peer transport connection."
    AUGMENTS    { dlswTConnOperEntry }
    ::= { ibdeTConnOperTable 1 }

IbdeTConnOperEntry ::=
    SEQUENCE {
        ibdeTConnOperPeerType         INTEGER,
        ibdeTConnOperVendorID         OCTET STRING,
        ibdeTConnOperVersionString    OCTET STRING,
        ibdeTConnOperUpTime           TimeTicks,
        ibdeTConnOperMulticastAddress TAddress,
        ibdeTConnOperStCapTcpNumber   Integer32,
        ibdeTConnOperRecvPkts         Counter32,
        ibdeTConnOperSendPkts         Counter32,
        ibdeTConnOperDropPkts         Counter32
    }

ibdeTConnOperPeerType OBJECT-TYPE
    SYNTAX      INTEGER
                {
                configured(1),
                learningDynamic(2),
                other(3)
                }
    MAX-ACCESS  read-only
    STATUS      current
    DESCRIPTION
        "The current remote peer is configured when the value is 'configured'."
    ::= { ibdeTConnOperEntry 1 }

ibdeTConnOperVendorID OBJECT-TYPE
    SYNTAX      OCTET STRING
    MAX-ACCESS  read-only
    STATUS      current
    DESCRIPTION
        "The value identifies the manufacturer's IEEE-assigned
        Organizationally Unique Identifier (OUI) of remote peer."
    ::= { ibdeTConnOperEntry 2 }

ibdeTConnOperVersionString OBJECT-TYPE
    SYNTAX      OCTET STRING
    MAX-ACCESS  read-only
    STATUS      current
    DESCRIPTION
        "Version information of remote peer. The length up to 512 bytes."
    ::= { ibdeTConnOperEntry 3 }

ibdeTConnOperUpTime OBJECT-TYPE
    SYNTAX      TimeTicks
    MAX-ACCESS  read-only
    STATUS      current
    DESCRIPTION
        "The amount of time (in seconds) since this transport
        connection last entered the 'connected' state."
    ::= { ibdeTConnOperEntry 4 }

ibdeTConnOperMulticastAddress OBJECT-TYPE
    SYNTAX      TAddress
    MAX-ACCESS  read-only
    STATUS      current
    DESCRIPTION
        "When remote peer supports DLSw2.0, this node identifies
        its multicast address."
    ::= { ibdeTConnOperEntry 5 }

ibdeTConnOperStCapTcpNumber OBJECT-TYPE
    SYNTAX      Integer32
    MAX-ACCESS  read-only
    STATUS      current
    DESCRIPTION
        "Number of tcp supported when capabilities exchanging."
    ::= { ibdeTConnOperEntry 6 }

ibdeTConnOperRecvPkts OBJECT-TYPE
    SYNTAX      Counter32
    MAX-ACCESS  read-only
    STATUS      current
    DESCRIPTION
        "The number of Switch-to-Switch Protocol (SSP) messages
        received on this tcp transport connection."
    ::= { ibdeTConnOperEntry 7 }

ibdeTConnOperSendPkts OBJECT-TYPE
    SYNTAX      Counter32
    MAX-ACCESS  read-only
    STATUS      current
    DESCRIPTION
        "The number of SSP messages
        sent on this tcp transport connection."
    ::= { ibdeTConnOperEntry 8 }

ibdeTConnOperDropPkts OBJECT-TYPE
    SYNTAX      Counter32
    MAX-ACCESS  read-only
    STATUS      current
    DESCRIPTION
        "The number of SSP messages
        dropped on this tcp transport connection."
    ::= { ibdeTConnOperEntry 9 }

-- ====================================================================
-- DLSw Extension TCP Transport Connection Specific Configuration
-- ====================================================================
ibdeTConnTcpConfigTable OBJECT-TYPE
    SYNTAX      SEQUENCE OF IbdeTConnTcpConfigEntry
    MAX-ACCESS  not-accessible
    STATUS      current
    DESCRIPTION
       "This table defines the TCP transport connections that
        will be either initiated by or accepted by this DSLw.
        It augments the entries in dlswTConnConfigTable whose
        domain is dlswTCPDomain. In other words for each conceptual row
        in the dlswTConnConfigTable, if the dlswTConnConfigTDomain is
        dlswTCPDomain, that conceptual row will be augmented by this
        table.

        dlswTCPDomain, dlswTConnConfigTable, and dlswTConnConfigTDomain
        are all imported from DLSW-MIB (RFC 2024).

        This table augments dlswTConnTcpConfigTable."
    ::= { ibdeTConn 3 }

ibdeTConnTcpConfigEntry OBJECT-TYPE
    SYNTAX      IbdeTConnTcpConfigEntry
    MAX-ACCESS  not-accessible
    STATUS      current
    DESCRIPTION
       "A list of objects that define specific configuration for
        a DLSw peer transport connection within the dlswTCPDomain.
        dlswTCPDomain is imported from DLSW-MIB (RFC 2024)."
    AUGMENTS    { dlswTConnTcpConfigEntry }
    ::= { ibdeTConnTcpConfigTable 1 }

IbdeTConnTcpConfigEntry ::=
    SEQUENCE {
        ibdeTConnTcpConfigQueueMax  Integer32
    }

ibdeTConnTcpConfigQueueMax  OBJECT-TYPE
    SYNTAX      Integer32 (50..2000)
    MAX-ACCESS  read-create
    STATUS      current
    DESCRIPTION
        "Maximum output TCP queue size for this remote peer.
        For DLSw over TCP encapsulation, packets may be queued
        due to congestion of the TCP network. This variable
        is used to set the output queue maximum of the underlying
        TCP connection for the peer represented by the conceptual row."
    DEFVAL      { 200 }
    ::= { ibdeTConnTcpConfigEntry 1 }

-- ====================================================================
-- DLSw Bridge MIB-Group
-- ====================================================================
ibdeBridgeTable OBJECT-TYPE
    SYNTAX      SEQUENCE OF IbdeBridgeEntry
    MAX-ACCESS  not-accessible
    STATUS      current
    DESCRIPTION
        "A list of bridge group which is serving for DLSw."
    ::= { ibdeBridge 1 }

ibdeBridgeEntry OBJECT-TYPE
    SYNTAX      IbdeBridgeEntry
    MAX-ACCESS  not-accessible
    STATUS      current
    DESCRIPTION
        "A list of bridge information."
    INDEX       { ibdeBridgeNumIndex }
    ::= { ibdeBridgeTable 1 }

IbdeBridgeEntry ::=
    SEQUENCE {
        ibdeBridgeNumIndex   Integer32,
        ibdeBridgeRowStatus  RowStatus
    }

ibdeBridgeNumIndex OBJECT-TYPE
    SYNTAX      Integer32 (1..255)
    MAX-ACCESS  not-accessible
    STATUS      current
    DESCRIPTION
        "This value identifies the bridge number."
    ::= { ibdeBridgeEntry 1 }

ibdeBridgeRowStatus OBJECT-TYPE
    SYNTAX      RowStatus
    MAX-ACCESS  read-create
    STATUS      current
    DESCRIPTION
        "RowStatus."
    ::= { ibdeBridgeEntry 2 }

-- ====================================================================
-- DLSw Bridge group number and interface
-- ====================================================================
ibdeBridgeIfTable OBJECT-TYPE
    SYNTAX      SEQUENCE OF IbdeBridgeIfEntry
    MAX-ACCESS  not-accessible
    STATUS      current
    DESCRIPTION
        "The list of interface on which DLSw is active."
    ::= { ibdeBridge 2 }

ibdeBridgeIfEntry OBJECT-TYPE
    SYNTAX      IbdeBridgeIfEntry
    MAX-ACCESS  not-accessible
    STATUS      current
    DESCRIPTION
        "The list of bridge interface information."
    INDEX       { ifIndex }
    ::= { ibdeBridgeIfTable 1 }

IbdeBridgeIfEntry ::=
    SEQUENCE {
        ibdeBridgeIfBrgGrp      Integer32,
        ibdeBridgeIfRowStatus   RowStatus
    }

ibdeBridgeIfBrgGrp OBJECT-TYPE
    SYNTAX      Integer32 (1..255)
    MAX-ACCESS  read-create
    STATUS      current
    DESCRIPTION
        "This value identifies the bridge number attached
        to the interface."
    ::= { ibdeBridgeIfEntry 1 }

ibdeBridgeIfRowStatus OBJECT-TYPE
    SYNTAX      RowStatus
    MAX-ACCESS  read-create
    STATUS      current
    DESCRIPTION
        "RowStatus."
    ::= { ibdeBridgeIfEntry 2 }

-- ====================================================================
-- DLSw Extension QLLC Port Configuration Table
-- ====================================================================
ibdeQllcTable  OBJECT-TYPE
    SYNTAX      SEQUENCE OF IbdeQllcEntry
    MAX-ACCESS  not-accessible
    STATUS      current
    DESCRIPTION
       "The table defines attributes related for those
        QLLC that participate in data link switching."
    ::= { ibdeQllc 1 }

ibdeQllcEntry  OBJECT-TYPE
    SYNTAX      IbdeQllcEntry
    MAX-ACCESS  not-accessible
    STATUS      current
    DESCRIPTION
       "The ifIndex belongs to the interface which link protocol is x.25."
    INDEX       { ifIndex }
    ::= { ibdeQllcTable 1 }

IbdeQllcEntry ::=
    SEQUENCE {
        ibQllcX121Address  Integer32,
        ibQllcLocalMac     MacAddressNC,
        ibQllcLocalSap     OCTET STRING,
        ibQllcRemoteMac    MacAddressNC,
        ibQllcRemoteSap    OCTET STRING,
        ibQllcRowStatus    RowStatus
    }

ibQllcX121Address  OBJECT-TYPE
    SYNTAX      Integer32
    MAX-ACCESS  read-create
    STATUS      current
    DESCRIPTION
       "X.121 address."
    ::= { ibdeQllcEntry 1 }

ibQllcLocalMac  OBJECT-TYPE
    SYNTAX      MacAddressNC
    MAX-ACCESS  read-create
    STATUS      current
    DESCRIPTION
       "The virtual MAC address used to represent the QLLC-attached
        link station to the rest of the DLSw network."
    ::= { ibdeQllcEntry 2 }

ibQllcLocalSap  OBJECT-TYPE
    SYNTAX      OCTET STRING (SIZE(1))
    MAX-ACCESS  read-create
    STATUS      current
    DESCRIPTION
       "The SAP used to represent this link station."
    ::= { ibdeQllcEntry 3 }

ibQllcRemoteMac  OBJECT-TYPE
    SYNTAX      MacAddressNC
    MAX-ACCESS  read-create
    STATUS      current
    DESCRIPTION
       "The MAC address to which DLSw should attempt to connect
        this link station. If this information is not available,
        a length of zero for this object should be returned."
    DEFVAL      { ''H }
    ::= { ibdeQllcEntry 4 }

ibQllcRemoteSap  OBJECT-TYPE
    SYNTAX      OCTET STRING (SIZE (0 | 1))
    MAX-ACCESS  read-create
    STATUS      current
    DESCRIPTION
       "The SAP of the remote station to which this link
        station should be connected. If this information
        is not available, a length of zero for this object
        should be returned."
    DEFVAL      { ''H }
    ::= { ibdeQllcEntry 5 }

ibQllcRowStatus  OBJECT-TYPE
    SYNTAX      RowStatus
    MAX-ACCESS  read-create
    STATUS      current
    DESCRIPTION
       "RowStatus."
    ::= { ibdeQllcEntry 6 }

-- ====================================================================
-- DLSw Extension SDLC Port Configuration Table
-- ====================================================================
ibdeSdlcPortTable OBJECT-TYPE
    SYNTAX      SEQUENCE OF IbdeSdlcPortEntry
    MAX-ACCESS  not-accessible
    STATUS      current
    DESCRIPTION
        "The table defines parameters for the interfaces
        whose link protocol is SDLC."
    ::= { ibdeSdlc 1 }

ibdeSdlcPortEntry OBJECT-TYPE
    SYNTAX      IbdeSdlcPortEntry
    MAX-ACCESS  not-accessible
    STATUS      current
    DESCRIPTION
        "Sdlc port entry."
    INDEX       { ifIndex }
    ::= { ibdeSdlcPortTable 1 }


IbdeSdlcPortEntry ::=
    SEQUENCE {
        ibdeSdlcPortRole                INTEGER,
        ibdeSdlcPortSendWindow          Integer32,
        ibdeSdlcPortModulo              INTEGER,
        ibdeSdlcPortMaxPdu              Integer32,
        ibdeSdlcPortMaxSendQueue        Integer32,
        ibdeSdlcPortMaxTransmission     Integer32,
        ibdeSdlcPortSimultaneousEnable  INTEGER,
        ibdeSdlcPortTimerACK            Integer32,
        ibdeSdlcPortTimerLifeTime       Integer32,
        ibdeSdlcPortTimerPollPause      Integer32,
        ibdeSdlcPortRowStatus           RowStatus
    }

ibdeSdlcPortRole OBJECT-TYPE
    SYNTAX      INTEGER
                {
                primary(1),
                seconday(2),
                norole(3)
                }
    MAX-ACCESS  read-create
    STATUS      current
    DESCRIPTION
        "The SDLC role of interface."
    DEFVAL      { norole }
    ::= { ibdeSdlcPortEntry 1 }

ibdeSdlcPortSendWindow OBJECT-TYPE
    SYNTAX      Integer32 (1..7)
    MAX-ACCESS  read-create
    STATUS      current
    DESCRIPTION
        "Size of local send window."
    DEFVAL      { 7 }
    ::= { ibdeSdlcPortEntry 2 }

ibdeSdlcPortModulo OBJECT-TYPE
    SYNTAX      INTEGER
                {
                m8(8),
                m128(128)
                }
    MAX-ACCESS  read-create
    STATUS      current
    DESCRIPTION
        "Size of modulus."
    DEFVAL      { m8 }
    ::= { ibdeSdlcPortEntry 3 }

ibdeSdlcPortMaxPdu OBJECT-TYPE
    SYNTAX      Integer32 (1..17600)
    MAX-ACCESS  read-create
    STATUS      current
    DESCRIPTION
        "Maximum bytes for incoming frames."
    DEFVAL      { 265 }
    ::= { ibdeSdlcPortEntry 4 }

ibdeSdlcPortMaxSendQueue OBJECT-TYPE
    SYNTAX      Integer32 (20..255)
    MAX-ACCESS  read-create
    STATUS      current
    DESCRIPTION
        "Size of hold queue."
    DEFVAL      { 50 }
    ::= { ibdeSdlcPortEntry 5 }

ibdeSdlcPortMaxTransmission OBJECT-TYPE
    SYNTAX      Integer32 (1..255)
    MAX-ACCESS  read-create
    STATUS      current
    DESCRIPTION
        "Number of times to retry an operation."
    DEFVAL      { 20 }
    ::= { ibdeSdlcPortEntry 6 }

ibdeSdlcPortSimultaneousEnable OBJECT-TYPE
    SYNTAX      INTEGER
                {
                enabled(1),
                disabled(2)
                }
    MAX-ACCESS  read-create
    STATUS      current
    DESCRIPTION
        "Activate SDLC two-way simultaneous mode."
    DEFVAL      { 1 }
    ::= { ibdeSdlcPortEntry 7 }

ibdeSdlcPortTimerACK OBJECT-TYPE
    SYNTAX      Integer32 (1..60000)
    UNITS       "milliseconds"
    MAX-ACCESS  read-create
    STATUS      current
    DESCRIPTION
        "Time to wait for a reply to a frame."
    DEFVAL      { 3000 }
    ::= { ibdeSdlcPortEntry 8 }

ibdeSdlcPortTimerLifeTime OBJECT-TYPE
    SYNTAX      Integer32 (1..60000)
    UNITS       "milliseconds"
    MAX-ACCESS  read-create
    STATUS      current
    DESCRIPTION
        "Time to wait for a reply used by secondary station."
    DEFVAL      { 500 }
    ::= { ibdeSdlcPortEntry 9 }

ibdeSdlcPortTimerPollPause OBJECT-TYPE
    SYNTAX      Integer32 (1..10000)
    UNITS       "milliseconds"
    MAX-ACCESS  read-create
    STATUS      current
    DESCRIPTION
        "Time between polls for each secondary SDLC station."
    DEFVAL      { 1000 }
    ::= { ibdeSdlcPortEntry 10 }

ibdeSdlcPortRowStatus OBJECT-TYPE
    SYNTAX      RowStatus
    MAX-ACCESS  read-create
    STATUS      current
    DESCRIPTION
        "RowStatus."
    ::= { ibdeSdlcPortEntry 11 }

-- ====================================================================
-- DLSw Extension LLC2 Port Configuration Table
-- ====================================================================
ibdeLlc2PortTable OBJECT-TYPE
    SYNTAX      SEQUENCE OF IbdeLlc2PortEntry
    MAX-ACCESS  not-accessible
    STATUS      current
    DESCRIPTION
        "This table defines parameters for the Ethernet interface."
    ::= { ibdeLlc2 1 }

ibdeLlc2PortEntry OBJECT-TYPE
    SYNTAX      IbdeLlc2PortEntry
    MAX-ACCESS  not-accessible
    STATUS      current
    DESCRIPTION
        "LLC2 port entry."
    INDEX       { ifIndex }
    ::= { ibdeLlc2PortTable 1 }

IbdeLlc2PortEntry ::=
    SEQUENCE {
        ibdeLlc2PortMaxAck           Integer32,
        ibdeLlc2PortMaxPdu           Integer32,
        ibdeLlc2PortMaxSendQueue     Integer32,
        ibdeLlc2PortMaxTransmission  Integer32,
        ibdeLlc2PortModulo           INTEGER,
        ibdeLlc2PortReceiveWindow    Integer32,
        ibdeLlc2PortTimerAck         Integer32,
        ibdeLlc2PortTimerAckDelay    Integer32,
        ibdeLlc2PortTimerDetect      Integer32,
        ibdeLlc2PortTimerBusy        Integer32,
        ibdeLlc2PortTimerPoll        Integer32,
        ibdeLlc2PortTimerReject      Integer32,
        ibdeLlc2PortRowStatus        RowStatus
    }

ibdeLlc2PortMaxAck OBJECT-TYPE
    SYNTAX      Integer32 (1..127)
    MAX-ACCESS  read-create
    STATUS      current
    DESCRIPTION
        "Maximum of I-frames received before ACK."
    DEFVAL      { 3 }
    ::= { ibdeLlc2PortEntry 1 }

ibdeLlc2PortMaxPdu OBJECT-TYPE
    SYNTAX      Integer32 (1..1700)
    MAX-ACCESS  read-create
    STATUS      current
    DESCRIPTION
        "Maximum of LLC2 pdu length."
    DEFVAL      { 1493 }
    ::= { ibdeLlc2PortEntry 2 }

ibdeLlc2PortMaxSendQueue OBJECT-TYPE
    SYNTAX      Integer32 (20..200)
    MAX-ACCESS  read-create
    STATUS      current
    DESCRIPTION
        "Queue for sending llc2 I-frames."
    DEFVAL      { 50 }
    ::= { ibdeLlc2PortEntry 3 }

ibdeLlc2PortMaxTransmission OBJECT-TYPE
    SYNTAX      Integer32 (1..255)
    MAX-ACCESS  read-create
    STATUS      current
    DESCRIPTION
        "Retry times of operations."
    DEFVAL      { 20 }
    ::= { ibdeLlc2PortEntry 4 }

ibdeLlc2PortModulo OBJECT-TYPE
    SYNTAX      INTEGER
                {
                m8(8),
                m128(128)
                }
    MAX-ACCESS  read-create
    STATUS      current
    DESCRIPTION
        "Modulus of LLC2."
    DEFVAL      { m128 }
    ::= { ibdeLlc2PortEntry 5 }

ibdeLlc2PortReceiveWindow OBJECT-TYPE
    SYNTAX      Integer32 (1..127)
    MAX-ACCESS  read-create
    STATUS      current
    DESCRIPTION
        "Maximum number of I-frames to send before received ACK."
    DEFVAL      { 7 }
    ::= { ibdeLlc2PortEntry 6 }

ibdeLlc2PortTimerAck OBJECT-TYPE
    SYNTAX      Integer32 (1..60000)
    UNITS       "milliseconds"
    MAX-ACCESS  read-create
    STATUS      current
    DESCRIPTION
        "Waiting for ACK time after sending an I-frame."
    DEFVAL      { 200 }
    ::= { ibdeLlc2PortEntry 7 }

ibdeLlc2PortTimerAckDelay OBJECT-TYPE
    SYNTAX      Integer32 (1..60000)
    UNITS       "milliseconds"
    MAX-ACCESS  read-create
    STATUS      current
    DESCRIPTION
        "Maximum time allows I-frames incoming without replay ACK."
    DEFVAL      { 100 }
    ::= { ibdeLlc2PortEntry 8 }

ibdeLlc2PortTimerDetect OBJECT-TYPE
    SYNTAX      Integer32 (1..60000)
    UNITS       "milliseconds"
    MAX-ACCESS  read-create
    STATUS      current
    DESCRIPTION
        "Detect the link status."
    DEFVAL      { 100 }
    ::= { ibdeLlc2PortEntry 9 }

ibdeLlc2PortTimerBusy OBJECT-TYPE
    SYNTAX      Integer32 (1..60000)
    UNITS       "milliseconds"
    MAX-ACCESS  read-create
    STATUS      current
    DESCRIPTION
        "Waiting time while other LLC2 station is in busy state."
    DEFVAL      { 300 }
    ::= { ibdeLlc2PortEntry 10 }

ibdeLlc2PortTimerPoll OBJECT-TYPE
    SYNTAX      Integer32 (1..60000)
    UNITS       "milliseconds"
    MAX-ACCESS  read-create
    STATUS      current
    DESCRIPTION
        "Waiting time after a P frame is sent."
    DEFVAL      { 5000 }
    ::= { ibdeLlc2PortEntry 11 }

ibdeLlc2PortTimerReject OBJECT-TYPE
    SYNTAX      Integer32 (1..60000)
    UNITS       "milliseconds"
    MAX-ACCESS  read-create
    STATUS      current
    DESCRIPTION
        "Waiting time after a REJ frame is sent."
    DEFVAL      { 500 }
    ::= { ibdeLlc2PortEntry 12 }

ibdeLlc2PortRowStatus OBJECT-TYPE
    SYNTAX      RowStatus
    MAX-ACCESS  read-create
    STATUS      current
    DESCRIPTION
        "RowStatus."
    ::= { ibdeLlc2PortEntry 13 }

-- ====================================================================
-- DLSw Reachable Cache MIB-Group
-- ====================================================================
ibdeRchCacheStat OBJECT IDENTIFIER ::= { ibdeReachableCache 1 }

ibdeRchCacheMaxIndex OBJECT-TYPE
    SYNTAX      Integer32
    MAX-ACCESS  read-only
    STATUS      current
    DESCRIPTION
        "Maximum of ibdeRchCacheIndex."
    ::= { ibdeRchCacheStat 1 }

ibdeRchCacheNextIndex OBJECT-TYPE
    SYNTAX      Integer32
    MAX-ACCESS  read-only
    STATUS      current
    DESCRIPTION
        "The next value of ibdeRchCacheIndex to be assigned by
        the agent. A retrieval of this object atomically reserves
        the returned value for use by the manager to create a row
        in ibdeRchCacheTable. This makes it possible for the agent
        to control the index space of the MAC address cache, yet
        allows the manager to administratively create new rows."
    ::= { ibdeRchCacheStat 2 }

ibdeRchCacheTable OBJECT-TYPE
    SYNTAX      SEQUENCE OF IbdeRchCacheEntry
    MAX-ACCESS  not-accessible
    STATUS      current
    DESCRIPTION
        "Reachable cache table."
    ::= { ibdeReachableCache 3 }

ibdeRchCacheEntry OBJECT-TYPE
    SYNTAX      IbdeRchCacheEntry
    MAX-ACCESS  not-accessible
    STATUS      current
    DESCRIPTION
        "Reachable cache entry."
    INDEX       { ibdeRchCacheIndex }
    ::= { ibdeRchCacheTable 1 }

IbdeRchCacheEntry ::=
    SEQUENCE {
        ibdeRchCacheIndex            Integer32,
        ibdeRchCacheStatus           INTEGER,
        ibdeRchCacheRemainTime       TimeTicks,
        ibdeRchCacheMac              MacAddressNC,
        ibdeRchCacheRemoteIpAddrType InetAddressType,
        ibdeRchCacheRemoteIp         InetAddress,
        ibdeRchCacheRowStatus        RowStatus
    }

ibdeRchCacheIndex OBJECT-TYPE
    SYNTAX      Integer32
    MAX-ACCESS  not-accessible
    STATUS      current
    DESCRIPTION
        "Index of reachable cache entry."
    ::= { ibdeRchCacheEntry 1 }

ibdeRchCacheStatus OBJECT-TYPE
    SYNTAX      INTEGER
                {
                found(1),
                verify(2),
                noCacheInfo(3),
                exploring(4),
                waiting(5)
                }
    MAX-ACCESS  read-only
    STATUS      current
    DESCRIPTION
        "Current status of reachable cache entry."
    ::= { ibdeRchCacheEntry 2 }

ibdeRchCacheRemainTime OBJECT-TYPE
    SYNTAX      TimeTicks
    MAX-ACCESS  read-only
    STATUS      current
    DESCRIPTION
        "Remain time of reachable cache entry."
    ::= { ibdeRchCacheEntry 3 }

ibdeRchCacheMac OBJECT-TYPE
    SYNTAX      MacAddressNC
    MAX-ACCESS  read-create
    STATUS      current
    DESCRIPTION
        "MAC address of reachable cache entry."
    ::= { ibdeRchCacheEntry 4 }

ibdeRchCacheRemoteIpAddrType OBJECT-TYPE
    SYNTAX      InetAddressType
    MAX-ACCESS  read-create
    STATUS      current
    DESCRIPTION
        "Remote peer ip address type."
    ::= { ibdeRchCacheEntry 5 }

ibdeRchCacheRemoteIp OBJECT-TYPE
    SYNTAX      InetAddress
    MAX-ACCESS  read-create
    STATUS      current
    DESCRIPTION
        "Remote peer ip address of reachable cache entry."
    ::= { ibdeRchCacheEntry 6 }

ibdeRchCacheRowStatus OBJECT-TYPE
    SYNTAX      RowStatus
    MAX-ACCESS  read-create
    STATUS      current
    DESCRIPTION
        "RowStatus."
    ::= { ibdeRchCacheEntry 7 }

-- ====================================================================
-- DLSw Ethernet Backup MIB-Group
-- ====================================================================
ibdeEBMacMapStat OBJECT IDENTIFIER ::= { ibdeEthernetBackup 1 }

ibdeEBMacMapMaxIndex OBJECT-TYPE
    SYNTAX      Integer32
    MAX-ACCESS  read-only
    STATUS      current
    DESCRIPTION
        "Maximum of ibdeEBMacMapIndex."
    ::= { ibdeEBMacMapStat 1 }

ibdeEBMacMapNextIndex OBJECT-TYPE
    SYNTAX      Integer32
    MAX-ACCESS  read-only
    STATUS      current
    DESCRIPTION
        "The next value of ibdeEBMacMapIndex to be assigned by
        the agent. A retrieval of this object atomically reserves
        the returned value for use by the manager to create a row
        in ibdeEBMacMapTable. This makes it possible for the agent
        to control the index space of the MAC mapping tables, yet
        allows the manager to administratively create new rows."
    ::= { ibdeEBMacMapStat 2 }

ibdeEBIfTable OBJECT-TYPE
    SYNTAX      SEQUENCE OF IbdeEBIfEntry
    MAX-ACCESS  not-accessible
    STATUS      current
    DESCRIPTION
        "Information of interface which works for DLSw Ethernet redundancy."
    ::= { ibdeEthernetBackup 3 }

ibdeEBIfEntry OBJECT-TYPE
    SYNTAX      IbdeEBIfEntry
    MAX-ACCESS  not-accessible
    STATUS      current
    DESCRIPTION
        "Parameters defined for DLSw Ethernet redundancy interface."
    INDEX       { ifIndex }
    ::= { ibdeEBIfTable 1 }

IbdeEBIfEntry ::=
    SEQUENCE {
        ibdeEBMulticastMac    MacAddressNC,
        ibdeEBPriority        Integer32,
        ibdeEBtimer           Integer32,
        ibdeEBRowStatus       RowStatus
    }

ibdeEBMulticastMac OBJECT-TYPE
    SYNTAX      MacAddressNC
    MAX-ACCESS  read-create
    STATUS      current
    DESCRIPTION
        "Multicast MAC address configured for the Ethernet
        redundancy of dlsw module. When Ethernet redundancy
        is inactive, its value is '000000000000'H.
        To active Ethernet redundancy, give it a valid multicast MAC address."
    DEFVAL      { '000000000000'h }
    ::= { ibdeEBIfEntry 1 }

ibdeEBPriority OBJECT-TYPE
    SYNTAX      Integer32 (1..254)
    MAX-ACCESS  read-create
    STATUS      current
    DESCRIPTION
        "Priority configured for the Ethernet redundancy of DLSw module."
    DEFVAL      { 100 }
    ::= { ibdeEBIfEntry 2 }

ibdeEBtimer OBJECT-TYPE
    SYNTAX      Integer32 (100..5000)
    MAX-ACCESS  read-create
    STATUS      current
    DESCRIPTION
        "Timer for the Ethernet redundancy of DLSw module."
    DEFVAL      { 500 }
    ::= { ibdeEBIfEntry 3 }

ibdeEBRowStatus OBJECT-TYPE
    SYNTAX      RowStatus
    MAX-ACCESS  read-create
    STATUS      current
    DESCRIPTION
        "RowStatus."
    ::= { ibdeEBIfEntry 4 }

ibdeEBMacMapTable OBJECT-TYPE
    SYNTAX      SEQUENCE OF IbdeEBMacMapEntry
    MAX-ACCESS  not-accessible
    STATUS      current
    DESCRIPTION
        "MAC address mapping table."
    ::= { ibdeEthernetBackup 4 }

ibdeEBMacMapEntry OBJECT-TYPE
    SYNTAX      IbdeEBMacMapEntry
    MAX-ACCESS  not-accessible
    STATUS      current
    DESCRIPTION
        "MAC address mapping entry."
    INDEX       { ifIndex, ibdeEBMacMapIndex }
    ::= { ibdeEBMacMapTable 1 }

IbdeEBMacMapEntry ::=
    SEQUENCE {
        ibdeEBMacMapIndex         Integer32,
        ibdeEBMacMapLocalMac      MacAddressNC,
        ibdeEBMacMapRemoteMac     MacAddressNC,
        ibdeEBMacMapNeighbour     MacAddressNC,
        ibdeEBMacMapRowStatus     RowStatus
    }

ibdeEBMacMapIndex OBJECT-TYPE
    SYNTAX      Integer32
    MAX-ACCESS  not-accessible
    STATUS      current
    DESCRIPTION
        "Index of MAC address mapping entry."
    ::= { ibdeEBMacMapEntry 1 }

ibdeEBMacMapLocalMac OBJECT-TYPE
    SYNTAX      MacAddressNC
    MAX-ACCESS  read-create
    STATUS      current
    DESCRIPTION
        "Local MAC address in MAC address mapping.
        When creating a new conceptual row, ibdeEBMacMapLocalMac
        and ibdeEBMacMapRemoteMac should be set simultaneously."
    ::= { ibdeEBMacMapEntry 2 }

ibdeEBMacMapRemoteMac OBJECT-TYPE
    SYNTAX      MacAddressNC
    MAX-ACCESS  read-create
    STATUS      current
    DESCRIPTION
        "Remote MAC address of MAC address mapping.
        When creating a new conceptual row, ibdeEBMacMapLocalMac
        and ibdeEBMacMapRemoteMac should be set simultaneously."
    ::= { ibdeEBMacMapEntry 3 }

ibdeEBMacMapNeighbour OBJECT-TYPE
    SYNTAX      MacAddressNC
    MAX-ACCESS  read-create
    STATUS      current
    DESCRIPTION
        "Neighbour of MAC address mapping."
    ::= { ibdeEBMacMapEntry 4 }

ibdeEBMacMapRowStatus OBJECT-TYPE
    SYNTAX      RowStatus
    MAX-ACCESS  read-create
    STATUS      current
    DESCRIPTION
        "Status of MAC address mapping entry."
    ::= { ibdeEBMacMapEntry 5 }


END
