-- ============================================================================
-- Copyright (C) 2023 Intelbras S.A. All rights reserved.
--
-- Description: This MIB is used for configuration of SECP (security policies).
-- Reference:
-- Version: V1.0
-- History:
-- V1.0 created by xuedeng.
-- ============================================================================
IB-SECP-MIB DEFINITIONS ::= BEGIN

IMPORTS
    ibCommon
        FROM  IB-OID-MIB
    OBJECT-TYPE, MODULE-IDENTITY,
    Unsigned32, Counter64
        FROM SNMPv2-SMI;

--
-- Node definitions
--

ibSecp MODULE-IDENTITY
    LAST-UPDATED "201612191605Z"        -- Dec 19, 2016 at 16:05 GMT
    ORGANIZATION
        "Intelbras S.A. Industria de Telecomunicacao Eletronica Brasileria."
    CONTACT-INFO
        ""
    DESCRIPTION
        "Security policies management information base for managing devices
        that support security policies.
        "
    REVISION "201612191605Z"            -- Dec 19, 2016 at 16:05 GMT
    DESCRIPTION
        "The initial revision of this MIB module."
    ::= { ibCommon 166 }

--
-- Nodes of ibSecpObjects
--
ibSecpObjects OBJECT IDENTIFIER ::= { ibSecp 1 }

--
-- Nodes of ibSecpRunningInfoTable
--
ibSecpRunningInfoTable OBJECT-TYPE
    SYNTAX SEQUENCE OF IbSecpRunningInfoEntry
    MAX-ACCESS not-accessible
    STATUS current
    DESCRIPTION
        "Security policies running information base."
    ::= { ibSecpObjects 1 }

ibSecpRunningInfoEntry OBJECT-TYPE
    SYNTAX IbSecpRunningInfoEntry
    MAX-ACCESS not-accessible
    STATUS current
    DESCRIPTION
        "Security policies running information entry."
    INDEX
    {
        ibSecpIPVersion,
        ibSecpRuleID
    }
    ::= { ibSecpRunningInfoTable 1 }

IbSecpRunningInfoEntry ::=
    SEQUENCE
    {
        ibSecpIPVersion
            INTEGER,
        ibSecpRuleID
            Unsigned32,
        ibSecpMatchPacketCount
            Counter64,
        ibSecpLastMatchTime
            Unsigned32
    }

ibSecpIPVersion OBJECT-TYPE
    SYNTAX INTEGER
    {
        ipv4(1),
        ipv6(2)
    }
    MAX-ACCESS not-accessible
    STATUS current
    DESCRIPTION
        "IP protocol version."
    ::= { ibSecpRunningInfoEntry 1 }

ibSecpRuleID OBJECT-TYPE
    SYNTAX Unsigned32 (0..65534)
    MAX-ACCESS not-accessible
    STATUS current
    DESCRIPTION
        "Rule ID of security policies."
    ::= { ibSecpRunningInfoEntry 2 }

ibSecpMatchPacketCount OBJECT-TYPE
    SYNTAX Counter64
    MAX-ACCESS read-only
    STATUS current
    DESCRIPTION
        "Number of packets matching the rule."
    ::= { ibSecpRunningInfoEntry 3 }

ibSecpLastMatchTime OBJECT-TYPE
    SYNTAX Unsigned32
    MAX-ACCESS read-only
    STATUS current
    DESCRIPTION
        "Interval in seconds between the last match and 1970/1/1 00:00:00."
    ::= { ibSecpRunningInfoEntry 4 }

END
