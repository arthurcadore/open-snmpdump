-- ==================================================================
-- Copyright (C) 2023 Intelbras S.A. All rights reserved.
--
-- Description: PIM MIB
-- Reference:
-- Version: V1.0
-- History:
-- V1.0 2021-12-14 Created by Ma Xiaozhong
--      Add IbPimMode, IbPimGroupMappingOriginType,
--      ibPimRPMappingChange, ibPimGroupMappingOrigin,
--      ibPimGroupMappingAddressType, ibPimGroupMappingGrpAddress,
--      ibPimGroupMappingGrpPrefixLen, ibPimGroupMappingRPAddressType,
--      ibPimGroupMappingRPAddress, ibPimGroupMappingPimMode,
--      ibPimGroupMappingPrecedence, ibPimInterfaceElection,
--      ibPimInterfaceIfIndex, ibPimInterfaceAddress,
--      ibPimInterfaceIPVersion, ibPimInterfaceAddressType,
--      ibPimNeighborLoss, ibPimNeighborUpTime,
--      ibPimNeighborLossReason, ibPimNeighborIfName,
--      ibPimInterfaceName by jiayunda
-- ==================================================================
--
-- Variables and types be imported
--
-- ==================================================================
IB-PIM-STD-MIB DEFINITIONS ::= BEGIN

IMPORTS

    MODULE-IDENTITY,OBJECT-TYPE,NOTIFICATION-TYPE,Unsigned32,
    TimeTicks
        FROM SNMPv2-SMI

    TEXTUAL-CONVENTION,DisplayString
        FROM SNMPv2-TC

    ibCommon
        FROM IB-OID-MIB

    InetAddressType,InetAddress,InetAddressPrefixLength,InetVersion
        FROM INET-ADDRESS-MIB

    InterfaceIndex
        FROM IF-MIB;

ibPimStd MODULE-IDENTITY
    LAST-UPDATED "202207211350Z"
    ORGANIZATION
        "Intelbras S.A. Industria de Telecomunicacao Eletronica Brasileria."
    CONTACT-INFO
        ""
    DESCRIPTION
        "PIM(Protocol Independent Multicast) Management MIB"
    -- Revision history.
    REVISION "202207211350Z"
    DESCRIPTION
       "Add IbPimMode, IbPimGroupMappingOriginType,
        ibPimRPMappingChange, ibPimGroupMappingOrigin,
        ibPimGroupMappingAddressType, ibPimGroupMappingGrpAddress,
        ibPimGroupMappingGrpPrefixLen, ibPimGroupMappingRPAddressType,
        ibPimGroupMappingRPAddress, ibPimGroupMappingPimMode,
        ibPimGroupMappingPrecedence, ibPimInterfaceElection,
        ibPimInterfaceIfIndex, ibPimInterfaceAddress,
        ibPimInterfaceIPVersion, ibPimInterfaceAddressType,
        ibPimNeighborLoss, ibPimNeighborUpTime,
        ibPimNeighborLossReason, ibPimNeighborIfName,
        ibPimInterfaceName"
    REVISION "202112141400Z"
    DESCRIPTION
        "The initial version of this MIB file."
    ::= { ibCommon 213 }

IbPimMode ::= TEXTUAL-CONVENTION
    STATUS     current
    DESCRIPTION
            "The PIM mode in which a group is operating.
            none:The group is not using PIM, which may be the
                 case if, for example, it is a link-local or
                 unroutable group address.
            ssm:Source-Specific Multicast (SSM) with PIM Sparse Mode.
            asm:Any Source Multicast (ASM) with PIM Spars Mode.
            bidir:Bidirectional PIM.
            dm:PIM Dense Mode.
            other:Any other PIM mode."

    SYNTAX     INTEGER {
                  none(1),
                  ssm(2),
                  asm(3),
                  bidir(4),
                  dm(5),
                  other(6)
                }

IbPimGroupMappingOriginType ::= TEXTUAL-CONVENTION
    STATUS     current
    DESCRIPTION
            "The mechanism by which a PIM group mapping was learned.
            fixed:Link-local or unroutable group mappings.
            configRp:Local static RP configuration.
            configSsm:Local SSM Group configuration.
            bsr:The PIM Bootstrap Router (BSR) mechanism.
            autoRP:Cisco's Auto-RP mechanism.
            embedded:The Embedded-RP mechanism where the RP address
                         is embedded in the multicast group address.
            other:Any other mechanism."
    SYNTAX     INTEGER {
                  fixed(1),
                  configRp(2),
                  configSsm(3),
                  bsr(4),
                  autoRP(5),
                  embedded(6),
                  other(7)
               }

ibPimNotifications OBJECT IDENTIFIER ::= { ibPimStd 0 }
ibPimTrapBindObjects OBJECT IDENTIFIER ::= { ibPimStd 1 }

ibPimInstanceID OBJECT-TYPE
    SYNTAX     Unsigned32
    MAX-ACCESS accessible-for-notify
    STATUS     current
    DESCRIPTION
            "The ID of the PIM instance."
    ::= { ibPimTrapBindObjects 1 }

ibPimInstanceName OBJECT-TYPE
    SYNTAX     DisplayString (SIZE (0..255))
    MAX-ACCESS accessible-for-notify
    STATUS     current
    DESCRIPTION
            "The Name of the PIM instance."
    ::= { ibPimTrapBindObjects 2 }

ibPimNeighborExpiryTime OBJECT-TYPE
    SYNTAX     TimeTicks
    MAX-ACCESS accessible-for-notify
    STATUS     current
    DESCRIPTION
            "The minimum time remaining before this PIM neighbor will
             time out.  The value zero indicates that this PIM neighbor
             will never time out."
    ::= { ibPimTrapBindObjects 3 }

ibPimNotificationLimitType OBJECT-TYPE
    SYNTAX     INTEGER {
                         smStarGroup(1),
                         smSourceGroup(2)
    }
    MAX-ACCESS accessible-for-notify
    STATUS     current
    DESCRIPTION
            "The entry type:
             The smStarGroup indicates that the current restricted table
              item type is PIM-SM (*,G) table item
             The smSourceGroup indicates that the current restricted table
              item type is PIM-SM (S,G) table item;"
    ::= { ibPimTrapBindObjects 4 }

ibPimNotificationAddressFamily OBJECT-TYPE
    SYNTAX     InetAddressType
    MAX-ACCESS accessible-for-notify
    STATUS     current
    DESCRIPTION
            "The address family of PIM."
    ::= { ibPimTrapBindObjects 5 }

ibPimNotificationEntryCount OBJECT-TYPE
    SYNTAX     Unsigned32
    MAX-ACCESS accessible-for-notify
    STATUS     current
    DESCRIPTION
            "The current PIM entry count."
    ::= { ibPimTrapBindObjects 6 }

ibPimNotificationLimitCount OBJECT-TYPE
    SYNTAX     Unsigned32
    MAX-ACCESS accessible-for-notify
    STATUS     current
    DESCRIPTION
            "The maxmum limit of PIM entry."
    ::= { ibPimTrapBindObjects 7 }

ibPimNotificationThresholdCnt OBJECT-TYPE
    SYNTAX     Unsigned32
    MAX-ACCESS accessible-for-notify
    STATUS     current
    DESCRIPTION
            "The Threshold value of PIM table entry."
    ::= { ibPimTrapBindObjects 8 }

ibPimThresholdReasonType OBJECT-TYPE
    SYNTAX     INTEGER {
                         entryCreated(1),
                         configurationChanged(2)
    }
    MAX-ACCESS accessible-for-notify
    STATUS     current
    DESCRIPTION
        "Describe the reason for trap sending:
         The smStarGroup indicates that the current restricted table
         item type is PIM-SM (*,G) table item
         The smSourceGroup indicates that the current restricted table
         item type is PIM-SM (S,G) table item;"
    ::= { ibPimTrapBindObjects 9 }

ibPimRouteEClearReasonType OBJECT-TYPE
    SYNTAX     INTEGER {
                         entryDeleted(1),
                         configurationChanged(2)
    }
    MAX-ACCESS accessible-for-notify
    STATUS     current
    DESCRIPTION
        "Describe the reason for trap sending:
         The smStarGroup indicates that the current restricted table
         item type is PIM-SM (*,G) table item.
         The smSourceGroup indicates that the current restricted table
         item type is PIM-SM (S,G) table item."
    ::= { ibPimTrapBindObjects 10 }

ibPimThresholdClearReasonType OBJECT-TYPE
    SYNTAX     INTEGER {
                         entryDeleted(1),
                         configurationChanged(2)
    }
    MAX-ACCESS accessible-for-notify
    STATUS     current
    DESCRIPTION
        "Describe the reason for trap sending:
         The smStarGroup indicates that the current threshold limit table
         item type is PIM-SM (*,G) table item.
         The smSourceGroup indicates that the current threshold limit
         table item type is PIM-SM (S,G) table item."
    ::= { ibPimTrapBindObjects 11 }

ibPimNotificationSourceAddress OBJECT-TYPE
    SYNTAX     InetAddress
    MAX-ACCESS accessible-for-notify
    STATUS     current
    DESCRIPTION
            "The source IP address of the PIM entry."
    ::= { ibPimTrapBindObjects 12 }

ibPimNotificationGroupAddress OBJECT-TYPE
    SYNTAX     InetAddress
    MAX-ACCESS accessible-for-notify
    STATUS     current
    DESCRIPTION
            "The group IP address of the PIM entry."
    ::= { ibPimTrapBindObjects 13 }

ibPimNbrAddressIfIndex OBJECT-TYPE
    SYNTAX     InterfaceIndex
    MAX-ACCESS accessible-for-notify
    STATUS     current
    DESCRIPTION
            "The value of ifIndex for the interface used to reach this
            PIM neighbor."
    ::= { ibPimTrapBindObjects 14 }

ibPimNbrAddressType OBJECT-TYPE
    SYNTAX     InetAddressType
    MAX-ACCESS accessible-for-notify
    STATUS     current
    DESCRIPTION
            "The address type of this PIM neighbor."
    ::= { ibPimTrapBindObjects 15}

ibPimNbrAddress OBJECT-TYPE
    SYNTAX     InetAddress (SIZE (4|8|16|20))
    MAX-ACCESS read-only
    STATUS     current
    DESCRIPTION
            "The IP address of this PIM neighbor. The InetAddressType
            is specified by the ibpimNbrAddressType object."
    ::= { ibPimTrapBindObjects 16 }

ibPimNeighborUpTime OBJECT-TYPE
    SYNTAX     TimeTicks
    MAX-ACCESS accessible-for-notify
    STATUS     current
    DESCRIPTION
            "The time since the PIM neighbor was created as
             a neighbor of the local router."
    ::= { ibPimTrapBindObjects 17 }

ibPimGroupMappingOrigin OBJECT-TYPE
    SYNTAX     IbPimGroupMappingOriginType
    MAX-ACCESS accessible-for-notify
    STATUS     current
    DESCRIPTION
            "The mechanism by which this group mapping was learned."
    ::= { ibPimTrapBindObjects 18 }

ibPimGroupMappingAddressType OBJECT-TYPE
    SYNTAX     InetAddressType
    MAX-ACCESS accessible-for-notify
    STATUS     current
    DESCRIPTION
            "The address type of the IP multicast group prefix."
    ::= { ibPimTrapBindObjects 19 }

ibPimGroupMappingGrpAddress OBJECT-TYPE
    SYNTAX     InetAddress (SIZE (4|8|16|20))
    MAX-ACCESS accessible-for-notify
    STATUS     current
    DESCRIPTION
            "This object is represented as an IP multicast group address."
    ::= { ibPimTrapBindObjects 20 }

ibPimGroupMappingGrpPrefixLen OBJECT-TYPE
    SYNTAX     InetAddressPrefixLength (4..128)
    MAX-ACCESS accessible-for-notify
    STATUS     current
    DESCRIPTION
            "This object represents the group address mask length."
    ::= { ibPimTrapBindObjects 21 }

ibPimGroupMappingRPAddressType OBJECT-TYPE
    SYNTAX     InetAddressType
    MAX-ACCESS accessible-for-notify
    STATUS     current
    DESCRIPTION
            "This object represents the address type of an RP"
    ::= { ibPimTrapBindObjects 22 }

ibPimGroupMappingRPAddress OBJECT-TYPE
    SYNTAX     InetAddress (SIZE (0|4|8|16|20))
    MAX-ACCESS accessible-for-notify
    STATUS     current
    DESCRIPTION
            "The IP address of the RP to be used for groups within this
            group prefix."
    ::= { ibPimTrapBindObjects 23 }

ibPimGroupMappingPimMode OBJECT-TYPE
    SYNTAX     IbPimMode
    MAX-ACCESS accessible-for-notify
    STATUS     current
    DESCRIPTION
            "This object represents the currently running PIM mode."
    ::= { ibPimTrapBindObjects 24 }

ibPimGroupMappingPrecedence OBJECT-TYPE
    SYNTAX     Unsigned32
    MAX-ACCESS accessible-for-notify
    STATUS     current
    DESCRIPTION
            "This object represents the corresponding priority of different
             RP types. The higher the value, the lower the priority, and
             0 means the highest priority"
    ::= { ibPimTrapBindObjects 25 }

ibPimInterfaceIfIndex OBJECT-TYPE
    SYNTAX     InterfaceIndex
    MAX-ACCESS accessible-for-notify
    STATUS     current
    DESCRIPTION
            "The ifIndex value of this PIM interface."
    ::= { ibPimTrapBindObjects 26 }

ibPimInterfaceIPVersion OBJECT-TYPE
    SYNTAX     InetVersion
    MAX-ACCESS accessible-for-notify
    STATUS     current
    DESCRIPTION
            "This object represents the IP version of the PIM interface
             , which can be IPv4 or IPv6"
    ::= { ibPimTrapBindObjects 27 }

ibPimInterfaceAddressType OBJECT-TYPE
    SYNTAX     InetAddressType
    MAX-ACCESS accessible-for-notify
    STATUS     current
    DESCRIPTION
            "The address type of this PIM interface."
    ::= { ibPimTrapBindObjects 28 }

ibPimInterfaceAddress OBJECT-TYPE
    SYNTAX     InetAddress (SIZE (0|4|8|16|20))
    MAX-ACCESS accessible-for-notify
    STATUS     current
    DESCRIPTION
            "The primary IP address of this router on this PIM
            interface.  The InetAddressType is given by the
            ibPimInterfaceAddress object."
    ::= { ibPimTrapBindObjects 29 }

ibPimNeighborLossReason OBJECT-TYPE
    SYNTAX     INTEGER {
                         holdTimeTimeout(1),
             notReceiveHelloForALongTime(2),
                           interfaceDown(3),
                       receiveHelloAgain(4),
                        neighbourDeleted(5),
                            alarmTimeOut(6),
                      receiveHelloCancel(7),
                        bfdSessionIsDown(8),
                           userOperation(9),
                            alarmClear(100)
    }
    MAX-ACCESS accessible-for-notify
    STATUS     current
    DESCRIPTION
        "Describe the reason for trap sending:
         holdTimeTimeout:Neighbor's holdtime timer timed out.
         interfaceDown:The interface state of the neighbor changes to down.
         neighbourDeleted:Neighbor deletion.
         receiveHelloCancel:Received a neighbor message with holdtime 0.
         bfdSessionIsDown:Neighbor's BFD session down."
    ::= { ibPimTrapBindObjects 30 }

ibPimNeighborIfName OBJECT-TYPE
    SYNTAX     DisplayString (SIZE (1..64))
    MAX-ACCESS accessible-for-notify
    STATUS     current
    DESCRIPTION
            "The name of the PIM neighbor interface."
    ::= { ibPimTrapBindObjects 31 }

ibPimInterfaceName OBJECT-TYPE
    SYNTAX     DisplayString (SIZE (1..64))
    MAX-ACCESS accessible-for-notify
    STATUS     current
    DESCRIPTION
            "The name of the PIM interface."
    ::= { ibPimTrapBindObjects 32 }

--
-- trap
--
ibPimNeighborAdd NOTIFICATION-TYPE
    OBJECTS { ibPimNeighborExpiryTime,
              ibPimInstanceID,
              ibPimInstanceName,
              ibPimNbrAddressType,
              ibPimNbrAddressIfIndex,
              ibPimNbrAddress
            }
    STATUS     current
    DESCRIPTION
            "A notification sent when PIM add a new neighbor."
    ::= { ibPimNotifications 1 }

ibPimRouteThresholdExceed NOTIFICATION-TYPE
    OBJECTS { ibPimNotificationLimitType,
              ibPimNotificationAddressFamily,
              ibPimNotificationEntryCount,
              ibPimNotificationThresholdCnt,
              ibPimThresholdReasonType
            }
    STATUS     current
    DESCRIPTION
            "A notification sent when the number of pim entries
            exceeded the global entry threshold."
    ::= { ibPimNotifications 2 }

ibPimRouteThresholdExceedClear NOTIFICATION-TYPE
    OBJECTS { ibPimNotificationLimitType,
              ibPimNotificationAddressFamily,
              ibPimNotificationEntryCount,
              ibPimNotificationThresholdCnt,
              ibPimThresholdClearReasonType
            }
    STATUS     current
    DESCRIPTION
            "A notification sent when the number of pim entries
            fell below the global entry threshold."
    ::= { ibPimNotifications 3 }

ibPimRouteExceed NOTIFICATION-TYPE
    OBJECTS { ibPimNotificationLimitType,
              ibPimNotificationAddressFamily,
              ibPimNotificationSourceAddress,
              ibPimNotificationGroupAddress,
              ibPimNotificationEntryCount,
              ibPimNotificationLimitCount,
              ibPimInstanceName
            }
    STATUS     current
    DESCRIPTION
            "A notification sent when the number of pim entries
            exceeded the global entry limit."
    ::= { ibPimNotifications 4 }

ibPimRouteExceedClear NOTIFICATION-TYPE
    OBJECTS { ibPimNotificationLimitType,
              ibPimNotificationAddressFamily,
              ibPimNotificationSourceAddress,
              ibPimNotificationGroupAddress,
              ibPimNotificationEntryCount,
              ibPimNotificationLimitCount,
              ibPimInstanceName,
              ibPimRouteEClearReasonType
            }
    STATUS     current
    DESCRIPTION
            "A notification sent when the number of pim entries
             fell below the global entry threshold."
    ::= { ibPimNotifications 5 }

ibPimNeighborLoss NOTIFICATION-TYPE
    OBJECTS { ibPimNbrAddressIfIndex,
              ibPimNbrAddressType,
              ibPimNbrAddress,
              ibPimNeighborUpTime,
              ibPimNeighborIfName,
              ibPimInstanceID,
              ibPimInstanceName,
              ibPimNeighborLossReason
            }
    STATUS     current
    DESCRIPTION
            "The ibPimNeighborLoss notification is generated
             when PIM lost a neighbor."
    ::= { ibPimNotifications 6 }

ibPimRPMappingChange NOTIFICATION-TYPE
    OBJECTS { ibPimGroupMappingOrigin,
              ibPimGroupMappingAddressType,
              ibPimGroupMappingGrpAddress,
              ibPimGroupMappingGrpPrefixLen,
              ibPimGroupMappingRPAddressType,
              ibPimGroupMappingRPAddress,
              ibPimGroupMappingPimMode,
              ibPimGroupMappingPrecedence,
              ibPimInstanceID,
              ibPimInstanceName
            }
    STATUS      current
    DESCRIPTION
            "The ibPimRPMappingChange notification is generated when
             the active RP mapping on this device is changed"
    ::= { ibPimNotifications 7 }

ibPimInterfaceElection NOTIFICATION-TYPE
    OBJECTS { ibPimInterfaceIfIndex,
              ibPimInterfaceName,
              ibPimInterfaceIPVersion,
              ibPimInterfaceAddressType,
              ibPimInterfaceAddress,
              ibPimInstanceID,
              ibPimInstanceName
            }
    STATUS      current
    DESCRIPTION
            "The ibPimInterfaceElection notification is generated when the
             new DR or DF has been elected on a network."
    ::= { ibPimNotifications 8 }

END
