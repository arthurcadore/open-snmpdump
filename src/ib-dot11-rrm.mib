-- ==========================================================================
-- Copyright (C) 2023 Intelbras S.A. All rights reserved.
--
-- Description: The purpose of this MIB file is to provide object definition
--              of WLAN radio resource management (RRM).
-- Reference:
-- Version: V1.9
-- History:
-- V1.0 2008-07-16 Initial version, created by ChenWei
-- V1.1 2009-04-16 modified by WangChunsheng
-- Add new table of ibDot11MonitorDetectedDevTable for ibDot11MonitorDetectedGroup.
-- Add new table of ibDot11RRMAPCfgTable for ibDot11RRMConfigGroup.
-- V1.2 2009-05-07 modified by Wang Shaojie, wangchunsheng
--      Add ibDot11APInterfNumThreshhd, ibDot11StaInterfNumThreshhd
--      to ibDot11GlobeConfigGroup.
--      Modify ibDot11RRMCfgIntrvl
-- V1.3 2009-05-07 modified by Wang Shaojie
--      Add new node ibDot11MonitorDevSNR to ibDot11MonitorDetectedDevTable
-- V1.4 2010-02-22 modified by Wang Chunsheng
--      Add new table ibDot11RRMSDRadioGroupTable to ibDot11RRMConfigGroup
--      2010-03-18 Modified by Wang Lu
--      Add ibDot11RRMAPCfg2Table
-- V1.5 2010-09-21 Modified by wu xiaopeng
--      Add new node ibDot11RRMCoChlIntfTrapThhd, ibDot11RRMAdjChlIntfTrapThhd
--      to ibDot11RRMAPCfg2Table
--      2011-03-23 Modified by NiuJian
--      Add new node ibDot11RrmNbrSSID
--      to ibDot11RRMNbrInfoTable
-- V1.6 2013-03-23 Modified by GaoFei
--      Change SYNTAX of ibDot11RRMCfgPERThres,ibDot11RRMCfgToleranceFctr
-- V1.7 2013-09-02 Modified by Zhang Siyu
--      Add new table ibDot11RRMRadioNbrInfoTable to ibDot11RRMDetectGroup
--      2013-11-19 Modified by wubin
--      Add new node ibDot11RRM11nMultiCastMcs
--      to ibDot11RRMGlobalCfgPara
--      2013-12-21 Modified by wubin
--      Add new node ibDot11RRM11acMadtMaxNss, ibDot11RRM11acSuptMaxNss,
--      ibDot11RRM11acMultiCastNss, ibDot11RRM11acMultiCastVhtMcs
--      to ibDot11RRMGlobalCfgPara
-- V1.8 2014-05-07 Modified by yubo
--      Change SYNTAX of ibDot11RRMCfgIntrfThres.
-- V1.9 2017-05-22 Modified by weizhiguang
--      Add new node ibDot11RrmNbrSNR, ibDot11RrmNbrNF
--      to IbDot11RRMNbrInfoEntry
-- ==========================================================================
IB-DOT11-RRM-MIB DEFINITIONS ::= BEGIN

IMPORTS
    IbDot11RadioType, IbDot11ChannelScopeType, IbDot11RadioElementIndex,
    IbDot11RadioScopeType, ibDot11APElementIndex
        FROM IB-DOT11-REF-MIB
    Integer32, Unsigned32, OBJECT-TYPE, MODULE-IDENTITY,
    NOTIFICATION-TYPE
        FROM SNMPv2-SMI
    TruthValue, MacAddress, DateAndTime, RowStatus
        FROM SNMPv2-TC
    ibDot11,
    IbDot11ObjectIDType,
    IbDot11SSIDStringType
        FROM IB-DOT11-REF-MIB;

ibDot11RRM MODULE-IDENTITY
    LAST-UPDATED "201705221600Z"        -- May 22, 2017 at 16:00 GMT
    ORGANIZATION
        "Intelbras S.A. Industria de Telecomunicacao Eletronica Brasileria."
    CONTACT-INFO
        ""
    DESCRIPTION
        "This MIB file is to provide the object definition of
        WLAN radio resource management (RRM)."

    REVISION "201705221600Z"        -- May 22, 2017 at 16:00 GMT
    DESCRIPTION
        "Modified to add new nodes."
    REVISION "201009251800Z"        -- Sep 25, 2010 at 18:00 GMT
    DESCRIPTION
        "Modified to add new nodes."
    REVISION "201002231800Z"        -- Feb 23, 2010 at 18:00 GMT
    DESCRIPTION
        "Modified to add new nodes."
    REVISION "200908012000Z"        -- Aug 1, 2009 at 20:00 GMT
    DESCRIPTION
        "Modified to add new nodes and new table."
    REVISION "200905072000Z"        -- May 7, 2009 at 20:00 GMT
    DESCRIPTION
        "Modified to add new nodes and new table."
    REVISION "200904172000Z"        -- April 17, 2009 at 20:00 GMT
    DESCRIPTION
        "Modified to add new table and new group."
    REVISION "200807141429Z"
    DESCRIPTION
        "The initial revision of this MIB module."
    ::= { ibDot11 8 }

--
-- Node definitions
--

ibDot11RRMConfigGroup OBJECT IDENTIFIER ::= { ibDot11RRM 1 }

ibDot11RRMGlobalCfgPara OBJECT IDENTIFIER ::= { ibDot11RRMConfigGroup 1 }

ibDot11RRM11nMadtMaxMcs OBJECT-TYPE
    SYNTAX Integer32 (0..76 | 255)
    MAX-ACCESS read-write
    STATUS current
    DESCRIPTION
        "Specify the maximum modulation and coding scheme (MCS) index for
        802.11n mandatory rates.
        The value 255 indicates that no maximum MCS index
        is specified.  No maximum MCS index is specified for 802.11n
        mandatory rates by default.
        Besides 255, the specified maximum MCS index for 802.11n supported
        rates must be no less than the specified maximum MCS index for 802.11n
        mandatory rates."
    DEFVAL { 255 }
    ::= { ibDot11RRMGlobalCfgPara 1 }

ibDot11RRM11nSuptMaxMcs OBJECT-TYPE
    SYNTAX Integer32 (0..76)
    MAX-ACCESS read-write
    STATUS current
    DESCRIPTION
        "Specify the maximum Modulation and Coding Scheme (MCS) index for
        802.11n supported rates.
        The specified maximum MCS index for 802.11n supported rates must be no
        less than the specified maximum MCS index for 802.11n mandatory rates."
    DEFVAL { 76 }
    ::= { ibDot11RRMGlobalCfgPara 2 }

ibDot11RRM11gProtect OBJECT-TYPE
    SYNTAX TruthValue
    MAX-ACCESS read-write
    STATUS current
    DESCRIPTION
        "Enable/Disable dot11g protection."
    DEFVAL { false }
    ::= { ibDot11RRMGlobalCfgPara 3 }

ibDot11RRM11aPwrConstrt OBJECT-TYPE
    SYNTAX Integer32
    UNITS "dBm"
    MAX-ACCESS read-write
    STATUS current
    DESCRIPTION
        "Configure the power constraint for all 802.11a radios.
        The configured power constraint is advertised in beacons if spectrum
        management is enabled.
        The range of power constraint is 0 to MAX-POWER-1 (where the MAX-POWER
        is defined by the regulatory domain)."
    DEFVAL { 0 }
    ::= { ibDot11RRMGlobalCfgPara 4 }

ibDot11RRM11aSpectrumManag OBJECT-TYPE
    SYNTAX TruthValue
    MAX-ACCESS read-write
    STATUS current
    DESCRIPTION
        "Enable/Disable spectrum management for 802.11a radios.
        When spectrum management is enabled, the WLAN sub-system advertises
        power capabilities of the AP and power constraints applicable to all
        devices in the BSS based on regulatory domain specification."
    DEFVAL { false }
    ::= { ibDot11RRMGlobalCfgPara 5 }

ibDot11RRMAutoChlAvoid11h OBJECT-TYPE
    SYNTAX TruthValue
    MAX-ACCESS read-write
    STATUS current
    DESCRIPTION
        "Configure the auto-channel set as non-dot11h channels, this is,
        only the non-dot11h channels belonging to the country code are scanned
        during initial channel selection and one of them is selected."
    DEFVAL { false }
    ::= { ibDot11RRMGlobalCfgPara 6 }

ibDot11RRMScanChl OBJECT-TYPE
    SYNTAX INTEGER
        {
        auto(1),
        all(2)
        }
    MAX-ACCESS read-write
    STATUS current
    DESCRIPTION
        "Set the scan mode.
        auto: When this option is set, all channels of the country code being
              set are scanned.
        all: When this option is set, all the channels of the radio band are
             scanned."
    DEFVAL { auto }
    ::= { ibDot11RRMGlobalCfgPara 7 }

ibDot11RRMScanRptIntvel OBJECT-TYPE
    SYNTAX Integer32 (5..120)
    UNITS "second"
    MAX-ACCESS read-write
    STATUS current
    DESCRIPTION
        "Set the scan report interval."
    DEFVAL { 10 }
    ::= { ibDot11RRMGlobalCfgPara 8 }

ibDot11APInterfNumThreshhd OBJECT-TYPE
    SYNTAX      Integer32
    MAX-ACCESS  read-write
    STATUS      current
    DESCRIPTION
        "Represents threshold of AP interference .
         If the value of AP interference exceeds this threshold,
         AP interference trap will be sent.  If the value of this node
         is zero, AP interference trap will be sent immediately."

    DEFVAL      { 0 }
    ::= { ibDot11RRMGlobalCfgPara 9 }

ibDot11StaInterfNumThreshhd OBJECT-TYPE
    SYNTAX      Integer32
    MAX-ACCESS  read-write
    STATUS      current
    DESCRIPTION
        "Represents threshold of STA interference.
         If the value of STA interference exceeds this threshold,
         STA interference trap will be sent.  If the value of this
         node is zero, STA interference trap will be sent immediately.
         "
    DEFVAL      { 0 }
    ::= { ibDot11RRMGlobalCfgPara 10 }

ibDot11RRM11nMultiCastMcs OBJECT-TYPE
    SYNTAX Unsigned32 (0..76 | 4294967295)
    MAX-ACCESS read-write
    STATUS current
    DESCRIPTION
        "Specify the modulation and coding scheme (MCS) index for 802.11n
        multicast rates.
        The value 4294967295 indicates that no MCS index is specified.
        No MCS index is specified for 802.11n multicast rates by default.
        Besides 4294967295, the specified MCS index for 802.11n multicast
        rates must be no less than the specified maximum MCS index for 802.11n
        mandatory rates.
        Before configure the MCS index for 802.11n multicast rates, the maximum
        MCS index for 802.11n mandatory rates must be configured"
    DEFVAL { 4294967295 }
    ::= { ibDot11RRMGlobalCfgPara 11 }

ibDot11RRM11acMadtMaxNss OBJECT-TYPE
    SYNTAX Integer32 (0..8)
    MAX-ACCESS read-write
    STATUS current
    DESCRIPTION
        "Specify the maximum NSS index for 802.11ac mandatory rates.
        The value 0 indicates that no maximum NSS index is specified.
        No maximum NSS index is specified for 802.11ac mandatory rates by default.
        The specified maximum NSS index for 802.11ac supported rates must be no less
        than the specified maximum NSS index for 802.11ac mandatory rates."
    DEFVAL { 0 }
    ::= { ibDot11RRMGlobalCfgPara 12 }

ibDot11RRM11acSuptMaxNss OBJECT-TYPE
    SYNTAX Integer32 (1..8)
    MAX-ACCESS read-write
    STATUS current
    DESCRIPTION
        "Specify the maximum NSS index for 802.11ac supported rates.
        The specified maximum NSS index for 802.11ac supported rates must be no
        less than the specified maximum NSS index for 802.11ac mandatory rates."
    DEFVAL { 8 }
    ::= { ibDot11RRMGlobalCfgPara 13 }

ibDot11RRM11acMultiCastNss OBJECT-TYPE
    SYNTAX Integer32 (0..8)
    MAX-ACCESS read-write
    STATUS current
    DESCRIPTION
        "Specify the NSS index for 802.11ac multicast rates.
        The value 0 indicates that no NSS index is specified.
        No NSS index is specified for 802.11ac multicast rates by default.
        The specified NSS index for 802.11ac multicast rates must be no less
        than the specified maximum NSS index for 802.11ac mandatory rates.
        Before configuring the NSS index for 802.11ac multicast rates, the maximum
        NSS index for 802.11ac mandatory rates must be configured.
        Besides, it must be configured together with the node below."
    DEFVAL { 0 }
    ::= { ibDot11RRMGlobalCfgPara 14 }

ibDot11RRM11acMultiCastVhtMcs OBJECT-TYPE
    SYNTAX Integer32 (0..9 | 255)
    MAX-ACCESS read-write
    STATUS current
    DESCRIPTION
        "Specify the MCS index for 802.11ac multicast rates.
        The value 255 indicates that no MCS index is specified.
        No MCS index is specified for 802.11ac multicast rates by default.
        Besides, it must be configured together with the node above."
    DEFVAL { 255 }
    ::= { ibDot11RRMGlobalCfgPara 15 }

ibDot11RRMRadioCfgTable OBJECT-TYPE
    SYNTAX SEQUENCE OF IbDot11RRMRadioCfgEntry
    MAX-ACCESS not-accessible
    STATUS current
    DESCRIPTION
        "Configure WLAN RRM based radio type.
        When 802.11b parameter is modified, 802.11g parameter will be
        changed at the same time.
        In the same way, when 802.11g parameter is modified, 802.11b parameter
        will be changed at the same time."
    ::= { ibDot11RRMConfigGroup 2 }

ibDot11RRMRadioCfgEntry OBJECT-TYPE
    SYNTAX IbDot11RRMRadioCfgEntry
    MAX-ACCESS not-accessible
    STATUS current
    DESCRIPTION
        "Configure WLAN RRM based radio type.
        When 802.11b parameter is modified, 802.11g parameter will be
        changed at the same time.
        In the same way, when 802.11g parameter is modified, 802.11b parameter
        will be changed at the same time."
    INDEX { ibDot11RRMRadioType }
    ::= { ibDot11RRMRadioCfgTable 1 }

IbDot11RRMRadioCfgEntry ::=
    SEQUENCE {
        ibDot11RRMRadioType
            IbDot11RadioType,
        ibDot11RRMCfgChlState
            TruthValue,
        ibDot11RRMCfgChlMode
            INTEGER,
        ibDot11RRMChlProntoRadioElmt
            Unsigned32,
        ibDot11RRMCfgPwrState
            TruthValue,
        ibDot11RRMCfgPwrMode
            INTEGER,
        ibDot11RRMPwrProntoRadioElmt
            Unsigned32,
        ibDot11RRMCfgIntrvl
            Integer32,
        ibDot11RRMCfgIntrfThres
            Integer32,
        ibDot11RRMCfgNoiseThres
            Integer32,
        ibDot11RRMCfgPERThres
            Integer32,
        ibDot11RRMCfgToleranceFctr
            Integer32,
        ibDot11RRMCfgAdjacencyFctr
            Integer32
     }

ibDot11RRMRadioType OBJECT-TYPE
    SYNTAX IbDot11RadioType
    MAX-ACCESS not-accessible
    STATUS current
    DESCRIPTION
        "802.11 radio type."
    ::= { ibDot11RRMRadioCfgEntry 1 }

ibDot11RRMCfgChlState OBJECT-TYPE
    SYNTAX TruthValue
    MAX-ACCESS read-write
    STATUS current
    DESCRIPTION
        "Enable/Disable dynamic channel selection."
    DEFVAL { false }
    ::= { ibDot11RRMRadioCfgEntry 2 }

ibDot11RRMCfgChlMode OBJECT-TYPE
    SYNTAX INTEGER
        {
        selfDecisive(1),
        userTriggered(2)
        }
    MAX-ACCESS read-write
    STATUS current
    DESCRIPTION
        "Configure the mode of channel selection.
        This node can be configured only when dynamic channel selection
        is enabled."
    DEFVAL { userTriggered }
    ::= { ibDot11RRMRadioCfgEntry 3 }

ibDot11RRMChlProntoRadioElmt OBJECT-TYPE
    SYNTAX Unsigned32
    MAX-ACCESS read-write
    STATUS current
    DESCRIPTION
        "Specify the AP and radio that will change channel at next
        calibration cycle.
        0 is returned when getting the value of this node.
        This node can be configured only when the mode of channel selection
        control is user-triggered.
        When configuring, the higher 24 bits stand for the AP index,
        and the last 8 bits stand for the radio index.
        4294967295 stand for configuring each radio on all APs."
    DEFVAL { 0 }
    ::= { ibDot11RRMRadioCfgEntry 4 }

ibDot11RRMCfgPwrState OBJECT-TYPE
    SYNTAX TruthValue
    MAX-ACCESS read-write
    STATUS current
    DESCRIPTION
        "Enable/Disable dynamic power selection for the band."
    DEFVAL { false }
    ::= { ibDot11RRMRadioCfgEntry 5 }

ibDot11RRMCfgPwrMode OBJECT-TYPE
    SYNTAX INTEGER
        {
        selfDecisive(1),
        userTriggered(2)
        }
    MAX-ACCESS read-write
    STATUS current
    DESCRIPTION
        "Configure the mode of transmit power control.
        This node can be configured only when dynamic power selection
        is enabled."
    DEFVAL { userTriggered }
    ::= { ibDot11RRMRadioCfgEntry 6 }

ibDot11RRMPwrProntoRadioElmt OBJECT-TYPE
    SYNTAX Unsigned32
    MAX-ACCESS read-write
    STATUS current
    DESCRIPTION
        "Specify the AP and radio that will change power at next
        calibration cycle.
        0 is returned when getting the value of this node.
        This node can be configured only when the mode of transmit power
        control is user-triggered.
        When configuring, the higher 24 bits stand for the AP index,
        and the last 8 bits stand for the radio index.
        4294967295 stand for configuring each radio on all APs."
    DEFVAL { 0 }
    ::= { ibDot11RRMRadioCfgEntry 7 }

ibDot11RRMCfgIntrvl OBJECT-TYPE
    SYNTAX Integer32
    UNITS "minute"
    MAX-ACCESS read-write
    STATUS current
    DESCRIPTION
        "Configure the calibration interval."
    DEFVAL { 8 }
    ::= { ibDot11RRMRadioCfgEntry 8 }

ibDot11RRMCfgIntrfThres OBJECT-TYPE
    SYNTAX Integer32 (1..100)
    UNITS "percent"
    MAX-ACCESS read-write
    STATUS current
    DESCRIPTION
        "Configure the interface threshold.
        By default, interference observed on an operating channel is considered
        during dynamic frequency selection and transmit power control.  If the
        interference percentage on the channel reaches the set threshold, RRM
        will perform resource adjustment to control the situation."
    DEFVAL { 50 }
    ::= { ibDot11RRMRadioCfgEntry 9 }

ibDot11RRMCfgNoiseThres OBJECT-TYPE
    SYNTAX Integer32 (-127..127)
    MAX-ACCESS read-write
    STATUS current
    DESCRIPTION
        "Configure the noise threshold."
    DEFVAL { -70 }
    ::= { ibDot11RRMRadioCfgEntry 10 }

ibDot11RRMCfgPERThres OBJECT-TYPE
    SYNTAX Integer32 (1..100)
    UNITS "percent"
    MAX-ACCESS read-write
    STATUS current
    DESCRIPTION
        "Configure the CRC error threshold.
        If the percentage of CRC errors reaches the threshold, RRM will perform
        resource adjustment to control the situation."
    DEFVAL { 20 }
    ::= { ibDot11RRMRadioCfgEntry 11 }

ibDot11RRMCfgToleranceFctr OBJECT-TYPE
    SYNTAX Integer32 (1..45)
    UNITS "percent"
    MAX-ACCESS read-write
    STATUS current
    DESCRIPTION
        "Configure the tolerance level.
        During dynamic frequency selection (DFS), the channel will be changed
        only if there is a better channel having lesser interference and packet
        error rate than those specified by the user."
    DEFVAL { 20 }
    ::= { ibDot11RRMRadioCfgEntry 12 }

ibDot11RRMCfgAdjacencyFctr OBJECT-TYPE
    SYNTAX Integer32 (1..16)
    MAX-ACCESS read-write
    STATUS current
    DESCRIPTION
        "Configure the adjacency factor for the band.
        If transmit power control (TPC) is configured, power will be adjusted
        when the nth neighbor is detected.  The value n is the adjacency factor."
    DEFVAL { 3 }
    ::= { ibDot11RRMRadioCfgEntry 13 }

ibDot11RRMAPCfgTable OBJECT-TYPE
    SYNTAX SEQUENCE OF IbDot11RRMAPCfgEntry
    MAX-ACCESS not-accessible
    STATUS current
    DESCRIPTION
        "This table defines the RRM parameters for AP."
    ::= { ibDot11RRMConfigGroup 3 }

ibDot11RRMAPCfgEntry OBJECT-TYPE
    SYNTAX IbDot11RRMAPCfgEntry
    MAX-ACCESS not-accessible
    STATUS current
    DESCRIPTION
        "Each entry contains information of RRM parameters for AP."
    INDEX { ibDot11APElementIndex }
    ::= { ibDot11RRMAPCfgTable 1 }

IbDot11RRMAPCfgEntry ::=
    SEQUENCE {
        ibDot11RRMAPWorkMode
          INTEGER
    }

ibDot11RRMAPWorkMode OBJECT-TYPE
    SYNTAX INTEGER
        {
        normal(1),
        monitor(2),
        hybrid(3)
        }
    MAX-ACCESS read-write
    STATUS current
    DESCRIPTION
        "AP work mode."
    ::= { ibDot11RRMAPCfgEntry 1 }

ibDot11RRMSDRadioGroupTable OBJECT-TYPE
    SYNTAX SEQUENCE OF IbDot11RRMSDRadioGroupEntry
    MAX-ACCESS not-accessible
    STATUS current
    DESCRIPTION
        "This table defines RRM self-decisive radio group."
    ::= { ibDot11RRMConfigGroup 4 }

ibDot11RRMSDRadioGroupEntry OBJECT-TYPE
    SYNTAX      IbDot11RRMSDRadioGroupEntry
    MAX-ACCESS  not-accessible
    STATUS      current
    DESCRIPTION
        "Each entry contains information of one RRM self-decisive radio group."
    INDEX
        {
            ibDot11RRMSDRadioGroupId
        }
    ::= { ibDot11RRMSDRadioGroupTable 1 }

IbDot11RRMSDRadioGroupEntry ::= SEQUENCE
    {
        ibDot11RRMSDRadioGroupId             Unsigned32,
        ibDot11RRMSDRadioGroupDesc           OCTET STRING,
        ibDot11RRMSDRdGrpChlHolddownTm       Unsigned32,
        ibDot11RRMSDRdGrpPwrHolddownTm       Unsigned32,
        ibDot11RRMSDRdGroupRowStatus         RowStatus
    }

ibDot11RRMSDRadioGroupId OBJECT-TYPE
    SYNTAX      Unsigned32
    MAX-ACCESS  not-accessible
    STATUS      current
    DESCRIPTION
        "Represents RRM self-decisive radio group ID."
    ::= { ibDot11RRMSDRadioGroupEntry 1 }

ibDot11RRMSDRadioGroupDesc OBJECT-TYPE
    SYNTAX      OCTET STRING
    MAX-ACCESS  read-create
    STATUS      current
    DESCRIPTION
        "Represents the description of RRM self-decisive radio group."
    ::= { ibDot11RRMSDRadioGroupEntry 2 }

ibDot11RRMSDRdGrpChlHolddownTm OBJECT-TYPE
    SYNTAX      Unsigned32
    UNITS       "minute"
    MAX-ACCESS  read-create
    STATUS      current
    DESCRIPTION
        "Represents the channel holddown time of RRM self-decisive radio group."
    ::= { ibDot11RRMSDRadioGroupEntry 3 }

ibDot11RRMSDRdGrpPwrHolddownTm OBJECT-TYPE
    SYNTAX      Unsigned32
    UNITS       "minute"
    MAX-ACCESS  read-create
    STATUS      current
    DESCRIPTION
        "Represents the power holddown time of RRM self-decisive radio group."
    ::= { ibDot11RRMSDRadioGroupEntry 4 }

ibDot11RRMSDRdGroupRowStatus OBJECT-TYPE
    SYNTAX      RowStatus
    MAX-ACCESS  read-create
    STATUS      current
    DESCRIPTION
        "The row status of this table entry."
    ::= { ibDot11RRMSDRadioGroupEntry 5 }

ibDot11RRMAPCfg2Table OBJECT-TYPE
    SYNTAX SEQUENCE OF IbDot11RRMAPCfg2Entry
    MAX-ACCESS not-accessible
    STATUS current
    DESCRIPTION
        "This table defines the RRM parameters for AP."
    ::= { ibDot11RRMConfigGroup 5 }

ibDot11RRMAPCfg2Entry OBJECT-TYPE
    SYNTAX IbDot11RRMAPCfg2Entry
    MAX-ACCESS not-accessible
    STATUS current
    DESCRIPTION
        "Each entry contains information of RRM parameters for AP."
    INDEX { ibDot11RRMAPSerialID }
    ::= { ibDot11RRMAPCfg2Table 1 }

IbDot11RRMAPCfg2Entry ::=
    SEQUENCE {
        ibDot11RRMAPSerialID
            IbDot11ObjectIDType,
        ibDot11RRMAPIntfThreshold
            Integer32,
        ibDot11RRMStaIntfThreshold
            Integer32,
        ibDot11RRMCoChlIntfTrapThhd
            Integer32,
        ibDot11RRMAdjChlIntfTrapThhd
            Integer32
    }

ibDot11RRMAPSerialID OBJECT-TYPE
    SYNTAX IbDot11ObjectIDType
    MAX-ACCESS not-accessible
    STATUS current
    DESCRIPTION
        "Serial ID of the AP."
    ::= { ibDot11RRMAPCfg2Entry 1 }

ibDot11RRMAPIntfThreshold OBJECT-TYPE
    SYNTAX Integer32
    MAX-ACCESS read-write
    STATUS current
    DESCRIPTION
        "Represents threshold of AP interference .
         If the number of AP interference exceeds this threshold,
         AP interference trap will be sent."
    ::= { ibDot11RRMAPCfg2Entry 2 }

ibDot11RRMStaIntfThreshold OBJECT-TYPE
    SYNTAX Integer32
    MAX-ACCESS read-write
    STATUS current
    DESCRIPTION
        "Represents threshold of STA interference.
         If the number of STA interference exceeds this threshold,
         station interference trap will be sent."
    ::= { ibDot11RRMAPCfg2Entry 3 }

ibDot11RRMCoChlIntfTrapThhd OBJECT-TYPE
    SYNTAX      Integer32
    UNITS       "dbm"
    MAX-ACCESS  read-write
    STATUS      current
    DESCRIPTION
        "Represents threshold of interference trap with current ap.
        If signal strength of the device exceeds this threshold,
        corresponding trap will be sent."
    ::= { ibDot11RRMAPCfg2Entry 4 }


ibDot11RRMAdjChlIntfTrapThhd OBJECT-TYPE
    SYNTAX      Integer32
    UNITS       "dbm"
    MAX-ACCESS  read-write
    STATUS      current
    DESCRIPTION
        "Represents threshold of adjacent interference trap with current ap.
        If signal strength of the device exceeds this threshold,
        corresponding trap will be sent."
    ::= { ibDot11RRMAPCfg2Entry 5 }

ibDot11RRMDetectGroup OBJECT IDENTIFIER ::= { ibDot11RRM 2 }

ibDot11RRMChlRptTable OBJECT-TYPE
    SYNTAX SEQUENCE OF IbDot11RRMChlRptEntry
    MAX-ACCESS not-accessible
    STATUS current
    DESCRIPTION
        "This table shows the RRM channel information of each radio
        on all APs."
    ::= { ibDot11RRMDetectGroup 1 }

ibDot11RRMChlRptEntry OBJECT-TYPE
    SYNTAX IbDot11RRMChlRptEntry
    MAX-ACCESS not-accessible
    STATUS current
    DESCRIPTION
        "Each entry contains information of RRM channel information
        of the radio on the AP."
    INDEX { ibDot11RRMRadioIndex, ibDot11RRMChlRptChlNum }
    ::= { ibDot11RRMChlRptTable 1 }

IbDot11RRMChlRptEntry ::=
    SEQUENCE {
        ibDot11RRMRadioIndex
            IbDot11RadioElementIndex,
        ibDot11RRMChlRptChlNum
            Integer32,
        ibDot11RRMChlRptChlType
            INTEGER,
        ibDot11RRMChlRptChlQlty
            INTEGER,
        ibDot11RRMChlRptNbrCnt
            Integer32,
        ibDot11RRMChlRptLoad
            Integer32,
        ibDot11RRMChlRptUtlz
            Integer32,
        ibDot11RRMChlRptIntrf
            Integer32,
        ibDot11RRMChlRptPER
            Integer32,
        ibDot11RRMChlRptRetryRate
            Integer32,
        ibDot11RRMChlRptNoise
            Integer32,
        ibDot11RRMChlRptRadarIndtcr
            INTEGER
     }

ibDot11RRMRadioIndex OBJECT-TYPE
    SYNTAX IbDot11RadioElementIndex
    MAX-ACCESS accessible-for-notify
    STATUS current
    DESCRIPTION
        "Represents index of the radio."
    ::= { ibDot11RRMChlRptEntry 1 }

ibDot11RRMChlRptChlNum OBJECT-TYPE
    SYNTAX Integer32
    MAX-ACCESS accessible-for-notify
    STATUS current
    DESCRIPTION
        "Channel number."
    ::= { ibDot11RRMChlRptEntry 2 }

ibDot11RRMChlRptChlType OBJECT-TYPE
    SYNTAX INTEGER
        {
        primeChannel(1),
        offChannel(2)
        }
    MAX-ACCESS read-only
    STATUS current
    DESCRIPTION
        "Channel type."
    ::= { ibDot11RRMChlRptEntry 3 }

ibDot11RRMChlRptChlQlty OBJECT-TYPE
    SYNTAX INTEGER
        {
        good(1),
        bad(2)
        }
    MAX-ACCESS read-only
    STATUS current
    DESCRIPTION
        "Channel quality."
    ::= { ibDot11RRMChlRptEntry 4 }

ibDot11RRMChlRptNbrCnt OBJECT-TYPE
    SYNTAX Integer32
    MAX-ACCESS read-only
    STATUS current
    DESCRIPTION
        "Number of neighbors found on the channel."
    ::= { ibDot11RRMChlRptEntry 5 }

ibDot11RRMChlRptLoad OBJECT-TYPE
    SYNTAX Integer32 (0..100)
    UNITS "percent"
    MAX-ACCESS read-only
    STATUS current
    DESCRIPTION
        "Load observed on the channel in percentage."
    ::= { ibDot11RRMChlRptEntry 6 }

ibDot11RRMChlRptUtlz OBJECT-TYPE
    SYNTAX Integer32 (0..100)
    UNITS "percent"
    MAX-ACCESS read-only
    STATUS current
    DESCRIPTION
        "Utilization of the channel in percentage."
    ::= { ibDot11RRMChlRptEntry 7 }

ibDot11RRMChlRptIntrf OBJECT-TYPE
    SYNTAX Integer32 (0..100)
    UNITS "percent"
    MAX-ACCESS read-only
    STATUS current
    DESCRIPTION
        "Interference observed on the channel in percentage."
    ::= { ibDot11RRMChlRptEntry 8 }

ibDot11RRMChlRptPER OBJECT-TYPE
    SYNTAX Integer32 (0..100)
    UNITS "percent"
    MAX-ACCESS read-only
    STATUS current
    DESCRIPTION
        "Packet error rate observed on the channel in percentage."
    ::= { ibDot11RRMChlRptEntry 9 }

ibDot11RRMChlRptRetryRate OBJECT-TYPE
    SYNTAX Integer32 (0..100)
    UNITS "percent"
    MAX-ACCESS read-only
    STATUS current
    DESCRIPTION
        "Percentage of retransmission happened on the channel."
    ::= { ibDot11RRMChlRptEntry 10 }

ibDot11RRMChlRptNoise OBJECT-TYPE
    SYNTAX Integer32
    MAX-ACCESS read-only
    STATUS current
    DESCRIPTION
        "Noise observed on the channel."
    ::= { ibDot11RRMChlRptEntry 11 }

ibDot11RRMChlRptRadarIndtcr OBJECT-TYPE
    SYNTAX INTEGER
        {
        detected(1),
        notDetected(2)
        }
    MAX-ACCESS read-write
    STATUS current
    DESCRIPTION
        "Radar detection status."
    ::= { ibDot11RRMChlRptEntry 12 }

ibDot11RRMNbrInfoTable OBJECT-TYPE
    SYNTAX SEQUENCE OF IbDot11RRMNbrInfoEntry
    MAX-ACCESS not-accessible
    STATUS current
    DESCRIPTION
        "This table shows the RRM neighbor information of each radio
        on all APs."
    ::= { ibDot11RRMDetectGroup 2 }

ibDot11RRMNbrInfoEntry OBJECT-TYPE
    SYNTAX IbDot11RRMNbrInfoEntry
    MAX-ACCESS not-accessible
    STATUS current
    DESCRIPTION
        "Each entry contains information of RRM neighbor information
        of the radio on an AP."
    INDEX { ibDot11RRMRadioIndex, ibDot11RrmNbrBSSID }
    ::= { ibDot11RRMNbrInfoTable 1 }

IbDot11RRMNbrInfoEntry ::=
    SEQUENCE {
        ibDot11RrmNbrBSSID
            MacAddress,
        ibDot11RrmNbrChl
            IbDot11ChannelScopeType,
        ibDot11RRMNbrIntrf
            Integer32,
        ibDot11RrmNbrRSSI
            Integer32,
        ibDot11RrmNbrType
            INTEGER,
        ibDot11RrmNbrSSID
            IbDot11SSIDStringType,
        ibDot11RrmNbrSNR
            Integer32,
        ibDot11RrmNbrNF
            Integer32
     }

ibDot11RrmNbrBSSID OBJECT-TYPE
    SYNTAX MacAddress
    MAX-ACCESS not-accessible
    STATUS current
    DESCRIPTION
        "MAC address of the AP."
    ::= { ibDot11RRMNbrInfoEntry 1 }

ibDot11RrmNbrChl OBJECT-TYPE
    SYNTAX IbDot11ChannelScopeType
    MAX-ACCESS read-only
    STATUS current
    DESCRIPTION
        "Channel number on which the neighbor was found."
    ::= { ibDot11RRMNbrInfoEntry 2 }

ibDot11RRMNbrIntrf OBJECT-TYPE
    SYNTAX Integer32 (0..100)
    UNITS "percent"
    MAX-ACCESS read-only
    STATUS current
    DESCRIPTION
        "Interference observed on the channel in percentage by neighbor."
    ::= { ibDot11RRMNbrInfoEntry 3 }

ibDot11RrmNbrRSSI OBJECT-TYPE
    SYNTAX Integer32
    UNITS "dBm"
    MAX-ACCESS read-only
    STATUS current
    DESCRIPTION
        "Signal strength of the AP in dBm."
    ::= { ibDot11RRMNbrInfoEntry 4 }

ibDot11RrmNbrType OBJECT-TYPE
    SYNTAX INTEGER
        {
        managed(1),
        unmanaged(2)
        }
    MAX-ACCESS read-only
    STATUS current
    DESCRIPTION
        "Type of the AP, managed or unmanaged."
    ::= { ibDot11RRMNbrInfoEntry 5 }

ibDot11RrmNbrSSID OBJECT-TYPE
    SYNTAX IbDot11SSIDStringType
    MAX-ACCESS read-only
    STATUS current
    DESCRIPTION
        "SSID of the Neighbor."
    ::= { ibDot11RRMNbrInfoEntry 6 }

ibDot11RrmNbrSNR OBJECT-TYPE
    SYNTAX Integer32
    UNITS "dB"
    MAX-ACCESS read-only
    STATUS current
    DESCRIPTION
        "Signal to noise ratio of the AP in dB."
    ::= { ibDot11RRMNbrInfoEntry 7 }

ibDot11RrmNbrNF OBJECT-TYPE
    SYNTAX Integer32
    UNITS "dBm"
    MAX-ACCESS read-only
    STATUS current
    DESCRIPTION
        "Noise floor of the AP in dBm."
    ::= { ibDot11RRMNbrInfoEntry 8 }

ibDot11RRMHistoryTable OBJECT-TYPE
    SYNTAX SEQUENCE OF IbDot11RRMHistoryEntry
    MAX-ACCESS not-accessible
    STATUS current
    DESCRIPTION
        "This table shows the details of the latest three channel changes
        and power changes applied on all APs, including time of change,
        reason of the change and the channel, power, interference parameters."
    ::= { ibDot11RRMDetectGroup 3 }

ibDot11RRMHistoryEntry OBJECT-TYPE
    SYNTAX IbDot11RRMHistoryEntry
    MAX-ACCESS not-accessible
    STATUS current
    DESCRIPTION
        "Each entry shows the details of channel and power changes."
    INDEX { ibDot11RRMRadioIndex,
            ibDot11RRMHistoryId,
            ibDot11RRMHistoryRecIndctr }
    ::= { ibDot11RRMHistoryTable 1 }

IbDot11RRMHistoryEntry ::=
    SEQUENCE {
        ibDot11RRMHistoryId
            Integer32,
        ibDot11RRMHistoryRecIndctr
            INTEGER,
        ibDot11RRMHistoryChl
            IbDot11ChannelScopeType,
        ibDot11RRMHistoryPwr
            Integer32,
        ibDot11RRMHistoryLoad
            Integer32,
        ibDot11RRMHistoryUtlz
            Integer32,
        ibDot11RRMHistoryIntrf
            Integer32,
        ibDot11RRMHistoryNoise
            Integer32,
        ibDot11RRMHistoryPER
            Integer32,
        ibDot11RRMHistoryRetryRate
            Integer32,
        ibDot11RRMHistoryChgReason
            BITS,
        ibDot11RRMHistoryChgDateTime
            DateAndTime
     }

ibDot11RRMHistoryId OBJECT-TYPE
    SYNTAX Integer32
    MAX-ACCESS not-accessible
    STATUS current
    DESCRIPTION
        "History number of the change."
    ::= { ibDot11RRMHistoryEntry 1 }

ibDot11RRMHistoryRecIndctr OBJECT-TYPE
    SYNTAX INTEGER
        {
        before(1),
        after(2)
        }
    MAX-ACCESS not-accessible
    STATUS current
    DESCRIPTION
        "History record type of the change."
    ::= { ibDot11RRMHistoryEntry 2 }

ibDot11RRMHistoryChl OBJECT-TYPE
    SYNTAX IbDot11ChannelScopeType
    MAX-ACCESS read-only
    STATUS current
    DESCRIPTION
        "Channel on which the radio operates before/after the change
        of channel or power."
    ::= { ibDot11RRMHistoryEntry 3 }

ibDot11RRMHistoryPwr OBJECT-TYPE
    SYNTAX Integer32
    UNITS "dBm"
    MAX-ACCESS read-only
    STATUS current
    DESCRIPTION
        "Power of the radio before/after the change of channel or
        power."
    ::= { ibDot11RRMHistoryEntry 4 }

ibDot11RRMHistoryLoad OBJECT-TYPE
    SYNTAX Integer32 (0..100)
    UNITS "percent"
    MAX-ACCESS read-only
    STATUS current
    DESCRIPTION
        "Load observed on the radio in percentage before/after the
        change of channel or power."
    ::= { ibDot11RRMHistoryEntry 5 }

ibDot11RRMHistoryUtlz OBJECT-TYPE
    SYNTAX Integer32 (0..100)
    UNITS "percent"
    MAX-ACCESS read-only
    STATUS current
    DESCRIPTION
        "Utilization of the radio in percentage before/after the
        change of channel or power."
    ::= { ibDot11RRMHistoryEntry 6 }

ibDot11RRMHistoryIntrf OBJECT-TYPE
    SYNTAX Integer32 (0..100)
    UNITS "percent"
    MAX-ACCESS read-only
    STATUS current
    DESCRIPTION
        "Interference observed on the radio in percentage
        before/after the change of channel or power."
    ::= { ibDot11RRMHistoryEntry 7 }

ibDot11RRMHistoryNoise OBJECT-TYPE
    SYNTAX Integer32
    MAX-ACCESS read-only
    STATUS current
    DESCRIPTION
        "Noise observed on the radio before/after the change
        of channel or power."
    ::= { ibDot11RRMHistoryEntry 8 }

ibDot11RRMHistoryPER OBJECT-TYPE
    SYNTAX Integer32 (0..100)
    UNITS "percent"
    MAX-ACCESS read-only
    STATUS current
    DESCRIPTION
        "Packet error rate observed on the radio in percentage
        before/after the change of channel or power."
    ::= { ibDot11RRMHistoryEntry 9 }

ibDot11RRMHistoryRetryRate OBJECT-TYPE
    SYNTAX Integer32 (0..100)
    UNITS "percent"
    MAX-ACCESS read-only
    STATUS current
    DESCRIPTION
        "Percentage of retransmission happened on the radio
        before/after the change of channel or power."
    ::= { ibDot11RRMHistoryEntry 10 }

ibDot11RRMHistoryChgReason OBJECT-TYPE
    SYNTAX BITS
        {
        others(0),
        coverage(1),
        radar(2),
        retransmission(3),
        packetsDiscarded(4),
        interference(5)
        }
    MAX-ACCESS read-only
    STATUS current
    DESCRIPTION
        "Reason for the change of channel or power.
        The various bit positions are:
        |0        |Others                    |
        |1        |Coverage                  |
        |2        |Radar                     |
        |3        |Retransmission            |
        |4        |Packets discarded         |
        |5        |Interference              |
        0 is returned when the history record type is after."
    ::= { ibDot11RRMHistoryEntry 11 }

ibDot11RRMHistoryChgDateTime OBJECT-TYPE
    SYNTAX DateAndTime
    MAX-ACCESS read-only
    STATUS current
    DESCRIPTION
        "The time when the channel or power change occurred."
    ::= { ibDot11RRMHistoryEntry 12 }

ibDot11RRMRadioNbrInfoTable OBJECT-TYPE
    SYNTAX SEQUENCE OF IbDot11RRMRadioNbrInfoEntry
    MAX-ACCESS not-accessible
    STATUS current
    DESCRIPTION
        "This table shows the RRM neighbor information of each radio
        on all APs."
    ::= { ibDot11RRMDetectGroup 4 }

ibDot11RRMRadioNbrInfoEntry OBJECT-TYPE
    SYNTAX IbDot11RRMRadioNbrInfoEntry
    MAX-ACCESS not-accessible
    STATUS current
    DESCRIPTION
        "Each entry contains information of RRM neighbor information
        of the radio on an AP."
    INDEX { ibDot11RRMRadioNbrAPID, ibDot11RRMRadioNbrRadioID }
    ::= { ibDot11RRMRadioNbrInfoTable 1 }

IbDot11RRMRadioNbrInfoEntry ::=
    SEQUENCE {
        ibDot11RRMRadioNbrAPID
            IbDot11ObjectIDType,
        ibDot11RRMRadioNbrRadioID
            IbDot11RadioScopeType,
        ibDot11RRMRadioNbrSSID
            OCTET STRING
     }

ibDot11RRMRadioNbrAPID OBJECT-TYPE
    SYNTAX IbDot11ObjectIDType
    MAX-ACCESS not-accessible
    STATUS current
    DESCRIPTION
        "AP serial id."
    ::= { ibDot11RRMRadioNbrInfoEntry 1 }

ibDot11RRMRadioNbrRadioID OBJECT-TYPE
    SYNTAX IbDot11RadioScopeType
    MAX-ACCESS not-accessible
    STATUS current
    DESCRIPTION
        "Radio Id on AP."
    ::= { ibDot11RRMRadioNbrInfoEntry 2 }

ibDot11RRMRadioNbrSSID OBJECT-TYPE
    SYNTAX  OCTET STRING
    MAX-ACCESS read-only
    STATUS current
    DESCRIPTION
        "All neighbour SSIDs scanned by the selected radio."
    ::= { ibDot11RRMRadioNbrInfoEntry 3 }

ibDot11RRMNotifyGroup OBJECT IDENTIFIER ::= { ibDot11RRM 3 }

ibDot11RRMChlQltyNotifications OBJECT IDENTIFIER ::= { ibDot11RRMNotifyGroup 1 }

ibDot11RRMChlQltyNtfPrefix OBJECT IDENTIFIER ::= { ibDot11RRMChlQltyNotifications 0 }

ibDot11RRMIntrfLimit NOTIFICATION-TYPE
    OBJECTS { ibDot11RRMChlRptIntrf }
    STATUS current
    DESCRIPTION
        "This notification will be sent when interference on the radio
        exceeds the limit."
    ::= { ibDot11RRMChlQltyNtfPrefix 1 }

ibDot11RRMPERLimit NOTIFICATION-TYPE
    OBJECTS { ibDot11RRMChlRptPER }
    STATUS current
    DESCRIPTION
        "This notification will be sent when packet error rate on the
        radio exceeds the limit."
    ::= { ibDot11RRMChlQltyNtfPrefix 2 }

ibDot11RRMNoiseLimit NOTIFICATION-TYPE
    OBJECTS { ibDot11RRMChlRptNoise }
    STATUS current
    DESCRIPTION
        "This notification will be sent when noise on the radio exceeds
        the limit."
    ::= { ibDot11RRMChlQltyNtfPrefix 3 }

ibDot11RRMResChgNotifications OBJECT IDENTIFIER ::= { ibDot11RRMNotifyGroup 2 }

ibDot11RRMResChgNtfPrefix OBJECT IDENTIFIER ::= { ibDot11RRMResChgNotifications 0 }

ibDot11RRMPowerChange NOTIFICATION-TYPE
    OBJECTS { ibDot11RRMRadioIndex, ibDot11NewPower, ibDot11OldPower }
    STATUS current
    DESCRIPTION
        "This notification will be sent when power changed on the radio
        automatically."
    ::= { ibDot11RRMResChgNtfPrefix 1 }

ibDot11RRMNotificationsVar OBJECT IDENTIFIER ::= { ibDot11RRMNotifyGroup 3 }

ibDot11NewPower OBJECT-TYPE
    SYNTAX Integer32
    MAX-ACCESS accessible-for-notify
    STATUS current
    DESCRIPTION
        "Power of the radio after the change of power."
    ::= { ibDot11RRMNotificationsVar 1 }

ibDot11OldPower OBJECT-TYPE
    SYNTAX Integer32
    MAX-ACCESS accessible-for-notify
    STATUS current
    DESCRIPTION
        "Power of the radio before the change of power."
    ::= { ibDot11RRMNotificationsVar 2 }

ibDot11MonitorDetectedGroup OBJECT IDENTIFIER ::= { ibDot11RRM 4 }

ibDot11MonitorDetectedDevTable OBJECT-TYPE
    SYNTAX SEQUENCE OF IbDot11MonitorDetectedDevEntry
    MAX-ACCESS not-accessible
    STATUS current
    DESCRIPTION
        "This table shows the devices of AP detected"
    ::= { ibDot11MonitorDetectedGroup 1 }

ibDot11MonitorDetectedDevEntry OBJECT-TYPE
    SYNTAX      IbDot11MonitorDetectedDevEntry
    MAX-ACCESS  not-accessible
    STATUS      current
    DESCRIPTION
        "Each entry contains information of detected devices."
    INDEX
        {
            ibDot11MonitorDevMAC, ibDot11APElementIndex
        }
    ::= { ibDot11MonitorDetectedDevTable 1 }

IbDot11MonitorDetectedDevEntry ::=
    SEQUENCE {
        ibDot11MonitorDevMAC
            MacAddress,
        ibDot11MonitorDevType
            INTEGER,
        ibDot11MonitorDevVendor
            OCTET STRING,
        ibDot11MonitorDevSSID
            OCTET STRING,
        ibDot11MonitorDevBSSID
            MacAddress,
        ibDot11MonitorDevChannel
            IbDot11ChannelScopeType,
        ibDot11MonitorRadioId
            IbDot11RadioScopeType,
        ibDot11MonitorDevMaxRSSI
            Integer32,
        ibDot11MonitorDevBeaconIntvl
            Integer32,
        ibDot11MonitorDevFstDctTime
            DateAndTime,
        ibDot11MonitorDevLstDctTime
            DateAndTime,
        ibDot11MonitorDevClear
            TruthValue,
        ibDot11MonitorDevSNR
            Integer32
     }

ibDot11MonitorDevMAC OBJECT-TYPE
    SYNTAX      MacAddress
    MAX-ACCESS  not-accessible
    STATUS      current
    DESCRIPTION
        "Represents MAC address of the device detected."
    ::= { ibDot11MonitorDetectedDevEntry 1 }

ibDot11MonitorDevType OBJECT-TYPE
    SYNTAX      INTEGER
                {
                    client(1),
                    ap(2),
                    adhoc(3),
                    wirelessBridge(4),
                    unknown(5)
                }
    MAX-ACCESS  read-only
    STATUS      current
    DESCRIPTION
        "Represents type of the device detected."
    ::= { ibDot11MonitorDetectedDevEntry 2 }

ibDot11MonitorDevVendor OBJECT-TYPE
    SYNTAX      OCTET STRING
    MAX-ACCESS  read-only
    STATUS      current
    DESCRIPTION
        "Represents vendor of the detected device."
    ::= { ibDot11MonitorDetectedDevEntry 3 }

ibDot11MonitorDevSSID OBJECT-TYPE
    SYNTAX      OCTET STRING
    MAX-ACCESS  read-only
    STATUS      current
    DESCRIPTION
        "Represents the service set identifier for the ESS of the device which
         type is ap or adhoc."
    ::= { ibDot11MonitorDetectedDevEntry 4 }

ibDot11MonitorDevBSSID OBJECT-TYPE
    SYNTAX      MacAddress
    MAX-ACCESS  read-only
    STATUS      current
    DESCRIPTION
        "Represents the basic service set identifier of the detected device."
    ::= { ibDot11MonitorDetectedDevEntry 5 }

ibDot11MonitorDevChannel OBJECT-TYPE
    SYNTAX      IbDot11ChannelScopeType
    MAX-ACCESS  read-only
    STATUS      current
    DESCRIPTION
        "Represents the channel in which the device was last detected.  AP will
         choose the channel which has maximum signal strength as effective
         channel, as there is interference between adjacent channels."
    ::= { ibDot11MonitorDetectedDevEntry 6 }

ibDot11MonitorRadioId OBJECT-TYPE
    SYNTAX      IbDot11RadioScopeType
    MAX-ACCESS  read-only
    STATUS      current
    DESCRIPTION
        "Represents the radio ID of the AP that detected the device."
    ::= { ibDot11MonitorDetectedDevEntry 7 }

ibDot11MonitorDevMaxRSSI OBJECT-TYPE
    SYNTAX      Integer32
    UNITS       "dbm"
    MAX-ACCESS  read-only
    STATUS      current
    DESCRIPTION
        "Represents the maximum detected RSSI of the device in a scan report cycle."
    ::= { ibDot11MonitorDetectedDevEntry 8 }

ibDot11MonitorDevBeaconIntvl OBJECT-TYPE
    SYNTAX      Integer32
    UNITS       "millisecond"
    MAX-ACCESS  read-only
    STATUS      current
    DESCRIPTION
        "Represents the beacon interval for the detected device(not include
         the device which type is client)."
    ::= { ibDot11MonitorDetectedDevEntry 9 }

ibDot11MonitorDevFstDctTime OBJECT-TYPE
    SYNTAX      DateAndTime
    MAX-ACCESS  read-only
    STATUS      current
    DESCRIPTION
        "Represents the time at which the device was first detected."
    ::= { ibDot11MonitorDetectedDevEntry 10 }

ibDot11MonitorDevLstDctTime OBJECT-TYPE
    SYNTAX      DateAndTime
    MAX-ACCESS  read-only
    STATUS      current
    DESCRIPTION
        "Represents the time at which the device was detected last time."
    ::= { ibDot11MonitorDetectedDevEntry 11 }

ibDot11MonitorDevClear OBJECT-TYPE
    SYNTAX      TruthValue
    MAX-ACCESS  read-write
    STATUS      current
    DESCRIPTION
        "This object is used to clear the information of the device detected
         in the WLAN.
         It will return false for get operation."
    ::= { ibDot11MonitorDetectedDevEntry 12 }

ibDot11MonitorDevSNR OBJECT-TYPE
    SYNTAX      Integer32
    MAX-ACCESS  read-only
    STATUS      current
    DESCRIPTION
        "Represents the SNR of the device in a scan report cycle."
    ::= { ibDot11MonitorDetectedDevEntry 13 }

END
