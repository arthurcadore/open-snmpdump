-- ============================================================================
-- Copyright (C) 2023 Intelbras S.A. All rights reserved.
--
-- Description: Multicast Group Membership Discovery (MGMD) Management
--              Information Base (MIB).
-- Reference:
-- Version: V1.0
-- History:
-- V1.0 2022-03-28 Created by QIU YINGZHE
-- ============================================================================
--
-- Variables and types be imported
--
-- ============================================================================

IB-MGMD-STD-MIB DEFINITIONS ::= BEGIN


IMPORTS

    MODULE-IDENTITY,OBJECT-TYPE,NOTIFICATION-TYPE,
    Unsigned32
        FROM SNMPv2-SMI

    DisplayString
        FROM SNMPv2-TC

    ibCommon
        FROM IB-OID-MIB

    InetAddressType,InetAddress
        FROM INET-ADDRESS-MIB

    InterfaceIndex
        FROM IF-MIB;

ibMgmdStd MODULE-IDENTITY
    LAST-UPDATED "202203281100Z"
    ORGANIZATION
        "Intelbras S.A. Industria de Telecomunicacao Eletronica Brasileria."
    CONTACT-INFO
        ""
    DESCRIPTION
        "The Management MIB for Internet Group Management Protocol
        (IGMP) and Multicast Listener Discover (MLD)"

    -- Revision history.
    REVISION "202203281100Z"
    DESCRIPTION
        "The initial version of this MIB file."
    ::= { ibCommon 223 }


ibMgmdStdNotifications   OBJECT IDENTIFIER ::= { ibMgmdStd 0 }
ibMgmdStdTrapBindObjects OBJECT IDENTIFIER ::= { ibMgmdStd 1 }
ibMgmdStdObjects      OBJECT IDENTIFIER ::= { ibMgmdStd 2 }


ibMgmdStdInterfaceName OBJECT-TYPE
    SYNTAX     DisplayString (SIZE(1..64))
    MAX-ACCESS accessible-for-notify
    STATUS     current
    DESCRIPTION
            "The interface name of the interface for which IGMP or MLD
            is enabled."
    ::= { ibMgmdStdTrapBindObjects 1 }

ibMgmdStdInterfaceIfIndex OBJECT-TYPE
    SYNTAX     InterfaceIndex
    MAX-ACCESS accessible-for-notify
    STATUS     current
    DESCRIPTION
            "The ifIndex value of the interface for which IGMP or MLD
            is enabled.  The table is indexed by the ifIndex value and
            the InetAddressType to allow for interfaces which may be
            configured in both IPv4 and IPv6 modes."
    ::= { ibMgmdStdTrapBindObjects 2 }

ibMgmdStdGmpJoinVersion OBJECT-TYPE
    SYNTAX     Unsigned32(1..3)
    MAX-ACCESS accessible-for-notify
    STATUS     current
    DESCRIPTION
            "The version of MGMD which is running on this interface.
            Value 1 applies to IGMPv1 and MLDv1 version.  Value 2 applies
            to IGMPv2 and MLDv2 version, and value 3 applies to IGMPv3
            version.
            This object can be used to configure a router capable of
            running either version.  For IGMP and MLD to function
            correctly, all routers on a Local Area Network (LAN)
            must be configured to run the same version on that LAN.
            This object MAY be modified under any rowstatus condition."
    DEFVAL     { 2 }
    ::= { ibMgmdStdTrapBindObjects 3 }

ibMgmdStdAddressType OBJECT-TYPE
    SYNTAX     InetAddressType
    MAX-ACCESS accessible-for-notify
    STATUS     current
    DESCRIPTION
            "The address type of this IGMP or MLD message."
    ::= { ibMgmdStdTrapBindObjects 4}

ibMgmdStdGmpJoinSrcAddr OBJECT-TYPE
    SYNTAX     InetAddress
    MAX-ACCESS accessible-for-notify
    STATUS     current
    DESCRIPTION
           "The IGMP or MLD source address to join."
    ::= { ibMgmdStdTrapBindObjects 5 }

ibMgmdStdGmpJoinGrpAddr OBJECT-TYPE
    SYNTAX     InetAddress
    MAX-ACCESS accessible-for-notify
    STATUS     current
    DESCRIPTION
           "The IGMP or MLD group address to join."
    ::= { ibMgmdStdTrapBindObjects 6 }

ibMgmdStdGmpJoinSenderIp OBJECT-TYPE
    SYNTAX     InetAddress
    MAX-ACCESS accessible-for-notify
    STATUS     current
    DESCRIPTION
           "The host IP address for sending membership report."
    ::= { ibMgmdStdTrapBindObjects 7 }

ibMgmdStdInstanceName OBJECT-TYPE
    SYNTAX     DisplayString (SIZE (0..255))
    MAX-ACCESS accessible-for-notify
    STATUS     current
    DESCRIPTION
            "The Name of the Protocol Independent Multicast (PIM) instance."
    ::= { ibMgmdStdTrapBindObjects 8 }

ibMgmdStdGmpJoin NOTIFICATION-TYPE
    OBJECTS { ibMgmdStdInterfaceName,
              ibMgmdStdInterfaceIfIndex,
              ibMgmdStdGmpJoinVersion,
              ibMgmdStdAddressType,
              ibMgmdStdGmpJoinSrcAddr,
              ibMgmdStdGmpJoinGrpAddr,
              ibMgmdStdGmpJoinSenderIp,
              ibMgmdStdInstanceName
            }
    STATUS     current
    DESCRIPTION
            "An ibMgmdStdGmpJoin notification signifies the IGMP or MLD
            join message was received."
    ::= { ibMgmdStdNotifications 1 }

ibMgmdStdGmpLeave NOTIFICATION-TYPE
    OBJECTS { ibMgmdStdInterfaceName,
              ibMgmdStdInterfaceIfIndex,
              ibMgmdStdAddressType,
              ibMgmdStdGmpJoinSrcAddr,
              ibMgmdStdGmpJoinGrpAddr,
              ibMgmdStdGmpJoinSenderIp,
              ibMgmdStdInstanceName
            }
    STATUS     current
    DESCRIPTION
            "An ibMgmdStdGmpLeave notification signifies the IGMP or MLD
            group leaved."
    ::= { ibMgmdStdNotifications 2 }

ibMgmdStdGmpJoinNotifPeriod OBJECT-TYPE
    SYNTAX     Unsigned32 (0..65535)
    UNITS      "seconds"
    MAX-ACCESS read-write
    STATUS     current
    DESCRIPTION
            "The minimum time that must elapse between ibMgmdStdGmpJoin
            notifications originated by this router.  The maximum value
            65535 represents an 'infinite' time, in which case, no
            GmpJoin notifications are ever sent."
    DEFVAL { 65535 }
    ::= { ibMgmdStdObjects 1 }

ibMgmdStdGmpLeaveNotifPeriod OBJECT-TYPE
    SYNTAX     Unsigned32 (0..65535)
    UNITS      "seconds"
    MAX-ACCESS read-write
    STATUS     current
    DESCRIPTION
            "The minimum time that must elapse between ibMgmdStdGmpLeave
            notifications originated by this router.  The maximum value
            65535 represents an 'infinite' time, in which case, no
            GmpLeave notifications are ever sent."
    DEFVAL { 65535 }
    ::= { ibMgmdStdObjects 2 }

END
