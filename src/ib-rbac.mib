-- =================================================================
-- Copyright (C) 2023 Intelbras S.A. All rights reserved.
--
-- Description: This MIB is to provide the definition of the RBAC
--              (Role Based Access Control) system.
-- Reference:
-- Version: V1.1
-- History:
-- V1.0 2014-08-08 Initial version, created by Xu Yang
-- V1.1 2022.07.11 Updated by zhanghang
--      Added ibRbacTrap, ibRbacSuperTrap, ibRbacSuperTrapPrefix,
--      ibRbacSuperChangeSuccessful, and ibRbacSuperChangeFailure.
-- =================================================================

IB-RBAC-MIB DEFINITIONS ::= BEGIN

IMPORTS
    ibCommon
        FROM IB-OID-MIB
    Unsigned32, OBJECT-TYPE, MODULE-IDENTITY, NOTIFICATION-TYPE
        FROM SNMPv2-SMI
    TruthValue, RowStatus, StorageType, TEXTUAL-CONVENTION
        FROM SNMPv2-TC;

ibRbac MODULE-IDENTITY
    LAST-UPDATED "202207110000Z"
    ORGANIZATION
        "Intelbras S.A. Industria de Telecomunicacao Eletronica Brasileria."
    CONTACT-INFO
        ""
    DESCRIPTION
        "This MIB is to provide the definition of the RBAC
        (Role Based Access Control) system."
    REVISION "202207110000Z"
    DESCRIPTION
        "Added ibRbacTrap, ibRbacSuperTrap, ibRbacSuperTrapPrefix,
         ibRbacSuperChangeSuccessful, and ibRbacSuperChangeFailure."
    REVISION "201408081547Z"
    DESCRIPTION
        "The initial revision of this MIB module."
    ::= { ibCommon 158 }

-- Top-level structure of MIB
ibRbacNotifications  OBJECT IDENTIFIER ::= { ibRbac 0 }
ibRbacObjects  OBJECT IDENTIFIER ::= { ibRbac 1 }

ibRbacInfo  OBJECT IDENTIFIER
    ::= { ibRbacObjects 1 }

ibRbacConfig  OBJECT IDENTIFIER
    ::= { ibRbacObjects 2 }


-- definition of textual conventions

IbResourceType ::= TEXTUAL-CONVENTION
    STATUS       current
    DESCRIPTION
        "A User can be restricted from accessing resources by RBAC resource
        access policies.  There are four types of resource access policies as
        below:
        vlan(0)
                Bit value of 0 indicates that the user has access
                to no VLANs.
                Bit value of 1 indicates that the user has access
                to all VLANs.
                A user can be selectively assigned access to VLANs
                by configuring entries in the 'ibRbacPolicyTable'.
        interface(1)
                Bit value of 0 indicates that the user has access
                to no interfaces.
                Bit value of 1 indicates that the user has access
                to all interfaces.
                A user can be selectively assigned access to interfaces
                by configuring entries in the 'ibRbacPolicyTable'.
        vrf(2)
                Bit value of 0 indicates that the user has access
                to no VRFs.
                Bit value of 1 indicates that the user has access
                to all VRFs.
                A user can be selectively assigned access to VRFs
                by configuring entries in the 'ibRbacPolicyTable'.
        seczone(3)
                Bit value of 0 indicates that the user has access
                to no security zones.
                Bit value of 1 indicates that the user has access
                to all security zones.
                A user can be selectively assigned access to security zones
                by configuring entries in the 'ibRbacPolicyTable'."
    SYNTAX BITS
        {
            vlan(0),
            interface(1),
            vrf(2),
            seczone(3)
        }

IbRuleType ::= TEXTUAL-CONVENTION
    STATUS       current
    DESCRIPTION
        "There are two types of rules.  List as below:
        system: pre-defined by system and isn't editable.
        user: defined by user and is editable.
        "
    SYNTAX INTEGER
        {
            system(1),
            user(2)
        }

IbRuleOperation ::= TEXTUAL-CONVENTION
    STATUS       current
    DESCRIPTION
        "Privileges of a rule.
        exec  - execute operation
        read  - Read operation
        write - Write operation
        Note that if an operation is not supported by an entity,
        the operation does not apply to the entity."
    SYNTAX BITS
        {
            exec(0),
            read(1),
            write(2)
        }

IbRuleAction ::= TEXTUAL-CONVENTION
    STATUS       current
    DESCRIPTION
        "This indicates the action of a rule that defines the access privileges.
        permit  - permit the privileges
        deny    - deny the privileges
        "
    SYNTAX INTEGER
        {
            permit(1),
            deny(2)
        }

IbEntityType ::= TEXTUAL-CONVENTION
    STATUS       current
    DESCRIPTION
        "This indicates the type of the entity in a rule."
    SYNTAX INTEGER
        {
            unknown(1),
            command(2),
            feature(3),
            featuregroup(4),
            webmenu(5),
            xmlelement(6),
            oid(7)
        }


--
-- nodes defined
--

ibRbacRoleDefaultEnable OBJECT-TYPE
    SYNTAX TruthValue
    MAX-ACCESS read-write
    STATUS current
    DESCRIPTION
        "This object controls if an authenticated user can access the system
        when he or she isn't authorized any user roles.
        The default value is false."
    DEFVAL { false }
    ::= { ibRbacConfig 1 }

ibRbacRoleDefaultRoleName OBJECT-TYPE
    SYNTAX OCTET STRING (SIZE (1..63))
    MAX-ACCESS read-write
    STATUS current
    DESCRIPTION
        "If ibRbacRoleDefaultEnable is true, this object specifies
        the user role applied to the user when he or she accesses
        the system without any authorized user roles.
        If this object is not configured, the default user role
        applied is listed as below:
        network-operator - When login to the default MDC or default Context.
        mdc-operator     - When login to the non-default MDC.
        context-operator - When login to a non-default Context.
        "
    ::= { ibRbacConfig 2 }

--
-- definition of ibRbacRoleTable
--

ibRbacRoleTable OBJECT-TYPE
    SYNTAX SEQUENCE OF IbRbacRoleEntry
    MAX-ACCESS not-accessible
    STATUS current
    DESCRIPTION
        "This table shows the basic configuration information
        about all user roles."
    ::= { ibRbacConfig 3 }

ibRbacRoleEntry OBJECT-TYPE
    SYNTAX IbRbacRoleEntry
    MAX-ACCESS not-accessible
    STATUS current
    DESCRIPTION
        "An entry in the ibRbacRoleTable.
        One entry per role defined on the device."
    INDEX { ibRbacRoleName }
    ::= { ibRbacRoleTable 1 }

IbRbacRoleEntry ::=
    SEQUENCE {
        ibRbacRoleName            OCTET STRING,
        ibRbacRoleDescription     OCTET STRING,
        ibRbacRoleResourceAccess  IbResourceType,
        ibRbacRoleStorageType     StorageType,
        ibRbacRoleRowStatus       RowStatus
    }

ibRbacRoleName OBJECT-TYPE
    SYNTAX OCTET STRING (SIZE (1..63))
    MAX-ACCESS not-accessible
    STATUS current
    DESCRIPTION
        "The name of a role."
    ::= { ibRbacRoleEntry 1 }

ibRbacRoleDescription OBJECT-TYPE
    SYNTAX OCTET STRING (SIZE (0..128))
    MAX-ACCESS read-create
    STATUS current
    DESCRIPTION
        "Description of the role."
    ::= { ibRbacRoleEntry 2 }

ibRbacRoleResourceAccess OBJECT-TYPE
    SYNTAX IbResourceType
    MAX-ACCESS read-create
    STATUS current
    DESCRIPTION
        "Defines the default access to the resources to which access can be
        controlled.  For example a role which has access to all VLANs,
        all Interfaces, no VRF and no security zone will be 0011."
    ::= { ibRbacRoleEntry 3 }

ibRbacRoleStorageType OBJECT-TYPE
    SYNTAX          StorageType
    MAX-ACCESS      read-only
    STATUS          current
    DESCRIPTION
        "Storage type of this row."
    ::= { ibRbacRoleEntry 4 }

ibRbacRoleRowStatus OBJECT-TYPE
    SYNTAX          RowStatus
    MAX-ACCESS      read-create
    STATUS          current
    DESCRIPTION
        "Status of this row."
    ::= { ibRbacRoleEntry 5 }

--
-- definition of ibRbacRuleTable
--

ibRbacRuleTable OBJECT-TYPE
    SYNTAX SEQUENCE OF IbRbacRuleEntry
    MAX-ACCESS not-accessible
    STATUS current
    DESCRIPTION
        "This table shows the configuration information about rules
        in all user roles."
    ::= { ibRbacConfig 4 }


ibRbacRuleEntry OBJECT-TYPE
    SYNTAX IbRbacRuleEntry
    MAX-ACCESS not-accessible
    STATUS current
    DESCRIPTION
        "An entry in the ibRbacRuleTable.
        One entry indicates one rule in a role."
    INDEX {
        ibRbacRoleName,
        ibRbacRuleType,
        ibRbacRuleNumber
    }
    ::= { ibRbacRuleTable 1 }

IbRbacRuleEntry ::=
    SEQUENCE {
        ibRbacRuleType            IbRuleType,
        ibRbacRuleNumber          Unsigned32,
        ibRbacRuleAction          IbRuleAction,
        ibRbacRuleOperation       IbRuleOperation,
        ibRbacRuleEntityType      IbEntityType,
        ibRbacRuleEntity          OCTET STRING,
        ibRbacRuleRowStatus       RowStatus
    }


ibRbacRuleType OBJECT-TYPE
    SYNTAX IbRuleType
    MAX-ACCESS not-accessible
    STATUS current
    DESCRIPTION
        "The type of a rule."
    ::= { ibRbacRuleEntry 1 }

ibRbacRuleNumber OBJECT-TYPE
    SYNTAX Unsigned32 (1..256)
    MAX-ACCESS not-accessible
    STATUS current
    DESCRIPTION
        "The index of rules in one role.  There are two kinds of rules in a role.
        One is system defined, the other is user defined.  The total numbers
        of user defined rules is 1024.
        In one role, the user defined rules will be applied first and then
        the system defined rules.
        For the rules of same type, the following guidelines will be applied:
        Non-OID: If two rules of the same entity type conflict,
        the rule with the higher index takes effect.
        OID: If the MIB node specified in a rule is a child node of
        the MIB nodes specified in other rules, only this rule takes effect.
        If the same OID is specified in multiple rules, the rule with
        the higher index takes effect."
    ::= { ibRbacRuleEntry 2 }

ibRbacRuleAction OBJECT-TYPE
    SYNTAX IbRuleAction
    MAX-ACCESS read-create
    STATUS current
    DESCRIPTION
        "The action of a rule."
    ::= { ibRbacRuleEntry 3 }

ibRbacRuleOperation OBJECT-TYPE
    SYNTAX IbRuleOperation
    MAX-ACCESS read-create
    STATUS current
    DESCRIPTION
        "Privileges of a rule."
    ::= { ibRbacRuleEntry 4 }

ibRbacRuleEntityType OBJECT-TYPE
    SYNTAX IbEntityType
    MAX-ACCESS read-create
    STATUS current
    DESCRIPTION
        "This indicates the type of the entity in a rule.
        There are seven types of entity as below:
        unknown: invalid.
        command: a command or a set of commands that match a regular expression.
        feature: a feature which contains a set of commands.
        featuregroup: a group of features.
        webmenu: web menus.
        xmlelement: XML elements.
        oid: the specified MIB node and its child nodes."
    ::= { ibRbacRuleEntry 5 }

ibRbacRuleEntity OBJECT-TYPE
    SYNTAX OCTET STRING (SIZE (0..255))
    MAX-ACCESS read-create
    STATUS current
    DESCRIPTION
        "This indicates the entity that the privileges of rule apply to.
        It is may be a regular expression of commands, feature name,
        feature group name, web menu, xml element or oid.
        If the type of entity is feature or webmenu or xmlelement and the
        entity is a zero length string, then this rules applies to all
        the features or web menus or xml elements."
    ::= { ibRbacRuleEntry 6 }

ibRbacRuleRowStatus OBJECT-TYPE
    SYNTAX          RowStatus
    MAX-ACCESS      read-create
    STATUS          current
    DESCRIPTION
        "Status of this rule."
    ::= { ibRbacRuleEntry 7 }

--
-- definition of ibRbacPolicyTable
--

ibRbacPolicyTable OBJECT-TYPE
    SYNTAX SEQUENCE OF IbRbacPolicyEntry
    MAX-ACCESS not-accessible
    STATUS current
    DESCRIPTION
        "This table shows the configuration information about resource
        access policies in all user roles.  A role may be restricted
        from accessing various resources of a device.  This table
        lists the resources that a role can access."
    ::= { ibRbacConfig 5 }


ibRbacPolicyEntry OBJECT-TYPE
    SYNTAX IbRbacPolicyEntry
    MAX-ACCESS not-accessible
    STATUS current
    DESCRIPTION
        "An entry in the ibRbacPolicyTable.
        One entry indicates an accessible resource.
        If a role named 'R' can access VLAN1 to VLAN10,
        then there will be 10 entries in this table.
        There are two objects to specify the resource
        in this table.
        If the value of 'ibRbacPolicyType' is 'vlan' or
        'interface', the column 'ibRbacPolicyValue' is a
        four octets value which means vlan ID or IfIndex.
        If the value of 'ibRbacPolicyType' is 'vrf' or 'seczone',
        the column 'ibRbacPolicyValue' is a string indicating
        the name of the VRF or security zone."
    INDEX {
        ibRbacRoleName,
        ibRbacPolicyType,
        ibRbacPolicyValue
    }
    ::= { ibRbacPolicyTable 1 }

IbRbacPolicyEntry ::=
    SEQUENCE {
        ibRbacPolicyType            INTEGER,
        ibRbacPolicyValue           OCTET STRING,
        ibRbacPolicyRowStatus       RowStatus
    }

ibRbacPolicyType OBJECT-TYPE
    SYNTAX INTEGER
        {
            vlan(1),
            interface(2),
            vrf(3),
            seczone(4)
        }
    MAX-ACCESS      not-accessible
    STATUS          current
    DESCRIPTION
        "This object indicates the type of the resource
        access policy of this entry."
    ::= { ibRbacPolicyEntry 1 }

ibRbacPolicyValue OBJECT-TYPE
    SYNTAX          OCTET STRING (SIZE(1..64))
    MAX-ACCESS      not-accessible
    STATUS          current
    DESCRIPTION
        "This object identifies the resource this role can access.
        If the value of 'ibRbacPolicyType' is 'vlan' or
        'interface', the column 'ibRbacPolicyValue' is a
        four-octet-value which means vlan ID or IfIndex.
        If the value of 'ibRbacPolicyType' is 'vrf' or 'seczone',
        the column 'ibRbacPolicyValue' is a string indicating
        the name of the VRF or security zone."
    ::= { ibRbacPolicyEntry 2 }

ibRbacPolicyRowStatus OBJECT-TYPE
    SYNTAX          RowStatus
    MAX-ACCESS      read-create
    STATUS          current
    DESCRIPTION
        "Status of this row."
    ::= { ibRbacPolicyEntry 3 }

--
-- definition of ibRbacFeatureGroupTable
--

ibRbacFeatureGroupTable OBJECT-TYPE
    SYNTAX SEQUENCE OF IbRbacFeatureGroupEntry
    MAX-ACCESS not-accessible
    STATUS current
    DESCRIPTION
        "This table shows the configuration information about
        feature groups on a device."
    ::= { ibRbacConfig 6 }


ibRbacFeatureGroupEntry OBJECT-TYPE
    SYNTAX IbRbacFeatureGroupEntry
    MAX-ACCESS not-accessible
    STATUS current
    DESCRIPTION
        "An entry in the ibRbacFeatureGroupTable.
        One entry indicates a feature in particular group."
    INDEX {
        ibRbacFeatureGroupName
    }
    ::= { ibRbacFeatureGroupTable 1 }

IbRbacFeatureGroupEntry ::=
    SEQUENCE {
        ibRbacFeatureGroupName            OCTET STRING,
        ibRbacFeatureGroupRowStatus       RowStatus
    }

ibRbacFeatureGroupName OBJECT-TYPE
    SYNTAX          OCTET STRING (SIZE(1..31))
    MAX-ACCESS      not-accessible
    STATUS          current
    DESCRIPTION
        "This object indicates the name of a feature group."
    ::= { ibRbacFeatureGroupEntry 1 }

ibRbacFeatureGroupRowStatus OBJECT-TYPE
    SYNTAX          RowStatus
    MAX-ACCESS      read-create
    STATUS          current
    DESCRIPTION
        "Status of this row."
    ::= { ibRbacFeatureGroupEntry 2 }

--
-- definition of ibRbacFeaturesInGroupTable
--

ibRbacFeatureInGroupTable OBJECT-TYPE
    SYNTAX SEQUENCE OF IbRbacFeatureInGroupEntry
    MAX-ACCESS not-accessible
    STATUS current
    DESCRIPTION
        "This table shows the configuration information about
        features in feature groups on a device."
    ::= { ibRbacConfig 7 }


ibRbacFeatureInGroupEntry OBJECT-TYPE
    SYNTAX IbRbacFeatureInGroupEntry
    MAX-ACCESS not-accessible
    STATUS current
    DESCRIPTION
        "An entry in the ibRbacFeaturesInGroupTable.
        One entry indicates a feature in a particular group.
        If a newly created feature group doesn't contain any
        feature, there's no entry appearing in this table."
    INDEX {
        ibRbacFeatureGroupName,
        ibRbacFeatureNameInGroup
    }
    ::= { ibRbacFeatureInGroupTable 1 }

IbRbacFeatureInGroupEntry ::=
    SEQUENCE {
        ibRbacFeatureNameInGroup            OCTET STRING,
        ibRbacFeatureInGroupRowStatus       RowStatus
    }

ibRbacFeatureNameInGroup OBJECT-TYPE
    SYNTAX          OCTET STRING (SIZE(1..15))
    MAX-ACCESS      not-accessible
    STATUS          current
    DESCRIPTION
        "This object indicates the name of a feature in the feature group."
    ::= { ibRbacFeatureInGroupEntry 1 }

ibRbacFeatureInGroupRowStatus OBJECT-TYPE
    SYNTAX          RowStatus
    MAX-ACCESS      read-create
    STATUS          current
    DESCRIPTION
        "Status of this row."
    ::= { ibRbacFeatureInGroupEntry 2 }

--
-- definition of ibRbacFeatureTable
--

ibRbacFeatureTable OBJECT-TYPE
    SYNTAX SEQUENCE OF IbRbacFeatureEntry
    MAX-ACCESS not-accessible
    STATUS current
    DESCRIPTION
        "This table shows the information about features on a device."
    ::= { ibRbacInfo 1 }

ibRbacFeatureEntry OBJECT-TYPE
    SYNTAX IbRbacFeatureEntry
    MAX-ACCESS not-accessible
    STATUS current
    DESCRIPTION
        "An entry in the ibRbacFeatureTable.
        One entry indicates information about a feature on a device."
    INDEX {
        ibRbacFeatureName
    }
    ::= { ibRbacFeatureTable 1 }

IbRbacFeatureEntry ::=
    SEQUENCE {
        ibRbacFeatureName            OCTET STRING,
        ibRbacFeatureDescription     OCTET STRING
    }

ibRbacFeatureName OBJECT-TYPE
    SYNTAX          OCTET STRING (SIZE(1..15))
    MAX-ACCESS      not-accessible
    STATUS          current
    DESCRIPTION
        "This object indicates the name of a feature."
    ::= { ibRbacFeatureEntry 1 }

ibRbacFeatureDescription OBJECT-TYPE
    SYNTAX          OCTET STRING (SIZE(1..63))
    MAX-ACCESS      read-only
    STATUS          current
    DESCRIPTION
        "This object indicates the introduction of the feature."
    ::= { ibRbacFeatureEntry 2 }

-- ----------------------------------------------------------------------
-- ibRbacTrap Table
-- ----------------------------------------------------------------------
ibRbacTrap OBJECT IDENTIFIER ::= { ibRbac 2 }

-- ----------------------------------------------------------------------
-- ibRbacSuperTrap Table
-- ----------------------------------------------------------------------
ibRbacSuperTrap OBJECT IDENTIFIER ::= { ibRbacTrap 1 }

-- ----------------------------------------------------------------------
-- ibRbacSuperTrapPrefix
-- ----------------------------------------------------------------------
ibRbacSuperTrapPrefix OBJECT IDENTIFIER ::= { ibRbacSuperTrap 0 }

ibRbacSuperChangeSuccessful NOTIFICATION-TYPE
    STATUS current
    DESCRIPTION
        "Temporary user role authorization succeeded."
    ::= { ibRbacSuperTrapPrefix 1 }

ibRbacSuperChangeFailure NOTIFICATION-TYPE
    STATUS current
    DESCRIPTION
        "Temporary user role authorization failed."
    ::= { ibRbacSuperTrapPrefix 2 }

END
