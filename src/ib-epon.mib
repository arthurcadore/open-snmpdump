-- ===========================================================
-- Copyright (C) 2023 Intelbras S.A. All rights reserved.
-- Description:
-- Reference:
-- Version: V2.9
-- History:
-- V1.0 created by liyue.
--     Define MODULE-IDENTITY for ibEpon
-- V1.1 2005-12-21 Adjusted the structure of some tables and the value of
--        some objects by liuhongxu
--        Redefined the scope of some objects
-- V1.2 2006-01-09 Updated file by liuhongxu and zoudian.
--        Added ibEponOnuTypeManTable, ibOltPortAlarmRegExcessEnabled,
--        ibOnuBindType, ibOnuPCBVersion, ibOnuRtt, ibOnuEEPROMVersion,
--        ibOnuRegType, ibOnuHostType, ibEponOnuRegExcessTrap,
--        ibEponOnuRegExcessRecoverTrap, ibOnuSlaBandWidthStepVal.
--        Changed the description of ibOnuSlaMaxBandWidth and ibOnuSlaMinBandWidth.
--        Adjusted the format.
-- V1.3 2006-01-16 Updated file by lichunyan.
--        Added ibOnuPacketManTable, ibOnuProtocolTable, ibOnuMulticastFilterStatus,
--        ibOnuDot1xTable.
--        Changed the default value of ibOnuSlaMaxBandWidth.
--        Adjusted the format of this mib.
-- V1.4 2006-06-08 Updated by chenzhaojie
--        Delete default values of ibOnuSlaMinBandWidth and ibOnuSlaMaxBandWidth
-- V1.5 2006-08-02 Updated by chenzhaojie
--        Add ibOnuSlaDelay, ibOnuDistance, ibOnuPriorityQueueTable,
--        ibOnuCountTable, ibOnuPriorityQueueSizeMinVal, ibOnuPriorityQueueSizeMaxVal,
--        ibEponOnuPowerOffTrap, ibEponOltSwitchoverTrap, ibEponStatTable.
--        Change DESCRIPTION of ibOnuSlaMinBandWidthMinVal, ibOnuSlaMinBandWidthMaxVal.
-- V1.6 2006-09-06 Updated by chenzhaojie
--        Add ibOnuPriorityQueueBandwidthMinVal, ibOnuPriorityQueueBandwidthMaxVal,
--        ibOnuPriorityQueueBurstsizeMinVal, ibOnuPriorityQueueBurstsizeMaxVal.
--        Add ibOnuQueueBandwidthTable.
-- V1.7 2007-05-21 Updated by chenzhaojie
--        Add ibEponSysScalarGroup
--        Add ibEponSysManTable ,ibEponAutoUpdateTable,ibEponOuiTable.
--        Add ibEponOuiIndexNextTable, ibEponMulticastControlTable.
--        Add ibOltPortAlarmDFEEnabled to ibOltPortAlarmThresholdTable.
--        Add ibOnuDbaReportQueueSetNumber, ibOnuRemoteFecStatus,ibOnuPortBerStatus
--        ibOnuReset, ibOnuMulticastControlMode,ibOnuAccessVlan,ibOnuEncryptKey
--        to ibOnuSysManTable
--        Add ibOnuLlid to ibOnuInfoTable.
--        Add ibOnuIpAddressTable, ibOnuChipSetInfoTable, ibOnuCapabilityTable,
--        ibOnuDbaReportTable.
--        Add ibEponOltDFETrap, ibEponOltDFERecoverTrap
-- V1.8 2007-10-13 Updated by liuhongxu, andapeng, lihaijun
--        Add ibOltMaxRtt to ibOltSysManTable.
--        Add ibOnuUniUpDownTrapStatus, ibOnuDhcpsnooping, ibOnuPppoe,
--        ibOnuIgmpSnoopingHostAgingT, ibOnuIgmpSnoopingMaxRespT,
--        ibOnuIgmpSnoopingRouterAgingT, ibOnuIgmpSnoopingAggReportS,
--        ibOnuIgmpSnoopingAggLeaveS, ibOnuDhcpallocate, ibOnuManageVID,
--        ibOnuManageVlanIntfS.
--        Add ibOnuCosToLocalPrecedenceTable.
--        Add ibOnuFecStatus to ibOnuSysManTable.
--        Add ibOnuIpAddressGateway to ibOnuIpAddressTable.
--        Changed the default value of ibEponMonitorCycle.
-- V1.9 2008-1-15 Updated by fengjian, qinlei, lihaijun
--        Add ibOnuSilentTable.
--        Add ibOltUsingOnuTable.
--        Add ibOnuFirmwareUpdateByTypeTable.
--        Add ibOnuUpdateByTypeNextIndex
--        Add ibOnuUpdateFileName to ibOnuFirmwareUpdateTable.
--        Add ibOnuUpdateResult values.
--        Add ibOnuSlaFixedBandWidth and ibOnuSlaPriorityClass to ibOnuSlaManTable.
--        Add ibEponOnuRegSilentMac.
--        Add ibEponOnuSilenceTrap, ibEponOnuSilenceRecoverTrap.
--        Add ibEponOnuUpdateResultTrap to report onu update result.
-- V2.0 2008-3-17 Updated by zoudian
--        Add ibOnuMcastCtrlHostAgingTime, ibOnuMulticastFastLeaveEnable
--        and ibOnuPortIsolateEnable to ibOnuSysManTable.
--        Add ibOnuIgspFastLeaveSupported and ibOnuMCtrlFastLeaveSupported
--        to ibOnuCapabilityTable.
--        Add ibOnuSlaFixedPacketSize to ibOnuSlaManTable.
-- V2.1 2008-07-25 updated by zhaodan and zoudian.
--        Add ibEponOnuAutoBindTrap and ibEponOperationResult.
--        Add ibOnuFirmwareVersion and ibOnuVendorId to ibOnuInfoTable.
--        Change the description of ibOnuDistance.
-- V2.2 2009-08-18 updated by zhaodan.
--        Add ibEponOnuStpPortTable.
--        Add ibEponOnuPortStpStateTrap to ibEponTrapPrefix.
-- V2.3 2010-02-25 updated by zhaodan.
--        Add ibEponOnuLaserState and ibEponOnuLaserFailedTrap.
--        Add ibOnuOpticalPowerReceivedByOlt to ibOnuInfoTable.
--        Add ibOltOpticalPowerTx and ibOltOpticalPowerRx to ibOltInfoTable.
--        Add ibOnuPhysicalTable and ibOnuSmlkTable.
--        Add ibOnuSmlkSwitchoverTrap to ibEponTrapPrefix.
-- V2.4 2010-12-02 updated by zhaodan.
--        Add ibOnuRS485PropertiesTable, ibOnuRS485SessionSummaryTable,
--            ibOnuRS485SessionTable and ibOnuRS485SessionErrInfoTable.
-- V2.5 2015-05-12 updated by lvhuipeng.
--        Add ibOnuDbaReport2Table.
--        Modify ibEponMonitorCycle, ibOltDbaDiscoveryLength, ibOltDbaDiscovryFrequency
--        Modify ibOnuCosToLocalPrecedenceValue
--        Modify ibEponOnuStpPortTable
-- V2.6 2016-11-29 updated by zhuhaifeng.
--        Add ibOnuSilentLoidTable, ibOnuLoidInfoTable.
--        Modify ibOnuFirmwareUpdateTable, ibOnuFirmwareUpdateByTypeTable.
--        Modify ibOnuBindMacAddrTable, ibEponSysMan, ibOltSysManTable.
--        Modify ibEponErrorInfo, ibEponTrap.
--      2018-02-02 updated by zhuhaifeng.
--        Add ibOnuStatisticsTable, ibOltTransceiverTxPowerTable, ibEponOnuPowerOnTrap.
--        Add ibOnuSlaMaxBandWidthMinVal10G, ibOnuSlaMaxBandWidthMaxVal10G.
--        Add ibOnuSlaMinBandWidthMinVal10G, ibOnuSlaMinBandWidthMaxVal10G.
--        Add ibEponOnuBindOneToOne.
--        Modify ibOltSysManTable, ibOnuSlaManTable, ibOnuCapabilityTable.
--        Modify ibOnuSysManTable, ibOnuDownStreamMaxBandWidth.
-- V2.7 2018-10-12 updated by zhuhaifeng.
--        Add ibOnuServiceSlaTable, ibOnuServiceSlaQueTable.
--        Add ibEponOpticalSignalLosTrap, ibEponOpticalSignalLosRecoverTrap.
--        Add ibEponOnuFiberFailTrap, ibEponOnuFiberFailRecoverTrap.
--      2018-11-28 updated by zhuhaifeng.
--        Add ibOnuInfoMac, ibOnuInfoLoid to ibOnuInfoTable.
--        Add ibOnuPoeTable.
-- V2.8 2019-07-08 updated by yinfengming.
--        Add ibRoltInterfaceTable, ibRoltMemberTable.
--        Modify ibOltUsingOnuTable.
--      2019-07-10 updated by duzhaohui.
--        Add ibEponOnuBlackListMacTable, ibEponOnuBlackListLoidTable.
-- V2.9 2021-01-25 updated by zhuhaifeng.
--        Add ibOnuUpdateStartTime and ibOnuUpdateDuration to ibOnuFirmwareUpdateTable.
--        Add ibOnuUpdateByTypeStartTime and ibOnuUpdateByTypeDuration to ibOnuFirmwareUpdateByTypeTable.
-- =================================================================
IB-EPON-MIB DEFINITIONS ::= BEGIN

IMPORTS
        ibEpon
    FROM IB-OID-MIB
        ifIndex, ifDescr
    FROM IF-MIB
        ibLswFrameIndex, ibLswSlotIndex
    FROM IB-LSW-DEV-ADM-MIB
        Integer32, Unsigned32, Counter64, IpAddress, OBJECT-TYPE, MODULE-IDENTITY,
        NOTIFICATION-TYPE
    FROM SNMPv2-SMI
        TruthValue, MacAddress, DateAndTime, RowStatus, DisplayString
    FROM SNMPv2-TC
        InetAddress, InetAddressType
    FROM INET-ADDRESS-MIB;

ibEponMibObjects MODULE-IDENTITY
    LAST-UPDATED "202101251038Z"  -- January 25, 2021
    ORGANIZATION
        "Intelbras S.A. Industria de Telecomunicacao Eletronica Brasileria."
    CONTACT-INFO
        ""
    DESCRIPTION
        "
        The objects in this MIB module are used to manage and
        display current configuration of Ethernet Passive Optical
        Network (EPON) port which are based on the Ethernet in
        the First Mile (EFM) Passive Optical Network(PON) as
        defined in IEEE Draft P802.3ah/D3.0 clause 60, 64, 65..
        "
    REVISION    "202101251038Z"  -- January 25, 2021
    DESCRIPTION "Add the objects of ibOnuFirmwareUpdateTable, ibOnuFirmwareUpdateByTypeTable."
    REVISION    "201907101038Z"  -- July 10, 2019
    DESCRIPTION "Add the objects of ibEponOnuBlackListMacTable, ibEponOnuBlackListLoidTable."
    REVISION    "201907081049Z"  -- July 08, 2019
    DESCRIPTION "Add the objects of ibRoltInterfaceTable, ibRoltMemberTable.
                 Modify ibOltUsingOnuTable."
    REVISION    "201811281049Z"  -- November 28, 2018
    DESCRIPTION "Add the objects of ibOnuServiceSlaTable, ibOnuServiceSlaQueTable,
                 ibEponOpticalSignalLosTrap, ibEponOpticalSignalLosRecoverTrap,
                 ibEponOnuFiberFailTrap, and ibEponOnuFiberFailRecoverTrap.
                 Add ibOnuInfoMac, ibOnuInfoLoid to ibOnuInfoTable.
                 Add ibOnuPoeTable."
    REVISION    "201703061145Z"  -- March 06, 2017
    DESCRIPTION "Add the objects of ibOnuStatisticsTable, and ibOltTransceiverTxPowerTable,
                 update the objects of ibOnuCapabilityTable, and ibOnuSysManTable."
    REVISION    "201702101145Z"  -- February 10, 2017
    DESCRIPTION "Add the objects of ibOnuSilentLoidTable, and ibOnuLoidInfoTable,
                 update the objects of ibOnuFirmwareUpdateTable,
                 ibOnuFirmwareUpdateByTypeTable, ibOnuBindMacAddrTable, ibEponSysMan,
                 ibOltSysManTable, ibEponErrorInfo, and ibEponTrap."
    REVISION    "201508041145Z"  -- August 4, 2015
    DESCRIPTION "Add the objects of ibOnuDbaReport2Table, update the
                 objects of ibEponMonitorCycle, ibOltDbaDiscoveryLength,
                 ibOltDbaDiscovryFrequency, and ibEponOnuStpPortTable."
    ::= { ibEpon 1 }

ibEponSysMan OBJECT IDENTIFIER ::= { ibEponMibObjects 1 }

ibEponAutoAuthorize OBJECT-TYPE
    SYNTAX      TruthValue
    MAX-ACCESS  read-write
    STATUS      current
    DESCRIPTION
        "
        This value determines whether software performs
        self-authorization for each Optical Network Unit(ONU)
        registering to the network.  Setting it to false
        means for every ONU registering, software requires
        external authorization, and until it's done the
        ONU is not authenticated.  True value means software
        authorizes each ONU registering to the network
        automatically.
        true  - ONUs are always authorized.
        false - If 802.1x authorization is enable,
        the ONUs have to be authorized by
        the protocol.
        - If 802.1x authorization is disable,
        ONUs are always authorized.
        "
    DEFVAL { false }
    ::= { ibEponSysMan 1 }


ibEponMonitorCycle OBJECT-TYPE
    SYNTAX      Integer32(1..3600)
    MAX-ACCESS  read-write
    STATUS      current
    DESCRIPTION
        "
        The cycle of alarm thresholds checking.
        Applying to the following types:
        Bit Error Rate(BER) alarm, Frame Error Rate(FER),
        Logical Link Identity(LLID) mismatch alarm and so on.
        The unit is second.
        "
    DEFVAL { 80 }
    ::= { ibEponSysMan 2 }

ibEponMsgTimeOut OBJECT-TYPE
    SYNTAX      Integer32
    MAX-ACCESS  read-write
    STATUS      current
    DESCRIPTION
        "
        Timeout waiting for a response from Optical Line Terminal(OLT)
        firmware after sending it a message.
        The unit is millisecond.
        "
    DEFVAL { 600 }
    ::= { ibEponSysMan 3 }

ibEponMsgLoseNum OBJECT-TYPE
    SYNTAX      Integer32
    MAX-ACCESS  read-write
    STATUS      current
    DESCRIPTION
        "
        The times of messages sending timeouts, after
        which OLT will reset (applying to every OLT).
        "
    DEFVAL { 20 }
    ::= { ibEponSysMan 4 }

ibEponSysHasEPONBoard OBJECT-TYPE
    SYNTAX      TruthValue
    MAX-ACCESS  read-only
    STATUS      current
    DESCRIPTION
        "
        true(1)  - At least an EPON board exists.
        false(2) - No EPON board exists.
        "
    ::= { ibEponSysMan 5 }

ibEponMonitorCycleEnable OBJECT-TYPE
    SYNTAX      TruthValue
    MAX-ACCESS  read-write
    STATUS      current
    DESCRIPTION
        "
        Stop or continue monitoring.
        true(1)  - Continue monitoring.
        false(2) - Stop monitoring.
        "
    DEFVAL { true }
    ::= { ibEponSysMan 6 }

ibEponOltSoftwareErrAlmEnable OBJECT-TYPE
    SYNTAX      TruthValue
    MAX-ACCESS  read-write
    STATUS      current
    DESCRIPTION
        "
        Software error alarm behavior of all active OLTs.
        true(1)  - alarm enable.
        false(2) - alarm disable.
        "
    DEFVAL { true }
    ::= { ibEponSysMan 7 }

ibEponPortLoopBackAlmEnable OBJECT-TYPE
    SYNTAX      TruthValue
    MAX-ACCESS  read-write
    STATUS      current
    DESCRIPTION
        "
        LoopBack alarm behavior of EPON ports.
        true(1)  - alarm enable.
        false(2) - alarm disable.
        "
    DEFVAL { true }
    ::= { ibEponSysMan 8 }

ibEponMonitorCycleMinVal OBJECT-TYPE
    SYNTAX      Integer32
    MAX-ACCESS  read-only
    STATUS      current
    DESCRIPTION
        "
        The lower limit of cycle which be confined to the
        ibEponMonitorCycle.
        "
    ::= { ibEponSysMan 9 }

ibEponMonitorCycleMaxVal OBJECT-TYPE
    SYNTAX      Integer32
    MAX-ACCESS  read-only
    STATUS      current
    DESCRIPTION
        "
        The upper limit of cycle which be confined to the
        ibEponMonitorCycle.
        "
    ::= { ibEponSysMan 10 }

ibEponMsgTimeOutMinVal OBJECT-TYPE
    SYNTAX      Integer32
    MAX-ACCESS  read-only
    STATUS      current
    DESCRIPTION
        "
        The lower limit of timeout which be confined to the
        ibEponMsgTimeOut.
        "
    ::= { ibEponSysMan 11 }

ibEponMsgTimeOutMaxVal OBJECT-TYPE
    SYNTAX      Integer32
    MAX-ACCESS  read-only
    STATUS      current
    DESCRIPTION
        "
        The upper limit of timeout which be confined to the
        ibEponMsgTimeOut.
        "
    ::= { ibEponSysMan 12 }

ibEponMsgLoseNumMinVal OBJECT-TYPE
    SYNTAX      Integer32
    MAX-ACCESS  read-only
    STATUS      current
    DESCRIPTION
        "
        The lower limit of time which be confined to the
        ibEponMsgLoseNum.
        "
    ::= { ibEponSysMan 13 }

ibEponMsgLoseNumMaxVal OBJECT-TYPE
    SYNTAX      Integer32
    MAX-ACCESS  read-only
    STATUS      current
    DESCRIPTION
        "
        The upper limit of time which be confined to the
        ibEponMsgLoseNum.
        "
    ::= { ibEponSysMan 14 }

ibEponSysScalarGroup OBJECT IDENTIFIER ::= { ibEponSysMan 15 }

--
-- ibEponSysManTable
--

ibEponSysManTable OBJECT-TYPE
    SYNTAX      SEQUENCE OF IbEponSysManEntry
    MAX-ACCESS  not-accessible
    STATUS      current
    DESCRIPTION
        "
        This table defines system related parameters.
        "
    ::= { ibEponSysMan 16 }

ibEponSysManEntry OBJECT-TYPE
    SYNTAX      IbEponSysManEntry
    MAX-ACCESS  not-accessible
    STATUS      current
    DESCRIPTION
        "
        The entry of the table ibEponSysManTable.
        "
    INDEX
        {
            ibEponSlotIndex
        }
    ::= { ibEponSysManTable 1 }

IbEponSysManEntry ::= SEQUENCE
    {
        ibEponSlotIndex                   Integer32,
        ibEponModeSwitch                  INTEGER,
        ibEponAutomaticMode               INTEGER,
        ibEponOamDiscoveryTimeout         Integer32,
        ibEponEncryptionNoReplyTimeOut    Integer32,
        ibEponEncryptionUpdateTime        Integer32,
        ibEponAutoBindStatus              INTEGER,
        ibEponAutoBindType                BITS
    }

ibEponSlotIndex OBJECT-TYPE
    SYNTAX      Integer32
    MAX-ACCESS  not-accessible
    STATUS      current
    DESCRIPTION
        "
        Slot Index, the index of ibEponSysManTable.
        "
    ::= { ibEponSysManEntry 1 }

ibEponModeSwitch OBJECT-TYPE
    SYNTAX      INTEGER
        {
            cmode(1),
            hmode(2)
        }
    MAX-ACCESS  read-write
    STATUS      current
    DESCRIPTION
        "
        cmode - epon standard mode.
        hmode - private mode.
        "
    DEFVAL { cmode }
    ::= { ibEponSysManEntry 2 }

ibEponAutomaticMode OBJECT-TYPE
    SYNTAX      INTEGER
        {
            enable(1),
            disable(2)
        }
    MAX-ACCESS  read-write
    STATUS      current
    DESCRIPTION
        "
        Automatic mode setting: when enabled - after
        new OLT is added, the OLT stack sets its encryption mode
        to 'triple churning' and configure the OLT to authorize
        ONU MAC addresses according to its table.
        enable  -enable automatic mode.
        disable -disable automatic mode.
        "
    DEFVAL { enable }
    ::= { ibEponSysManEntry 3 }

ibEponOamDiscoveryTimeout OBJECT-TYPE
    SYNTAX      Integer32
    MAX-ACCESS  read-write
    STATUS      current
    DESCRIPTION
        "
        Time out parameter for extended OAM discovery
        process message, ranging from 0 to 2550,
        measured in 100 milliseconds.
        "
    DEFVAL { 30 }
    ::= { ibEponSysManEntry 4 }

ibEponEncryptionNoReplyTimeOut OBJECT-TYPE
    SYNTAX      Integer32
    MAX-ACCESS  read-write
    STATUS      current
    DESCRIPTION
        "
        Encryption response timeout,
        ranging from 1 to 2550,
        measured in 100 milliseconds.
        "
    DEFVAL { 30 }
    ::= { ibEponSysManEntry 5 }

ibEponEncryptionUpdateTime OBJECT-TYPE
    SYNTAX      Integer32
    MAX-ACCESS  read-write
    STATUS      current
    DESCRIPTION
        "
        Encryption key update timer for all ONUs on slot,
        indicated by ibEponSlotIndex,
        ranging from 1 to 255, measured in seconds.
        "
    DEFVAL { 10 }
    ::= { ibEponSysManEntry 6 }

ibEponAutoBindStatus OBJECT-TYPE
    SYNTAX      INTEGER
        {
            enable(1),
            disable(2)
        }
    MAX-ACCESS  read-write
    STATUS      current
    DESCRIPTION
        "
        enable  - auto bind ONU ID when the ONU registered in the EPON system.
        disable - need manual bind ONU ID when the ONU registered in the EPON system.
        "
    DEFVAL { disable }
    ::= { ibEponSysManEntry 7 }

ibEponAutoBindType OBJECT-TYPE
    SYNTAX      BITS
        {
            mac(0),
            loid(1),
            loidPassword(2)
        }
    MAX-ACCESS  read-write
    STATUS      current
    DESCRIPTION
        "
        Set auto binding type, which can be combined.
        If auto binding is disabled, 0 is returned.
        "
    ::= { ibEponSysManEntry 8 }

--
-- ibEponAutoUpdateTable
--
ibEponAutoUpdateTable OBJECT-TYPE
    SYNTAX      SEQUENCE OF IbEponAutoUpdateEntry
    MAX-ACCESS  not-accessible
    STATUS      current
    DESCRIPTION
        "
        EPON auto update ONU application configuration.
        "
    ::= { ibEponSysMan 17 }

ibEponAutoUpdateEntry OBJECT-TYPE
    SYNTAX      IbEponAutoUpdateEntry
    MAX-ACCESS  not-accessible
    STATUS      current
    DESCRIPTION
        "
        The entry of the table ibEponAutoUpdateTable.
        "
    INDEX
        {
            ibEponSlotIndex
        }
    ::= { ibEponAutoUpdateTable 1 }

IbEponAutoUpdateEntry ::= SEQUENCE
    {
        ibEponAutoUpdateFileName          DisplayString,
        ibEponAutoUpdateSchedStatus       INTEGER,
        ibEponAutoUpdateSchedTime         OCTET STRING,
        ibEponAutoUpdateSchedType         INTEGER,
        ibEponAutoUpdateRealTimeStatus    INTEGER
    }
ibEponAutoUpdateFileName OBJECT-TYPE
    SYNTAX      DisplayString(SIZE(0..255))
    MAX-ACCESS  read-write
    STATUS      current
    DESCRIPTION
        "
        The name of ONU application file,  the file name must be valid
        and include the path.  It is a zero length string by default.
        "
    ::= { ibEponAutoUpdateEntry 1 }

ibEponAutoUpdateSchedStatus OBJECT-TYPE
    SYNTAX      INTEGER
        {
            enable(1),
            disable(2)
        }
    MAX-ACCESS  read-write
    STATUS      current
    DESCRIPTION
        "
        The status of schedule update configuration.
        The ibEponAutoUpdateFileName must be set before enable
        ibEponAutoUpdateSchedStatus.
        enable - enable ONU schedule update.
        disable - disable ONU schedule update.
        "
    DEFVAL { disable }
    ::= { ibEponAutoUpdateEntry 2 }

ibEponAutoUpdateSchedTime OBJECT-TYPE
    SYNTAX      OCTET STRING(SIZE(0..255))
    MAX-ACCESS  read-write
    STATUS      current
    DESCRIPTION
        "
        The schedule update timing configuration is related to
        the ibEponAutoUpdateSchedType.
        auto update daily: the string format is hhmm
        auto update weekly: the string format is hhmmw
        'w' means update weekly, it ranges from 0 to 6:
        0 - Sunday.
        1 - Monday.
        2 - Tuesday.
        3 - Wednesday.
        4 - Thursday.
        5 - Friday.
        6 - Saturday.
        auto update in coming date : the string format is hhmmyyyymmdd.
        The configuration will take effect only if ibEponAutoUpdateSchedStatus
        is enabled.
        "
    ::= { ibEponAutoUpdateEntry 3 }

ibEponAutoUpdateSchedType OBJECT-TYPE
    SYNTAX      INTEGER
        {
            daily(1),
            weekly(2),
            comingdate(3)
        }
    MAX-ACCESS  read-write
    STATUS      current
    DESCRIPTION
        "
        The update type of auto updating configuration.
        daily - update ONU application every day.
        weekly - update ONU application every week.
        comingdate - update ONU application on coming date.
        "
    ::= { ibEponAutoUpdateEntry 4 }

ibEponAutoUpdateRealTimeStatus OBJECT-TYPE
    SYNTAX      INTEGER
        {
            enable(1),
            disable(2)
        }
    MAX-ACCESS  read-write
    STATUS      current
    DESCRIPTION
        "
        The status of real time update configuration.
        The ibEponAutoUpdateFileName must be set before enable
        ibEponAutoUpdateRealTimeStatus.
        enable - enable ONU real time update.
        disable - disable ONU real time update.
        "
    DEFVAL { disable }
    ::= { ibEponAutoUpdateEntry 5 }

--
-- ibEponOuiIndexNextTable
--

ibEponOuiIndexNextTable OBJECT-TYPE
    SYNTAX      SEQUENCE OF IbEponOuiIndexNextEntry
    MAX-ACCESS  not-accessible
    STATUS      current
    DESCRIPTION
        "
        Next OUI index table.
        "
    ::= { ibEponSysMan 18 }

ibEponOuiIndexNextEntry OBJECT-TYPE
    SYNTAX      IbEponOuiIndexNextEntry
    MAX-ACCESS  not-accessible
    STATUS      current
    DESCRIPTION
        "
        The entry of the table ibEponOuiIndexNextTable.
        "
    INDEX
        {
            ibEponSlotIndex
        }
    ::= { ibEponOuiIndexNextTable 1 }

IbEponOuiIndexNextEntry ::= SEQUENCE
    {
        ibEponOuiIndexNext    Integer32
    }

ibEponOuiIndexNext OBJECT-TYPE
    SYNTAX      Integer32
    MAX-ACCESS  read-only
    STATUS      current
    DESCRIPTION
        "
        This object contains an appropriate value to be used for
        ibEponOuiIndex when creating rows in the
        ibEponOuiTable.
        "
    ::= { ibEponOuiIndexNextEntry 1 }

--
-- ibEponOuiTable
--

ibEponOuiTable OBJECT-TYPE
    SYNTAX      SEQUENCE OF IbEponOuiEntry
    MAX-ACCESS  not-accessible
    STATUS      current
    DESCRIPTION
        "
        List of OUI and OAM supported by OLT.
        "
    ::= { ibEponSysMan 19 }

ibEponOuiEntry OBJECT-TYPE
    SYNTAX      IbEponOuiEntry
    MAX-ACCESS  not-accessible
    STATUS      current
    DESCRIPTION
        "
        The entry of the table ibEponOuiTable.
        "
    INDEX
        {
            ibEponSlotIndex,
            ibEponOuiIndex
        }
    ::= { ibEponOuiTable 1 }

IbEponOuiEntry ::= SEQUENCE
    {
        ibEponOuiIndex        Integer32,
        ibEponOuiValue        OCTET STRING,
        ibEponOamVersion      OCTET STRING,
        ibEponOuiRowStatus    RowStatus
    }

ibEponOuiIndex OBJECT-TYPE
    SYNTAX      Integer32
    MAX-ACCESS  not-accessible
    STATUS      current
    DESCRIPTION
        "
        The index of this table.
        "
    ::= { ibEponOuiEntry 1 }

ibEponOuiValue OBJECT-TYPE
    SYNTAX      OCTET STRING(SIZE(0..512))
    MAX-ACCESS  read-create
    STATUS      current
    DESCRIPTION
        "
        OUI list supported by the extended OAM discovery process.
        The OUI is composed of six octets.  The first six octets denote the first OUI ,
        the second six octets denote the second OUI, and the like.
        "
    ::= { ibEponOuiEntry 2 }


ibEponOamVersion OBJECT-TYPE
    SYNTAX      OCTET STRING(SIZE(0..255))
    MAX-ACCESS  read-create
    STATUS      current
    DESCRIPTION
        "
        Version of OAM protocol defined by the organization denoted by OUI.
        "
    ::= { ibEponOuiEntry 3 }

ibEponOuiRowStatus OBJECT-TYPE
    SYNTAX      RowStatus
    MAX-ACCESS  read-create
    STATUS      current
    DESCRIPTION
        "
        The status of this table entry.  Only active,
        createAndGo, and destroy are supported.
        "
    ::= { ibEponOuiEntry 4 }

--
-- ibEponMulticastControlTable
--

ibEponMulticastControlTable OBJECT-TYPE
    SYNTAX      SEQUENCE OF IbEponMulticastControlEntry
    MAX-ACCESS  not-accessible
    STATUS      current
    DESCRIPTION
        "
        Multicast control global configuration.
        "
    ::= { ibEponSysMan 20 }

ibEponMulticastControlEntry OBJECT-TYPE
    SYNTAX      IbEponMulticastControlEntry
    MAX-ACCESS  not-accessible
    STATUS      current
    DESCRIPTION
        "
        The entry of the table ibEponMulticastControlTable.
        "
    INDEX
        {
            ibEponMulticastVlanId
        }
    ::= { ibEponMulticastControlTable 1 }

IbEponMulticastControlEntry ::= SEQUENCE
    {
        ibEponMulticastVlanId         Integer32,
        ibEponMulticastAddressList    OCTET STRING,
        ibEponMulticastStatus         RowStatus
    }

ibEponMulticastVlanId OBJECT-TYPE
    SYNTAX      Integer32
    MAX-ACCESS  not-accessible
    STATUS      current
    DESCRIPTION
        "
        The index of this table.
        "
    ::= { ibEponMulticastControlEntry 1 }

ibEponMulticastAddressList OBJECT-TYPE
    SYNTAX      OCTET STRING(SIZE(0..255))
    MAX-ACCESS  read-create
    STATUS      current
    DESCRIPTION
        "
        The multicast address, each four octets represents a multicast address,
        the address section ranging from the first four octets to the second
        four octets, and the like.
        "
    ::= { ibEponMulticastControlEntry 2 }

ibEponMulticastStatus OBJECT-TYPE
    SYNTAX      RowStatus
    MAX-ACCESS  read-create
    STATUS      current
    DESCRIPTION
        "
        The status of this table entry. Only active,
        createAndGo, and destroy are supported.
        "
    ::= { ibEponMulticastControlEntry 3 }

ibEponAuthMode OBJECT-TYPE
    SYNTAX      BITS
        {
            mac(0),
            loid(1),
            loidPassword(2)
        }
    MAX-ACCESS  read-write
    STATUS      current
    DESCRIPTION
        "
        Set global auth mode, which can be combined(loid and loid-password cannot be configured at the same time).
        If no auth mode was set, 0 is returned.
        "
    ::= { ibEponSysMan 21 }

ibEponOnuBindOneToOne OBJECT-TYPE
    SYNTAX      TruthValue
    MAX-ACCESS  read-write
    STATUS      current
    DESCRIPTION
        "
        Enable or disable one-to-one ONU binding feature.
        true(1)  - feature enable.
        false(2) - feature disable.
        "
    ::= { ibEponSysMan 22 }

ibEponOnuBlackListMacTable OBJECT-TYPE
    SYNTAX      SEQUENCE OF IbEponOnuBlackListMacEntry
    MAX-ACCESS  not-accessible
    STATUS      current
    DESCRIPTION
        "
        The table contains the configurations for managing the ONU MAC blacklist.
        "
    ::= { ibEponSysMan 23 }

ibEponOnuBlackListMacEntry OBJECT-TYPE
    SYNTAX      IbEponOnuBlackListMacEntry
    MAX-ACCESS  not-accessible
    STATUS      current
    DESCRIPTION
        "
        The entry of the table ibEponOnuBlackListMacTable.
        "
    INDEX
        {
            ibEponOnuBlackListMac
        }
    ::= { ibEponOnuBlackListMacTable 1 }

IbEponOnuBlackListMacEntry  ::= SEQUENCE
    {
        ibEponOnuBlackListMac             MacAddress,
        ibEponOnuBlackListMacRowStatus    RowStatus
    }

ibEponOnuBlackListMac OBJECT-TYPE
    SYNTAX      MacAddress
    MAX-ACCESS  read-only
    STATUS      current
    DESCRIPTION
        "
        The ONU MAC blacklist value.  This value is used to specify the blacklist MAC
        which is bound by the ONU interface.
        "
    ::= { ibEponOnuBlackListMacEntry 1 }

ibEponOnuBlackListMacRowStatus OBJECT-TYPE
    SYNTAX      RowStatus
    MAX-ACCESS  read-create
    STATUS      current
    DESCRIPTION
        "
        This object is responsible for managing the creation,
        deletion and modification of rows, which supports active
        status and CreatAndGo, destroy operation.
        "
    ::= { ibEponOnuBlackListMacEntry 2 }

ibEponOnuBlackListLoidTable OBJECT-TYPE
    SYNTAX      SEQUENCE OF IbEponOnuBlackListLoidEntry
    MAX-ACCESS  not-accessible
    STATUS      current
    DESCRIPTION
        "
        The table contains the configurations for managing the ONU LOID blacklist.
        "
    ::= { ibEponSysMan 24 }

ibEponOnuBlackListLoidEntry OBJECT-TYPE
    SYNTAX      IbEponOnuBlackListLoidEntry
    MAX-ACCESS  not-accessible
    STATUS      current
    DESCRIPTION
        "
        The entry of the table ibEponOnuBlackListLoidTable.
        "
    INDEX
        {
            ibEponOnuBlackListLoid
        }
    ::= { ibEponOnuBlackListLoidTable 1 }

IbEponOnuBlackListLoidEntry  ::= SEQUENCE
    {
        ibEponOnuBlackListLoid            OCTET STRING,
        ibEponOnuBlackListLoidRowStatus   RowStatus
    }

ibEponOnuBlackListLoid    OBJECT-TYPE
    SYNTAX      OCTET STRING(SIZE(1..24))
    MAX-ACCESS  read-only
    STATUS      current
    DESCRIPTION
        "
        The ONU LOID blacklist value.  This value is used to specify the blacklist LOID
        which is bound by the ONU interface.
        "
    ::= { ibEponOnuBlackListLoidEntry 1 }

ibEponOnuBlackListLoidRowStatus OBJECT-TYPE
    SYNTAX      RowStatus
    MAX-ACCESS  read-create
    STATUS      current
    DESCRIPTION
        "
        This object is responsible for managing the creation,
        deletion and modification of rows, which supports active
        status and CreatAndGo, destroy operation.
        "
    ::= { ibEponOnuBlackListLoidEntry 2 }

ibEponFileName OBJECT IDENTIFIER ::= { ibEponMibObjects 2 }

ibEponDbaUpdateFileName OBJECT-TYPE
    SYNTAX      OCTET STRING(SIZE(0..64))
    MAX-ACCESS  read-write
    STATUS      current
    DESCRIPTION
        "
        The name of a binary file which is loaded to
        the OLT from an external source.  Note that the filename
        must contain the file path.
        "
    ::= { ibEponFileName 1 }

ibEponOnuUpdateFileName OBJECT-TYPE
    SYNTAX      OCTET STRING(SIZE(0..64))
    MAX-ACCESS  read-write
    STATUS      current
    DESCRIPTION
        "
        The filename of the ONU firmware to be updated.
        Note that the filename must contain the file path.
        "
    ::= { ibEponFileName 2 }

ibEponOltMan OBJECT IDENTIFIER ::= { ibEponMibObjects 3 }

--
-- ibOltSysManTable
--

ibOltSysManTable OBJECT-TYPE
    SYNTAX      SEQUENCE OF IbOltSysManEntry
    MAX-ACCESS  not-accessible
    STATUS      current
    DESCRIPTION
        "
        This table defines several OLT system parameters:
        (1)laser on time
        (2)laser off time
        (3)whether multiple copy broadcast
        (4)whether discard packet
        (5)self test
        (6)self test result
        "
    ::= { ibEponOltMan 1 }

ibOltSysManEntry OBJECT-TYPE
    SYNTAX      IbOltSysManEntry
    MAX-ACCESS  not-accessible
    STATUS      current
    DESCRIPTION
        "
        The entry of the table ibOltSysManTable.
        "
    INDEX
        {
            ifIndex
        }
    ::= { ibOltSysManTable 1 }

IbOltSysManEntry ::= SEQUENCE
    {
        ibOltLaserOnTime            Integer32,
        ibOltLaserOffTime           Integer32,
        ibOltMultiCopyBrdCast       TruthValue,
        ibOltEnableDiscardPacket    TruthValue,
        ibOltSelfTest               INTEGER,
        ibOltSelfTestResult         INTEGER,
        ibOltMaxRtt                 Unsigned32,
        ibOltAuthMode               BITS,
        ibOltOnuBindOneToOne        TruthValue
    }

ibOltLaserOnTime OBJECT-TYPE
    SYNTAX      Integer32
    MAX-ACCESS  read-write
    STATUS      current
    DESCRIPTION
        "
        The laser on time of the ONUs during the
        discovery process, measured in Time Quanta(TQ).
        "
    DEFVAL { 96 }
    ::= { ibOltSysManEntry 1 }

ibOltLaserOffTime OBJECT-TYPE
    SYNTAX      Integer32
    MAX-ACCESS  read-write
    STATUS      current
    DESCRIPTION
        "
        The laser off time of the ONUs during the
        discovery process, measured in TQ.
        "
    DEFVAL { 96 }
    ::= { ibOltSysManEntry 2 }

ibOltMultiCopyBrdCast OBJECT-TYPE
    SYNTAX      TruthValue
    MAX-ACCESS  read-write
    STATUS      current
    DESCRIPTION
        "
        true/false filtering of tagged  multicast frames.
        The software avert tagged downstream frames with
        multicast or broadcast DA to the PON and not to the
        CPU, except for special multicast frames
        (link-constraint, IGMP control and ARP) that are
        passed to the CPU regardless of this feature.
        "
    DEFVAL { false }
    ::= { ibOltSysManEntry 3 }

ibOltEnableDiscardPacket OBJECT-TYPE
    SYNTAX      TruthValue
    MAX-ACCESS  read-write
    STATUS      current
    DESCRIPTION
        "
        Forward(false)/discard(true) any frames received from
        unlearned source address when the inside address
        table of the original ONU entry reach to the limit.
        "
    DEFVAL { false }
    ::= { ibOltSysManEntry 4 }

ibOltSelfTest OBJECT-TYPE
    SYNTAX      INTEGER
        {
            selftest(1)
        }
    MAX-ACCESS  read-write
    STATUS      current
    DESCRIPTION
        "
        selftest(1): Test OLT to check whether it's OK.
        "
    ::= { ibOltSysManEntry 5 }

ibOltSelfTestResult OBJECT-TYPE
    SYNTAX      INTEGER
        {
            other(1),
            ok(2),
            fail(3)
        }
    MAX-ACCESS  read-only
    STATUS      current
    DESCRIPTION
        "
        The self test result of the specific OLT.
        other(1): The self test result is another reason.
        ok(2):    The self test result is OK.
        fail(3):  The self test result is fail.
        "
    ::= { ibOltSysManEntry 6 }

ibOltMaxRtt OBJECT-TYPE
    SYNTAX      Unsigned32
    MAX-ACCESS  read-write
    STATUS      current
    DESCRIPTION
        "
        Set the max Round Trip Time of this OLT.
        "
    ::= { ibOltSysManEntry 7 }

ibOltAuthMode OBJECT-TYPE
    SYNTAX      BITS
        {
            mac(0),
            loid(1),
            loidPassword(2)
        }
    MAX-ACCESS  read-write
    STATUS      current
    DESCRIPTION
        "
        Set the auth mode of this OLT, which can be combined(loid and loid-password cannot be configured at the same time).
        If no auth mode was set, 0 is returned.
        "
    ::= { ibOltSysManEntry 8 }

ibOltOnuBindOneToOne OBJECT-TYPE
    SYNTAX      TruthValue
    MAX-ACCESS  read-write
    STATUS      current
    DESCRIPTION
        "
        Enable or disable one-to-one ONU binding feature.
        true(1)  - feature enable.
        false(2) - feature disable.
        "
    ::= { ibOltSysManEntry 9 }
--
-- ibOltInfoTable
--
ibOltInfoTable OBJECT-TYPE
    SYNTAX      SEQUENCE OF IbOltInfoEntry
    MAX-ACCESS  not-accessible
    STATUS      current
    DESCRIPTION
        "
        Primary status of the specified OLT.
        There will be one row in this table for each
        information in the system.
        (1)Software and hardware versions of the specified OLT
        (ibOltFirmMajorVersion, ibOltFirmMinorVersion,
        ibOltHardMajorVersion, ibOltHardMinorVersion)
        (2)Several physical capabilities of an OLT device.
        (ibOltAgcLockTime, ibOltAgcCdrTime)
        (3)The operation(activation) status of an OLT.
        (ibOltMacAddress, ibOltWorkMode)
        "
    ::= { ibEponOltMan 2 }

ibOltInfoEntry OBJECT-TYPE
    SYNTAX      IbOltInfoEntry
    MAX-ACCESS  not-accessible
    STATUS      current
    DESCRIPTION
        "
        The entry of the table ibOltInfoTable.
        "
    INDEX
        {
            ifIndex
        }
    ::= { ibOltInfoTable 1 }

IbOltInfoEntry ::= SEQUENCE
    {
        ibOltFirmMajorVersion    OCTET STRING,
        ibOltFirmMinorVersion    OCTET STRING,
        ibOltHardMajorVersion    OCTET STRING,
        ibOltHardMinorVersion    OCTET STRING,
        ibOltAgcLockTime         Integer32,
        ibOltAgcCdrTime          Integer32,
        ibOltMacAddress          MacAddress,
        ibOltWorkMode            INTEGER,
        ibOltOpticalPowerTx      Integer32,
        ibOltOpticalPowerRx      Integer32
    }

ibOltFirmMajorVersion OBJECT-TYPE
    SYNTAX      OCTET STRING
    MAX-ACCESS  read-only
    STATUS      current
    DESCRIPTION
        "
        OLT firmware major version.  If the object length is
        zero, it means the version is unknown.
        "
    ::= { ibOltInfoEntry 1 }

ibOltFirmMinorVersion OBJECT-TYPE
    SYNTAX      OCTET STRING
    MAX-ACCESS  read-only
    STATUS      current
    DESCRIPTION
        "
        OLT firmware minor version.  If the object length is
        zero, it means the version is unknown.
        "
    ::= { ibOltInfoEntry 2 }

ibOltHardMajorVersion OBJECT-TYPE
    SYNTAX      OCTET STRING
    MAX-ACCESS  read-only
    STATUS      current
    DESCRIPTION
        "
        OLT hardware major version.  If the object length is
        zero, it means the version is unknown.
        "
    ::= { ibOltInfoEntry 3 }

ibOltHardMinorVersion OBJECT-TYPE
    SYNTAX      OCTET STRING
    MAX-ACCESS  read-only
    STATUS      current
    DESCRIPTION
        "
        OLT hardware minor version.  If the object length is
        zero, it means the version is unknown.
        "
    ::= { ibOltInfoEntry 4 }

ibOltAgcLockTime OBJECT-TYPE
    SYNTAX      Integer32
    MAX-ACCESS  read-only
    STATUS      current
    DESCRIPTION
        "
        PON upstream data Automatic Gain Control(AGC) lock time,
        measured in TQ,
        range: 1 - 2^15.
        0x7FFFFFFF: unknown value.
        "
    ::= { ibOltInfoEntry 5 }

ibOltAgcCdrTime OBJECT-TYPE
    SYNTAX      Integer32
    MAX-ACCESS  read-only
    STATUS      current
    DESCRIPTION
        "
        PON RX signal synchronization time,
        measured in TQ,
        range: 1 - 2^15.
        0x7FFFFFFF: unknown value
        "
    ::= { ibOltInfoEntry 6 }

ibOltMacAddress OBJECT-TYPE
    SYNTAX      MacAddress
    MAX-ACCESS  read-only
    STATUS      current
    DESCRIPTION
        "
        OLT MAC address.
        "
    ::= { ibOltInfoEntry 7 }

ibOltWorkMode OBJECT-TYPE
    SYNTAX      INTEGER
        {
            other(1),
            open(2),
            reset(3),
            closed(4)
        }
    MAX-ACCESS  read-only
    STATUS      current
    DESCRIPTION
        "
        The operation(activation) modes of an OLT.
        other(1)  - The OLT is in another mode.
        open(2)   - The OLT is open.
        reset(3)  - The OLT is reset.
        closed(4) - The OLT is closed.
        "
    ::= { ibOltInfoEntry 8 }

ibOltOpticalPowerTx OBJECT-TYPE
    SYNTAX      Integer32
    MAX-ACCESS  read-only
    STATUS      current
    DESCRIPTION
        "
        The optical power transmitted by this OLT.
        It measured in 0.01 dBm unit.
        "
    ::= { ibOltInfoEntry 9 }

ibOltOpticalPowerRx OBJECT-TYPE
    SYNTAX      Integer32
    MAX-ACCESS  read-only
    STATUS      current
    DESCRIPTION
        "
        The burst optical power received by this OLT.
        It measured in 0.01 dBm unit.
        "
    ::= { ibOltInfoEntry 10 }

--
-- ibOltDbaManTable
--
ibOltDbaManTable OBJECT-TYPE
    SYNTAX      SEQUENCE OF IbOltDbaManEntry
    MAX-ACCESS  not-accessible
    STATUS      current
    DESCRIPTION
        "
        This table defines the primary parameters of the
        Dynamic Bandwidth Allocation(DBA) algorithm applying to the OLT.
        "
    ::= { ibEponOltMan 3 }

ibOltDbaManEntry OBJECT-TYPE
    SYNTAX      IbOltDbaManEntry
    MAX-ACCESS  not-accessible
    STATUS      current
    DESCRIPTION
        "
        The entry of the table ibOltDbaManTable.
        "
    INDEX
        {
            ifIndex
        }
    ::= { ibOltDbaManTable 1 }

IbOltDbaManEntry ::= SEQUENCE
    {
        ibOltDbaEnabledType          INTEGER,
        ibOltDbaDiscoveryLength      Integer32,
        ibOltDbaDiscovryFrequency    Integer32,
        ibOltDbaCycleLength          Integer32,
        ibOltDbaVersion              OCTET STRING,
        ibOltDbaUpdate               INTEGER,
        ibOltDbaUpdateResult         INTEGER
    }

ibOltDbaEnabledType OBJECT-TYPE
    SYNTAX      INTEGER
        {
            internal(1),
            external(2)
        }
    MAX-ACCESS  read-write
    STATUS      current
    DESCRIPTION
        "
        Enable different types of the DBA algorithm.
        Start upstream dynamic bandwidth allocation algorithm,
        replacing former bandwidth allocation mechanism.
        internal(1) - OLT internal Service Level Agreement(SLA) based
        algorithm, always being activated.
        external(2) - DBA algorithm in a binary file which is loaded to
        the OLT from an external source.
        "
    DEFVAL { internal }
    ::= { ibOltDbaManEntry 1 }

ibOltDbaDiscoveryLength OBJECT-TYPE
    SYNTAX      Integer32
    MAX-ACCESS  read-write
    STATUS      current
    DESCRIPTION
        "
        Discovery length in TQ units.
        "
    ::= { ibOltDbaManEntry 2 }

ibOltDbaDiscovryFrequency OBJECT-TYPE
    SYNTAX      Integer32
    MAX-ACCESS  read-write
    STATUS      current
    DESCRIPTION
        "
        How often should the OLT send discovery frames to
        the ONUs, measured in grant cycles.
        "
    ::= { ibOltDbaManEntry 3 }

ibOltDbaCycleLength OBJECT-TYPE
    SYNTAX      Integer32
    MAX-ACCESS  read-write
    STATUS      current
    DESCRIPTION
        "
        The grant cycle length in TQ units.
        "
    DEFVAL { 65535 }
    ::= { ibOltDbaManEntry 4 }

ibOltDbaVersion OBJECT-TYPE
    SYNTAX      OCTET STRING
    MAX-ACCESS  read-only
    STATUS      current
    DESCRIPTION
        "
        DBA version of the OLT.
        "
    ::= { ibOltDbaManEntry 5 }

ibOltDbaUpdate OBJECT-TYPE
    SYNTAX      INTEGER
        {
            update(1)
        }
    MAX-ACCESS  read-write
    STATUS      current
    DESCRIPTION
        "
        Update(1): Update the DBA algorithm with a binary
        file which is loaded to the OLT from an external source(flash).
        Config the MIB object module ibEponDbaUpdateFileName.
        "
    ::= { ibOltDbaManEntry 6 }

ibOltDbaUpdateResult OBJECT-TYPE
    SYNTAX      INTEGER
        {
            other(1),
            ok(2),
            fail(3),
            fileNotExist(4),
            notSetFilename(5)
        }
    MAX-ACCESS  read-only
    STATUS      current
    DESCRIPTION
        "
        The latest DBA update result.
        other: The DBA update result is another reason.
        ok:    The DBA update result is OK.
        fail:  The DBA update result is fail.
        fileNotExist: The DBA update failed because the file
        does not exist.
        notSetFilename: The DBA filename is not set.
        "
    ::= { ibOltDbaManEntry 7 }

--
-- ibOltPortAlarmThresholdTable
--

ibOltPortAlarmThresholdTable OBJECT-TYPE
    SYNTAX      SEQUENCE OF IbOltPortAlarmThresholdEntry
    MAX-ACCESS  not-accessible
    STATUS      current
    DESCRIPTION
        "
        The table defines the alarm threshold of OLT.
        "
    ::= { ibEponOltMan 4 }

ibOltPortAlarmThresholdEntry OBJECT-TYPE
    SYNTAX      IbOltPortAlarmThresholdEntry
    MAX-ACCESS  not-accessible
    STATUS      current
    DESCRIPTION
        "
        The entry of the table ibOltPortAlarmThresholdTable.
        "
    INDEX
        {
            ifIndex
        }
    ::= { ibOltPortAlarmThresholdTable 1 }

IbOltPortAlarmThresholdEntry ::= SEQUENCE
    {
        ibOltPortAlarmBerEnabled                 TruthValue,
        ibOltPortAlarmBerDirect                  INTEGER,
        ibOltPortAlarmBerThreshold               Integer32,
        ibOltPortAlarmFerEnabled                 TruthValue,
        ibOltPortAlarmFerDirect                  INTEGER,
        ibOltPortAlarmFerThreshold               Integer32,
        ibOltPortAlarmLlidMismatchEnabled        TruthValue,
        ibOltPortAlarmLlidMismatchThreshold      Integer32,
        ibOltPortAlarmRemoteStableEnabled        TruthValue,
        ibOltPortAlarmLocalStableEnabled         TruthValue,
        ibOltPortAlarmRegistrationEnabled        TruthValue,
        ibOltPortAlarmOamDisconnectionEnabled    TruthValue,
        ibOltPortAlarmEncryptionKeyEnabled       TruthValue,
        ibOltPortAlarmVendorSpecificEnabled      TruthValue,
        ibOltPortAlarmRegExcessEnabled           TruthValue,
        ibOltPortAlarmDFEEnabled                 TruthValue
    }

ibOltPortAlarmBerEnabled OBJECT-TYPE
    SYNTAX      TruthValue
    MAX-ACCESS  read-write
    STATUS      current
    DESCRIPTION
        "
        Behavior of BER alarm.
        true(1)  - alarm enable.
        false(2) - alarm disable.
        "
    DEFVAL { true }
    ::= { ibOltPortAlarmThresholdEntry 1 }

ibOltPortAlarmBerDirect OBJECT-TYPE
    SYNTAX      INTEGER
        {
            berUplink(1),
            berDownlink(2),
            berAll(3)
        }
    MAX-ACCESS  read-write
    STATUS      current
    DESCRIPTION
        "
        Traffic direction to monitor for BER alarm.
        "
    DEFVAL { berAll }
    ::= { ibOltPortAlarmThresholdEntry 2 }

ibOltPortAlarmBerThreshold OBJECT-TYPE
    SYNTAX      Integer32
    MAX-ACCESS  read-write
    STATUS      current
    DESCRIPTION
        "
        BER threshold exceed which the alarm is raised.
        "
    DEFVAL { 10 }
    ::= { ibOltPortAlarmThresholdEntry 3 }

ibOltPortAlarmFerEnabled OBJECT-TYPE
    SYNTAX      TruthValue
    MAX-ACCESS  read-write
    STATUS      current
    DESCRIPTION
        "
        Behavior of FER alarm.
        true(1)  - alarm enable.
        false(2) - alarm disable.
        "
    DEFVAL { true }
    ::= { ibOltPortAlarmThresholdEntry 4 }

ibOltPortAlarmFerDirect OBJECT-TYPE
    SYNTAX      INTEGER
        {
            ferUplink(1),
            ferDownlink(2),
            ferAll(3)
        }
    MAX-ACCESS  read-write
    STATUS      current
    DESCRIPTION
        "
        Traffic direction to monitor for FER alarm.
        "
    DEFVAL { ferAll }
    ::= { ibOltPortAlarmThresholdEntry 5 }

ibOltPortAlarmFerThreshold OBJECT-TYPE
    SYNTAX      Integer32
    MAX-ACCESS  read-write
    STATUS      current
    DESCRIPTION
        "
        Frame error rate exceed threshold then the alarm is raised.
        "
    DEFVAL { 1 }
    ::= { ibOltPortAlarmThresholdEntry 6 }

ibOltPortAlarmLlidMismatchEnabled OBJECT-TYPE
    SYNTAX      TruthValue
    MAX-ACCESS  read-write
    STATUS      current
    DESCRIPTION
        "
        Behavior of LLID mismatch alarm.
        true(1)  - alarm enable.
        false(2) - alarm disable.
        "
    DEFVAL { false }
    ::= { ibOltPortAlarmThresholdEntry 7 }

ibOltPortAlarmLlidMismatchThreshold OBJECT-TYPE
    SYNTAX      Integer32
    MAX-ACCESS  read-write
    STATUS      current
    DESCRIPTION
        "
        The minimal number of mismatched frames exceed threshold then
        LLID mismatch alarm is raised.
        "
    DEFVAL { 5000 }
    ::= { ibOltPortAlarmThresholdEntry 8 }

ibOltPortAlarmRemoteStableEnabled OBJECT-TYPE
    SYNTAX      TruthValue
    MAX-ACCESS  read-write
    STATUS      current
    DESCRIPTION
        "
        Behavior of remote stable alarm.
        true(1)  - alarm enable.
        false(2) - alarm disable.
        "
    DEFVAL { true }
    ::= { ibOltPortAlarmThresholdEntry 9 }

ibOltPortAlarmLocalStableEnabled OBJECT-TYPE
    SYNTAX      TruthValue
    MAX-ACCESS  read-write
    STATUS      current
    DESCRIPTION
        "
        Behavior of local stable alarm.
        true(1)  - alarm enable.
        false(2) - alarm disable.
        "
    DEFVAL { true }
    ::= { ibOltPortAlarmThresholdEntry 10 }

ibOltPortAlarmRegistrationEnabled OBJECT-TYPE
    SYNTAX      TruthValue
    MAX-ACCESS  read-write
    STATUS      current
    DESCRIPTION
        "
        Behavior of registration alarm.
        true(1)  - alarm enable.
        false(2) - alarm disable.
        "
    DEFVAL { true }
    ::= { ibOltPortAlarmThresholdEntry 11 }

ibOltPortAlarmOamDisconnectionEnabled OBJECT-TYPE
    SYNTAX      TruthValue
    MAX-ACCESS  read-write
    STATUS      current
    DESCRIPTION
        "
        Behavior of Operations Administration and Maintenance(OAM)
        disconnection alarm.
        true(1)  - alarm enable.
        false(2) - alarm disable.
        "
    DEFVAL { true }
    ::= { ibOltPortAlarmThresholdEntry 12 }

ibOltPortAlarmEncryptionKeyEnabled OBJECT-TYPE
    SYNTAX      TruthValue
    MAX-ACCESS  read-write
    STATUS      current
    DESCRIPTION
        "
        Behavior of encryption bad key alarm.
        true(1)  - alarm enable.
        false(2) - alarm disable.
        "
    DEFVAL { true }
    ::= { ibOltPortAlarmThresholdEntry 13 }

ibOltPortAlarmVendorSpecificEnabled OBJECT-TYPE
    SYNTAX      TruthValue
    MAX-ACCESS  read-write
    STATUS      current
    DESCRIPTION
        "
        Behavior of vendor specific alarm.
        true(1)  - alarm enable.
        false(2) - alarm disable.
        "
    DEFVAL { true }
    ::= { ibOltPortAlarmThresholdEntry 14 }

ibOltPortAlarmRegExcessEnabled OBJECT-TYPE
    SYNTAX      TruthValue
    MAX-ACCESS  read-write
    STATUS      current
    DESCRIPTION
        "
        Behavior of ONU registering over limitation alarm.
        true(1)  - alarm enable.
        false(2) - alarm disable.
        "
    DEFVAL { true }
    ::= { ibOltPortAlarmThresholdEntry 15 }

ibOltPortAlarmDFEEnabled OBJECT-TYPE
    SYNTAX      TruthValue
    MAX-ACCESS  read-write
    STATUS      current
    DESCRIPTION
        "
        Behavior of device fatal error alarm.
        true  - alarm enable.
        false - alarm disable.
        "
    DEFVAL { true }
    ::= { ibOltPortAlarmThresholdEntry 16 }

ibOltLaserOnTimeMinVal OBJECT-TYPE
    SYNTAX      Integer32
    MAX-ACCESS  read-only
    STATUS      current
    DESCRIPTION
        "
        The lower limit of time which is confined to
        ibOltLaserOnTime.
        "
    ::= { ibEponOltMan 5 }

ibOltLaserOnTimeMaxVal OBJECT-TYPE
    SYNTAX      Integer32
    MAX-ACCESS  read-only
    STATUS      current
    DESCRIPTION
        "
        The upper limit of time which is confined to
        ibOltLaserOnTime.
        "
    ::= { ibEponOltMan 6 }

ibOltLaserOffTimeMinVal OBJECT-TYPE
    SYNTAX      Integer32
    MAX-ACCESS  read-only
    STATUS      current
    DESCRIPTION
        "
        The lower limit of time which is confined to
        ibOltLaserOffTime.
        "
    ::= { ibEponOltMan 7 }

ibOltLaserOffTimeMaxVal OBJECT-TYPE
    SYNTAX      Integer32
    MAX-ACCESS  read-only
    STATUS      current
    DESCRIPTION
        "
        The upper limit of time which is confined to
        ibOltLaserOffTime.
        "
    ::= { ibEponOltMan 8 }

ibOltDbaDiscoveryLengthMinVal OBJECT-TYPE
    SYNTAX      Integer32
    MAX-ACCESS  read-only
    STATUS      current
    DESCRIPTION
        "
        The lower limit of the discovery length which is confined to
        ibOltDbaDiscoveryLength.
        "
    ::= { ibEponOltMan 9 }

ibOltDbaDiscoveryLengthMaxVal OBJECT-TYPE
    SYNTAX      Integer32
    MAX-ACCESS  read-only
    STATUS      current
    DESCRIPTION
        "
        The upper limit of the discovery length which is confined to
        ibOltDbaDiscoveryLength.
        "
    ::= { ibEponOltMan 10 }

ibOltDbaDiscovryFrequencyMinVal OBJECT-TYPE
    SYNTAX      Integer32
    MAX-ACCESS  read-only
    STATUS      current
    DESCRIPTION
        "
        The lower limit of the discovery length which is confined to
        ibOltDbaDiscovryFrequency.
        "
    ::= { ibEponOltMan 11 }

ibOltDbaDiscovryFrequencyMaxVal OBJECT-TYPE
    SYNTAX      Integer32
    MAX-ACCESS  read-only
    STATUS      current
    DESCRIPTION
        "
        The upper limit of the discovery length which is confined to
        ibOltDbaDiscovryFrequency.
        "
    ::= { ibEponOltMan 12 }

ibOltDbaCycleLengthMinVal OBJECT-TYPE
    SYNTAX      Integer32
    MAX-ACCESS  read-only
    STATUS      current
    DESCRIPTION
        "
        The lower limit of the frames which is confined to
        ibOltDbaCycleLength.
        "
    ::= { ibEponOltMan 13 }

ibOltDbaCycleLengthMaxVal OBJECT-TYPE
    SYNTAX      Integer32
    MAX-ACCESS  read-only
    STATUS      current
    DESCRIPTION
        "
        The upper limit of the frames which is confined to
        ibOltDbaCycleLength.
        "
    ::= { ibEponOltMan 14 }

ibOltPortAlarmLlidMisMinVal OBJECT-TYPE
    SYNTAX      Integer32
    MAX-ACCESS  read-only
    STATUS      current
    DESCRIPTION
        "
        The lower limit of the frames which is confined to
        ibOltPortAlarmLlidMismatchThreshold.
        "
    ::= { ibEponOltMan 15 }

ibOltPortAlarmLlidMisMaxVal OBJECT-TYPE
    SYNTAX      Integer32
    MAX-ACCESS  read-only
    STATUS      current
    DESCRIPTION
        "
        The upper limit of the frames which is confined to
        ibOltPortAlarmLlidMismatchThreshold.
        "
    ::= { ibEponOltMan 16 }

ibOltPortAlarmBerMinVal OBJECT-TYPE
    SYNTAX      Integer32
    MAX-ACCESS  read-only
    STATUS      current
    DESCRIPTION
        "
        The lower limit of threshold which is confined to
        ibOltPortAlarmBerThreshold.
        "
    ::= { ibEponOltMan 17 }

ibOltPortAlarmBerMaxVal OBJECT-TYPE
    SYNTAX      Integer32
    MAX-ACCESS  read-only
    STATUS      current
    DESCRIPTION
        "
        The upper limit of threshold which is confined to
        ibOltPortAlarmBerThreshold.
        "
    ::= { ibEponOltMan 18 }

ibOltPortAlarmFerMinVal OBJECT-TYPE
    SYNTAX      Integer32
    MAX-ACCESS  read-only
    STATUS      current
    DESCRIPTION
        "
        The lower limit of threshold which is confined to
        ibOltPortAlarmFerThreshold.
        "
    ::= { ibEponOltMan 19 }

ibOltPortAlarmFerMaxVal OBJECT-TYPE
    SYNTAX      Integer32
    MAX-ACCESS  read-only
    STATUS      current
    DESCRIPTION
        "
        The upper limit of threshold which is confined to
        ibOltPortAlarmFerThreshold.
        "
    ::= { ibEponOltMan 20 }

--
-- ibOnuSilentTable
--

ibOnuSilentTable OBJECT-TYPE
    SYNTAX      SEQUENCE OF IbOnuSilentEntry
    MAX-ACCESS  not-accessible
    STATUS      current
    DESCRIPTION
        "
        This table is used for getting silent ONU information of OLT.
        "
    ::= { ibEponOltMan 21 }

ibOnuSilentEntry OBJECT-TYPE
    SYNTAX      IbOnuSilentEntry
    MAX-ACCESS  not-accessible
    STATUS      current
    DESCRIPTION
        "
        The entry of the table ibOnuSilentTable.
        "
    INDEX
        {
            ifIndex,
            ibOnuSilentMacAddr
        }
    ::= { ibOnuSilentTable 1 }

IbOnuSilentEntry ::= SEQUENCE
    {
        ibOnuSilentMacAddr    MacAddress,
        ibOnuSilentTime       Integer32
    }

ibOnuSilentMacAddr OBJECT-TYPE
    SYNTAX      MacAddress
    MAX-ACCESS  not-accessible
    STATUS      current
    DESCRIPTION
        "
        The MAC address of silent ONUs in OLT.
        "
    ::= { ibOnuSilentEntry 1 }

ibOnuSilentTime OBJECT-TYPE
    SYNTAX      Integer32
    MAX-ACCESS  read-only
    STATUS      current
    DESCRIPTION
        "
        The aging time of a silent ONU.
        "
    ::= { ibOnuSilentEntry 2 }

--
-- ibOltUsingOnuTable
--

ibOltUsingOnuTable OBJECT-TYPE
    SYNTAX      SEQUENCE OF IbOltUsingOnuEntry
    MAX-ACCESS  not-accessible
    STATUS      current
    DESCRIPTION
        "
        The table containing configurations to manage ONU interface(s)
        based on OLT interface.
        "
    ::= { ibEponOltMan 22 }

ibOltUsingOnuEntry OBJECT-TYPE
    SYNTAX      IbOltUsingOnuEntry
    MAX-ACCESS  not-accessible
    STATUS      current
    DESCRIPTION
        "
        The entry of the table ibOltUsingOnuTable.
        "
    INDEX
        {
            ifIndex,
            ibOltUsingOnuNum
        }
    ::= { ibOltUsingOnuTable 1 }

IbOltUsingOnuEntry  ::= SEQUENCE
    {
        ibOltUsingOnuNum          Integer32,
        ibOltUsingOnuIfIndex      Integer32,
        ibOltUsingOnuRowStatus    RowStatus
    }

ibOltUsingOnuNum OBJECT-TYPE
    SYNTAX      Integer32(1..128)
    MAX-ACCESS  not-accessible
    STATUS      current
    DESCRIPTION
        "
        The ONU interface number.  This value is used to specify the ONU interface
        which the user wants to configure for an OLT interface.
        "
    ::= { ibOltUsingOnuEntry 1 }

ibOltUsingOnuIfIndex OBJECT-TYPE
    SYNTAX      Integer32
    MAX-ACCESS  read-only
    STATUS      current
    DESCRIPTION
        "
        The ifIndex of the ONU interface.
        "
    ::= { ibOltUsingOnuEntry 2 }

ibOltUsingOnuRowStatus OBJECT-TYPE
    SYNTAX      RowStatus
    MAX-ACCESS  read-create
    STATUS      current
    DESCRIPTION
        "
        This object is responsible for managing the creation,
        deletion and modification of rows, which supports active
        status and CreatAndGo, destroy operation.
        "
    ::= { ibOltUsingOnuEntry 3 }

--
-- ibOnuSilentLoidTable
--

ibOnuSilentLoidTable OBJECT-TYPE
    SYNTAX      SEQUENCE OF IbOnuSilentLoidEntry
    MAX-ACCESS  not-accessible
    STATUS      current
    DESCRIPTION
        "
        This table is used for getting silent ONU's LOID information of an OLT.
        "
    ::= { ibEponOltMan 23 }

ibOnuSilentLoidEntry OBJECT-TYPE
    SYNTAX      IbOnuSilentLoidEntry
    MAX-ACCESS  not-accessible
    STATUS      current
    DESCRIPTION
        "
        The entry of the table ibOnuSilentLoidTable.
        "
    INDEX
        {
            ifIndex,
            ibOnuSilentLoid
        }
    ::= { ibOnuSilentLoidTable 1 }

IbOnuSilentLoidEntry ::= SEQUENCE
    {
        ibOnuSilentLoid       OCTET STRING,
        ibOnuSilentLoidTime   Integer32
    }

ibOnuSilentLoid OBJECT-TYPE
    SYNTAX      OCTET STRING(SIZE(1..24))
    MAX-ACCESS  not-accessible
    STATUS      current
    DESCRIPTION
        "
        The LOID of a silent ONU in an OLT.
        "
    ::= { ibOnuSilentLoidEntry 1 }

ibOnuSilentLoidTime OBJECT-TYPE
    SYNTAX      Integer32
    MAX-ACCESS  read-only
    STATUS      current
    DESCRIPTION
        "
        The aging time of a silent ONU.
        "
    ::= { ibOnuSilentLoidEntry 2 }

--
-- ibOltTransceiverTxPowerTable
--

ibOltTransceiverTxPowerTable OBJECT-TYPE
    SYNTAX      SEQUENCE OF IbOltTransceiverTxPowerEntry
    MAX-ACCESS  not-accessible
    STATUS      current
    DESCRIPTION
        "
        This table is used for setting ONU's Tx power on an OLT.
        "
    ::= { ibEponOltMan 24 }

ibOltTransceiverTxPowerEntry OBJECT-TYPE
    SYNTAX      IbOltTransceiverTxPowerEntry
    MAX-ACCESS  not-accessible
    STATUS      current
    DESCRIPTION
        "
        The entry of the table ibOltTransceiverTxPowerTable.
        "
    INDEX
        {
            ifIndex
        }
    ::= { ibOltTransceiverTxPowerTable 1 }

IbOltTransceiverTxPowerEntry ::= SEQUENCE
    {
        ibOltTransTxPwrTransId             INTEGER,
        ibOltTransTxPwrOffTime             Unsigned32,
        ibOltTransTxPwrIsAllOnu            TruthValue,
        ibOltTransTxPwrOnuIfList           OCTET STRING
    }

ibOltTransTxPwrTransId OBJECT-TYPE
    SYNTAX      INTEGER
        {
            main(0),
            standby(1),
            all(2)
        }
    MAX-ACCESS  read-write
    STATUS      current
    DESCRIPTION
        "
        The transceiver ID of an ONU in an OLT.
        "
    ::= { ibOltTransceiverTxPowerEntry 1 }

ibOltTransTxPwrOffTime OBJECT-TYPE
    SYNTAX      Unsigned32
    MAX-ACCESS  read-write
    STATUS      current
    DESCRIPTION
        "
        The turnoff time of the transceiver Tx power.
        "
    ::= { ibOltTransceiverTxPowerEntry 2 }

ibOltTransTxPwrIsAllOnu OBJECT-TYPE
    SYNTAX      TruthValue
    MAX-ACCESS  read-write
    STATUS      current
    DESCRIPTION
        "
        Setting all ONUs' transceiver Tx power or not.
        "
    ::= { ibOltTransceiverTxPowerEntry 3 }

ibOltTransTxPwrOnuIfList OBJECT-TYPE
    SYNTAX      OCTET STRING(SIZE(0..20))
    MAX-ACCESS  read-write
    STATUS      current
    DESCRIPTION
        "
        ONUs' ifIndex for which the transceiver Tx power is to be set.
        "
    ::= { ibOltTransceiverTxPowerEntry 4 }

ibEponOnuMan OBJECT IDENTIFIER ::= { ibEponMibObjects 5 }

--
-- ibOnuSysManTable
--

ibOnuSysManTable OBJECT-TYPE
    SYNTAX      SEQUENCE OF IbOnuSysManEntry
    MAX-ACCESS  not-accessible
    STATUS      current
    DESCRIPTION
        "
        This table implements the following functions for ONUs:
        1. Encrypting all downstream/upstream and
        downstream directions traffic destined to and
        originated from a specific LLID
        (ONU in current implementation).
        2. Restart a process of ONU authentication, using
        the OLT (IEEE 802.1x) authenticator.
        "
    ::= { ibEponOnuMan 1 }

ibOnuSysManEntry OBJECT-TYPE
    SYNTAX      IbOnuSysManEntry
    MAX-ACCESS  not-accessible
    STATUS      current
    DESCRIPTION
        "
        The entry of the table ibOnuSysManTable.
        "
    INDEX
        {
            ifIndex
        }
    ::= { ibOnuSysManTable 1 }

IbOnuSysManEntry ::= SEQUENCE
    {
        ibOnuEncryptMan                 INTEGER,
        ibOnuReAuthorize                INTEGER,
        ibOnuMulticastFilterStatus      TruthValue,
        ibOnuDbaReportQueueSetNumber    Integer32,
        ibOnuRemoteFecStatus            INTEGER,
        ibOnuPortBerStatus              INTEGER,
        ibOnuReset                      INTEGER,
        ibOnuMulticastControlMode       INTEGER,
        ibOnuAccessVlan                 Integer32,
        ibOnuEncryptKey                 DisplayString,
        ibOnuUniUpDownTrapStatus        TruthValue,
        ibOnuFecStatus                  INTEGER,
        ibOnuMcastCtrlHostAgingTime     Integer32,
        ibOnuMulticastFastLeaveEnable   TruthValue,
        ibOnuPortIsolateEnable          TruthValue,
        ibOnuMacAddressTimer            Unsigned32
    }

ibOnuEncryptMan OBJECT-TYPE
    SYNTAX      INTEGER
        {
            off(1),
            downlink(2),
            updownlink(3)
        }
    MAX-ACCESS  read-write
    STATUS      current
    DESCRIPTION
        "
        Start encrypting all downstream/upstream and downstream
        directions traffic destined to and originated from a
        specific LLID (ONU in current implementation).  ONU
        registration encryption key is used as an initial value.
        If the encryption key was updated after ONU
        registration, the last updated key is used.
        off(1):        - Stop encrypting.
        downlink(2):   - Start encrypting all downstream
        directions traffic.
        updownlink(3): - Start encrypting all downstream/upstream
        directions traffic.
        "
    DEFVAL { downlink }
    ::= { ibOnuSysManEntry 1 }

ibOnuReAuthorize OBJECT-TYPE
    SYNTAX      INTEGER
        {
            reAuthorize(1)
        }
    MAX-ACCESS  read-write
    STATUS      current
    DESCRIPTION
        "
        Restart a process of ONU authentication.
        If 802.1x authentication is enabled, the OLT
        (IEEE 802.1x) authenticator is applied.
        Otherwise, use the default authentication.
        Until the reauthentication succeeds, the ONU remains
        its previous authorization mode.
        The reauthentication process includes a new
        authentication request sent to the authentication server.
        "
    ::= { ibOnuSysManEntry 2 }

ibOnuMulticastFilterStatus OBJECT-TYPE
    SYNTAX      TruthValue
    MAX-ACCESS  read-write
    STATUS      current
    DESCRIPTION
        "
        true(1)  - Multicast-Filter enable on ONU.
        false(2) - Multicast-Filter disable on ONU.
        "
    DEFVAL { false }
    ::= { ibOnuSysManEntry 3 }

ibOnuDbaReportQueueSetNumber OBJECT-TYPE
    SYNTAX      Integer32
    MAX-ACCESS  read-write
    STATUS      current
    DESCRIPTION
        "
        The number of queue sets reported in MPCP report frames.
        "
    DEFVAL { 2 }
    ::= { ibOnuSysManEntry 4 }

ibOnuRemoteFecStatus OBJECT-TYPE
    SYNTAX      INTEGER
        {
            enable(1),
            disable(2)
        }
    MAX-ACCESS  read-write
    STATUS      current
    DESCRIPTION
        "
        Value that indicates status of the 1000BASE-PX PHY
        optional FEC Sublayer for forward error correction
        see [802.3ah] clause 65.2.
        enable - enable remote forward error correction.
        disable - disable remote forward error correction.
        "
    DEFVAL { disable }
    ::= { ibOnuSysManEntry 5 }

ibOnuPortBerStatus OBJECT-TYPE
    SYNTAX      INTEGER
        {
            enable(1),
            disable(2)
        }
    MAX-ACCESS  read-write
    STATUS      current
    DESCRIPTION
        "
        enable - enable ONU port bit error rate alarm.
        disable - disable ONU port bit error rate alarm.
        "
    DEFVAL { enable }
    ::= { ibOnuSysManEntry 6 }

ibOnuReset OBJECT-TYPE
    SYNTAX      INTEGER
        {
            reset(1)
        }
    MAX-ACCESS  read-write
    STATUS      current
    DESCRIPTION
        "
        Reboot ONU.
        "
    ::= { ibOnuSysManEntry 7 }

ibOnuMulticastControlMode OBJECT-TYPE
    SYNTAX      INTEGER
        {
            igmpsnooping(1),
            multicastcontrol(2)
        }
    MAX-ACCESS  read-write
    STATUS      current
    DESCRIPTION
        "
        igmpsnooping - the traditional IGMP snooping mode.
        multicastcontrol - the specific multicast control mode.
        "
    DEFVAL { igmpsnooping }
    ::= { ibOnuSysManEntry 8 }

ibOnuAccessVlan OBJECT-TYPE
    SYNTAX      Integer32
    MAX-ACCESS  read-write
    STATUS      current
    DESCRIPTION
        "
        The VLAN ID assigned to untagged frames received on ONU.
        "
    ::= { ibOnuSysManEntry 9 }

ibOnuEncryptKey OBJECT-TYPE
    SYNTAX      DisplayString(SIZE(0..255))
    MAX-ACCESS  read-write
    STATUS      current
    DESCRIPTION
        "
        The encryption key, used to encrypt all downstream
        traffic destined to and/or upstream traffic originating
        from a specific ONU.  It is a zero length, or MD5 hashed string,
        by default, the string is empty.
        "
    ::= { ibOnuSysManEntry 10 }

ibOnuUniUpDownTrapStatus OBJECT-TYPE
    SYNTAX      TruthValue
    MAX-ACCESS  read-write
    STATUS      current
    DESCRIPTION
        "
        true - A notification will be sent when UNI link status is change.
        false - Device will not sent notification when UNI link status is
        change.
        "
    DEFVAL { false }
    ::= { ibOnuSysManEntry 11 }

ibOnuFecStatus OBJECT-TYPE
    SYNTAX      INTEGER
        {
            enable(1),
            disable(2)
        }
    MAX-ACCESS  read-write
    STATUS      current
    DESCRIPTION
        "
        Value that indicates status of the 1000BASE-PX PHY
        optional FEC Sublayer for forward error correction
        (include remote onu and local OLT)
        see [802.3ah] clause 65.2
        enable - enable forward error correction.
        disable - disable forward error correction.
        "
    DEFVAL { disable }
    ::= { ibOnuSysManEntry 12 }

ibOnuMcastCtrlHostAgingTime OBJECT-TYPE
    SYNTAX      Integer32
    MAX-ACCESS  read-write
    STATUS      current
    DESCRIPTION
        "
        The host aging time of multicast control mode on ONU,
        ranging from 200 to 1000, measured in seconds.
        "
    ::= { ibOnuSysManEntry 13 }

ibOnuMulticastFastLeaveEnable OBJECT-TYPE
    SYNTAX     TruthValue
    MAX-ACCESS read-write
    STATUS     current
    DESCRIPTION
        "
        true(1)  - Enable multicast fast leave attribute on all ethernet UNIs of the ONU.
        false(2) - Disable multicast fast leave attribute on all ethernet UNIs of the ONU.
        "
    ::= { ibOnuSysManEntry 14 }

ibOnuPortIsolateEnable OBJECT-TYPE
    SYNTAX     TruthValue
    MAX-ACCESS read-write
    STATUS     current
    DESCRIPTION
        "
        true(1)  - Enable port isolate setting on all ethernet UNIs of the ONU.
        false(2) - Disable port isolate setting on all ethernet UNIs of the ONU.
        "
    ::= { ibOnuSysManEntry 15 }

ibOnuMacAddressTimer OBJECT-TYPE
    SYNTAX     Unsigned32
    MAX-ACCESS read-write
    STATUS     current
    DESCRIPTION
        "
        no-aging(0)  - Disable aging.
        others       - Aging time(seconds).
        "
    DEFVAL { 300 }
    ::= { ibOnuSysManEntry 16 }

--
-- ibOnuLinkTestTable
--

ibOnuLinkTestTable OBJECT-TYPE
    SYNTAX      SEQUENCE OF IbOnuLinkTestEntry
    MAX-ACCESS  not-accessible
    STATUS      current
    DESCRIPTION
        "
        LLID link test applying to the ONU only including delay
        measurement option.  The command tests a link to a single
        LLID over a period of time or once, using a variable
        number of measurement frames.  The length of the measurement
        frames is also parameterized.  The test uses a loopback
        mode of the ONU to return each measurement frame,
        loopback activation is done using randomly patterned
        OAM Protocol Data Unit(PDU) frames.
        "
    ::= { ibEponOnuMan 2 }

ibOnuLinkTestEntry OBJECT-TYPE
    SYNTAX      IbOnuLinkTestEntry
    MAX-ACCESS  not-accessible
    STATUS      current
    DESCRIPTION
        "
        The entry of ibOnuLinkTestEntry.
        "
    INDEX
        {
            ifIndex
        }
    ::= { ibOnuLinkTestTable 1 }

IbOnuLinkTestEntry ::= SEQUENCE
    {
        ibOnuLinkTestFrameNum                Integer32,
        ibOnuLinkTestFrameSize               Integer32,
        ibOnuLinkTestDelay                   TruthValue,
        ibOnuLinkTestVlanTag                 TruthValue,
        ibOnuLinkTestVlanPriority            Integer32,
        ibOnuLinkTestVlanTagID               Integer32,
        ibOnuLinkTestResultSentFrameNum      Integer32,
        ibOnuLinkTestResultRetFrameNum       Integer32,
        ibOnuLinkTestResultRetErrFrameNum    Integer32,
        ibOnuLinkTestResultMinDelay          Integer32,
        ibOnuLinkTestResultMeanDelay         Integer32,
        ibOnuLinkTestResultMaxDelay          Integer32
    }

ibOnuLinkTestFrameNum OBJECT-TYPE
    SYNTAX      Integer32
    MAX-ACCESS  read-write
    STATUS      current
    DESCRIPTION
        "
        Exact number of measurement frames.
        "
    DEFVAL { 20 }
    ::= { ibOnuLinkTestEntry 1 }

ibOnuLinkTestFrameSize OBJECT-TYPE
    SYNTAX      Integer32(60..1514)
    MAX-ACCESS  read-write
    STATUS      current
    DESCRIPTION
        "
        Measurement frames data size, measured in bytes.
        Not including Preamble, SFD, VLAN tag, and FCS.
        Frame size minimum value is 56 - if VLAN tag is
        enabled('VLAN enable' field is set to ENABLE),
        and 60 - if VLAN tag is disabled.  The actual
        measurement frames sent to the PON are always
        minimum 60 bytes long.  When VLAN tag is enabled,
        the actual measurement frames size including
        FCS may reach (1514+4+4=)1522 bytes.
        60(60 is VLAN tag disabled) - 1514 .
        "
    DEFVAL { 1000 }
    ::= { ibOnuLinkTestEntry 2 }

ibOnuLinkTestDelay OBJECT-TYPE
    SYNTAX      TruthValue
    MAX-ACCESS  read-write
    STATUS      current
    DESCRIPTION
        "
        true:Link test includes delay measurement,
        which corresponds to the difference between sent
        and received times(including granting delay and
        firmware processing time overheads).
        false:Link test not includes a delay measurement.
        "
    DEFVAL { true }
    ::= { ibOnuLinkTestEntry 3 }

ibOnuLinkTestVlanTag OBJECT-TYPE
    SYNTAX      TruthValue
    MAX-ACCESS  read-write
    STATUS      current
    DESCRIPTION
        "
        true:Enable VLAN tag in link test frames.
        false:Link test not includes frames with VLAN tag.
        "
    DEFVAL { true }
    ::= { ibOnuLinkTestEntry 4 }

ibOnuLinkTestVlanPriority OBJECT-TYPE
    SYNTAX      Integer32(0..7)
    MAX-ACCESS  read-write
    STATUS      current
    DESCRIPTION
        "
        VLAN priority: 0-7.
        "
    DEFVAL { 2 }
    ::= { ibOnuLinkTestEntry 5 }

ibOnuLinkTestVlanTagID OBJECT-TYPE
    SYNTAX      Integer32(1..4094)
    MAX-ACCESS  read-write
    STATUS      current
    DESCRIPTION
        "
        VLAN ID: 1-4094.
        "
    DEFVAL { 1 }
    ::= { ibOnuLinkTestEntry 6 }

ibOnuLinkTestResultSentFrameNum OBJECT-TYPE
    SYNTAX      Integer32
    MAX-ACCESS  read-only
    STATUS      current
    DESCRIPTION
        "
        The total number of frames sent during the link test process.
        "
    ::= { ibOnuLinkTestEntry 7 }

ibOnuLinkTestResultRetFrameNum OBJECT-TYPE
    SYNTAX      Integer32
    MAX-ACCESS  read-only
    STATUS      current
    DESCRIPTION
        "
        The total number of frames return back during the link test process.
        "
    ::= { ibOnuLinkTestEntry 8 }

ibOnuLinkTestResultRetErrFrameNum OBJECT-TYPE
    SYNTAX      Integer32
    MAX-ACCESS  read-only
    STATUS      current
    DESCRIPTION
        "
        The total number of error frames return back during the
        link test process.
        "
    ::= { ibOnuLinkTestEntry 9 }

ibOnuLinkTestResultMinDelay OBJECT-TYPE
    SYNTAX      Integer32
    MAX-ACCESS  read-only
    STATUS      current
    DESCRIPTION
        "
        The minimum delay time in TQ units, which corresponds
        to the difference between sent and received times
        (including granting delay and firmware processing time
        overheads).  It's invalid if the field
        'ibOnuLinkTestDelay' is set to be true.
        "
    ::= { ibOnuLinkTestEntry 10 }

ibOnuLinkTestResultMeanDelay OBJECT-TYPE
    SYNTAX      Integer32
    MAX-ACCESS  read-only
    STATUS      current
    DESCRIPTION
        "
        The average delay time in TQ units, which corresponds
        to the difference between sent and received times
        (including granting delay and firmware processing time
        overheads).  It's invalid if the field
        'ibOnuLinkTestDelay' is set to be true.
        "
    ::= { ibOnuLinkTestEntry 11 }

ibOnuLinkTestResultMaxDelay OBJECT-TYPE
    SYNTAX      Integer32
    MAX-ACCESS  read-only
    STATUS      current
    DESCRIPTION
        "
        The maximum delay time in TQ units, which corresponds
        to the difference between sent and received times
        (including granting delay and firmware processing time
        overheads).  It's invalid if the field
        'ibOnuLinkTestDelay' is set to be true.
        "
    ::= { ibOnuLinkTestEntry 12 }

--
-- ibOnuBandWidthTable
--

ibOnuBandWidthTable OBJECT-TYPE
    SYNTAX      SEQUENCE OF IbOnuBandWidthEntry
    MAX-ACCESS  not-accessible
    STATUS      current
    DESCRIPTION
        "
        Set bandwidth policy parameters(restrictions)for a LLID
        (only for the ONU).  Default policies are set to disable.
        Policy parameters will be erased upon LLID network disconnection.
        "
    ::= { ibEponOnuMan 3 }

ibOnuBandWidthEntry OBJECT-TYPE
    SYNTAX      IbOnuBandWidthEntry
    MAX-ACCESS  not-accessible
    STATUS      current
    DESCRIPTION
        "
        The entry of table ibOnuBandWidthTable.
        "
    INDEX
        {
            ifIndex
        }
    ::= { ibOnuBandWidthTable 1 }

IbOnuBandWidthEntry ::= SEQUENCE
    {
        ibOnuDownStreamBandWidthPolicy      TruthValue,
        ibOnuDownStreamMaxBandWidth         Integer32,
        ibOnuDownStreamMaxBurstSize         Integer32,
        ibOnuDownStreamHighPriorityFirst    TruthValue,
        ibOnuDownStreamShortFrameFirst      TruthValue,
        ibOnuP2PBandWidthPolicy             TruthValue,
        ibOnuP2PMaxBandWidth                Integer32,
        ibOnuP2PMaxBurstSize                Integer32,
        ibOnuP2PHighPriorityFirst           TruthValue,
        ibOnuP2PShortFrameFirst             TruthValue
    }

ibOnuDownStreamBandWidthPolicy OBJECT-TYPE
    SYNTAX      TruthValue
    MAX-ACCESS  read-write
    STATUS      current
    DESCRIPTION
        "
        true:Enable static bandwidth configuration policing.
        false:Disable static bandwidth configuration policing.
        "
    DEFVAL { false }
    ::= { ibOnuBandWidthEntry 1 }

ibOnuDownStreamMaxBandWidth OBJECT-TYPE
    SYNTAX      Integer32
    MAX-ACCESS  read-write
    STATUS      current
    DESCRIPTION
        "
        Maximum bandwidth allowed for the ONU,
        measured in Kbits/Sec.
        "
    DEFVAL { 1000000 }
    ::= { ibOnuBandWidthEntry 2 }

ibOnuDownStreamMaxBurstSize OBJECT-TYPE
    SYNTAX      Integer32(0..8388480)
    MAX-ACCESS  read-write
    STATUS      current
    DESCRIPTION
        "
        Maximal number of bytes in a burst.
        The value is truncated to the nearest
        smaller 128 bytes multiple value,
        measured in bytes.
        "
    DEFVAL { 8388480 }
    ::= { ibOnuBandWidthEntry 3 }

ibOnuDownStreamHighPriorityFirst OBJECT-TYPE
    SYNTAX      TruthValue
    MAX-ACCESS  read-write
    STATUS      current
    DESCRIPTION
        "
        true:Enable high priority frames preference.
        false:Disable high priority frames preference.
        "
    DEFVAL { false }
    ::= { ibOnuBandWidthEntry 4 }

ibOnuDownStreamShortFrameFirst OBJECT-TYPE
    SYNTAX      TruthValue
    MAX-ACCESS  read-write
    STATUS      current
    DESCRIPTION
        "
        true:Enable short frames preference.
        false:Disable short frames preference.
        "
    DEFVAL { false }
    ::= { ibOnuBandWidthEntry 5 }

ibOnuP2PBandWidthPolicy OBJECT-TYPE
    SYNTAX      TruthValue
    MAX-ACCESS  read-write
    STATUS      current
    DESCRIPTION
        "
        true:Enable static bandwidth configuration policing.
        false:Disable static bandwidth configuration policing.
        "
    DEFVAL { false }
    ::= { ibOnuBandWidthEntry 6 }

ibOnuP2PMaxBandWidth OBJECT-TYPE
    SYNTAX      Integer32(0..1000000)
    MAX-ACCESS  read-write
    STATUS      current
    DESCRIPTION
        "
        Maximum bandwidth allowed for the ONU,
        measured in Kbits/Sec.
        "
    DEFVAL { 1000000 }
    ::= { ibOnuBandWidthEntry 7 }

ibOnuP2PMaxBurstSize OBJECT-TYPE
    SYNTAX      Integer32(0..8388480)
    MAX-ACCESS  read-write
    STATUS      current
    DESCRIPTION
        "
        Maximal number of bytes in a burst.
        The value is truncated to the nearest
        smaller 128 bytes multiple value,
        measured in bytes.
        "
    DEFVAL { 8388480 }
    ::= { ibOnuBandWidthEntry 8 }

ibOnuP2PHighPriorityFirst OBJECT-TYPE
    SYNTAX      TruthValue
    MAX-ACCESS  read-write
    STATUS      current
    DESCRIPTION
        "
        true:Enable high priority frames preference.
        false:Disable high priority frames preference.
        "
    DEFVAL { false }
    ::= { ibOnuBandWidthEntry 9 }

ibOnuP2PShortFrameFirst OBJECT-TYPE
    SYNTAX      TruthValue
    MAX-ACCESS  read-write
    STATUS      current
    DESCRIPTION
        "
        true:Enable short frames preference.
        false:Disable short frames preference.
        "
    DEFVAL { false }
    ::= { ibOnuBandWidthEntry 10 }

--
-- ibOnuSlaManTable
--

ibOnuSlaManTable OBJECT-TYPE
    SYNTAX      SEQUENCE OF IbOnuSlaManEntry
    MAX-ACCESS  not-accessible
    STATUS      current
    DESCRIPTION
        "
        Two types of DBA algorithm are supported in the ONU.
        The internal SLA based algorithm is always activated.
        This table defines the primary parameter about the
        internal SLA algorithm.
        "
    ::= { ibEponOnuMan 4 }

ibOnuSlaManEntry OBJECT-TYPE
    SYNTAX      IbOnuSlaManEntry
    MAX-ACCESS  not-accessible
    STATUS      current
    DESCRIPTION
        "
        The entry of table ibOnuSlaManTable.
        "
    INDEX
        {
            ifIndex
        }
    ::= { ibOnuSlaManTable 1 }

IbOnuSlaManEntry ::= SEQUENCE
    {
        ibOnuSlaMaxBandWidth        Integer32,
        ibOnuSlaMinBandWidth        Integer32,
        ibOnuSlaBandWidthStepVal    Integer32,
        ibOnuSlaDelay               INTEGER,
        ibOnuSlaFixedBandWidth      Integer32,
        ibOnuSlaPriorityClass       Integer32,
        ibOnuSlaFixedPacketSize     Integer32,
        ibOnuSlaWrrBandWidth        Integer32
    }

ibOnuSlaMaxBandWidth OBJECT-TYPE
    SYNTAX      Integer32
    MAX-ACCESS  read-write
    STATUS      current
    DESCRIPTION
        "
        Maximum bandwidth - measured in Kbit/s.
        The value of this object should be the multiple of
        the value of ibOnuSlaBandWidthStepVal.
        The minimum bandwidth should not be larger than the maximum
        bandwidth.
        "
    ::= { ibOnuSlaManEntry 1 }

ibOnuSlaMinBandWidth OBJECT-TYPE
    SYNTAX      Integer32
    MAX-ACCESS  read-write
    STATUS      current
    DESCRIPTION
        "
        Minimum bandwidth - measured in Kbit/s.
        The value of this object should be the multiple of
        the value of ibOnuSlaBandWidthStepVal.
        The maximum bandwidth should be larger than the minimum bandwidth.
        "
    ::= { ibOnuSlaManEntry 2 }

ibOnuSlaBandWidthStepVal OBJECT-TYPE
    SYNTAX      Integer32
    MAX-ACCESS  read-only
    STATUS      current
    DESCRIPTION
        "
        Granularity of bandwidth - measured in Kbit/s.
        The value of ibOnuSlaMaxBandWidth and ibOnuSlaMinBandWidth should
        be the multiple of the value of this object.
        "
    ::= { ibOnuSlaManEntry 3 }

ibOnuSlaDelay OBJECT-TYPE
    SYNTAX      INTEGER
        {
            low(1),
            high(2)
        }
    MAX-ACCESS  read-write
    STATUS      current
    DESCRIPTION
        "
        low  - low delay.
        high - high delay.
        The delay constraint of a specific ONU.  Set to high may improve the
        bandwidth usage at the cost of delay.
        "
    DEFVAL { low }
    ::= { ibOnuSlaManEntry 4 }

ibOnuSlaFixedBandWidth OBJECT-TYPE
    SYNTAX      Integer32
    MAX-ACCESS  read-write
    STATUS      current
    DESCRIPTION
        "
        Fixed bandwidth - measured in Kbit/s.
        The value of this object should be the multiple of
        the value of ibOnuSlaBandWidthStepVal.
        "
    ::= { ibOnuSlaManEntry 5 }

ibOnuSlaPriorityClass OBJECT-TYPE
    SYNTAX      Integer32
    MAX-ACCESS  read-write
    STATUS      current
    DESCRIPTION
        "
        Precedence of this flow over others in case of contention.
        0 is the lowest priority and 7 is the highest priority.
        "
    DEFVAL { 0 }
    ::= { ibOnuSlaManEntry 6 }

ibOnuSlaFixedPacketSize OBJECT-TYPE
    SYNTAX      Integer32
    MAX-ACCESS  read-write
    STATUS      current
    DESCRIPTION
        "
        Fixed packet size - measured in byte.
        The value of this object should be valid when ibOnuSlaFixedBandWidth is configured.
        "
    ::= { ibOnuSlaManEntry 7 }

ibOnuSlaWrrBandWidth OBJECT-TYPE
    SYNTAX      Integer32
    MAX-ACCESS  read-write
    STATUS      current
    DESCRIPTION
        "
        The WRR weight will be used to compute the remaining bandwidth
        allocation after each CIR has been guaranteed.
        "
    DEFVAL { 1 }
    ::= { ibOnuSlaManEntry 8 }
--
-- ibOnuInfoTable
--

ibOnuInfoTable OBJECT-TYPE
    SYNTAX      SEQUENCE OF IbOnuInfoEntry
    MAX-ACCESS  not-accessible
    STATUS      current
    DESCRIPTION
        "
        Primary status of the specified ONU.
        There will be one row in this table for each
        information in the system.
        (1)Software and hardware versions of the specified ONU
        (ibOnuHardMajorVersion, ibOnuHardMinorVersion,
        ibOnuUniMacType)
        (2)Several physical capabilities of the ONU.
        (ibOnuLaserOnTime, ibOnuLaserOffTime,
        ibOnuGrantFifoDep.)
        (3)The operation(activation) status of the ONU.
        (ibOnuWorkMode)
        "
    ::= { ibEponOnuMan 5 }

ibOnuInfoEntry OBJECT-TYPE
    SYNTAX      IbOnuInfoEntry
    MAX-ACCESS  not-accessible
    STATUS      current
    DESCRIPTION
        "
        The entry of the ibOnuInfoTable.
        "
    INDEX
        {
            ifIndex
        }
    ::= { ibOnuInfoTable 1 }

IbOnuInfoEntry ::= SEQUENCE
    {
        ibOnuHardMajorVersion    OCTET STRING,
        ibOnuHardMinorVersion    OCTET STRING,
        ibOnuSoftwareVersion     OCTET STRING,
        ibOnuUniMacType          INTEGER,
        ibOnuLaserOnTime         Integer32,
        ibOnuLaserOffTime        Integer32,
        ibOnuGrantFifoDep        Integer32,
        ibOnuWorkMode            INTEGER,
        ibOnuPCBVersion          OCTET STRING,
        ibOnuRtt                 Unsigned32,
        ibOnuEEPROMVersion       OCTET STRING,
        ibOnuRegType             OCTET STRING,
        ibOnuHostType            OCTET STRING,
        ibOnuDistance            Integer32,
        ibOnuLlid                Integer32,
        ibOnuVendorId            OCTET STRING,
        ibOnuFirmwareVersion     OCTET STRING,
        ibOnuOpticalPowerReceivedByOlt  Integer32,
        ibOnuInfoMac             MacAddress,
        ibOnuInfoLoid            OCTET STRING
    }

ibOnuHardMajorVersion OBJECT-TYPE
    SYNTAX      OCTET STRING
    MAX-ACCESS  read-only
    STATUS      current
    DESCRIPTION
        "
        ONU hardware major version.  If the object length is
        zero, it means the version is unknown.
        "
    ::= { ibOnuInfoEntry 1 }

ibOnuHardMinorVersion OBJECT-TYPE
    SYNTAX      OCTET STRING
    MAX-ACCESS  read-only
    STATUS      current
    DESCRIPTION
        "
        ONU hardware minor version.  If the object length is
        zero, it means the version is unknown.
        "
    ::= { ibOnuInfoEntry 2 }

ibOnuSoftwareVersion OBJECT-TYPE
    SYNTAX      OCTET STRING
    MAX-ACCESS  read-only
    STATUS      current
    DESCRIPTION
        "
        ONU software version.
        "
    ::= { ibOnuInfoEntry 3 }

ibOnuUniMacType OBJECT-TYPE
    SYNTAX      INTEGER
        {
            other(1),
            mii(2),
            gmii(3),
            tbi(4)
        }
    MAX-ACCESS  read-only
    STATUS      current
    DESCRIPTION
        "
        ONU User Network Interface(UNI) port MAC type.
        "
    ::= { ibOnuInfoEntry 4 }

ibOnuLaserOnTime OBJECT-TYPE
    SYNTAX      Integer32
    MAX-ACCESS  read-only
    STATUS      current
    DESCRIPTION
        "
        The ONU laser on time measured in TQ units.  If the object value is
        0x7FFFFFFF, it means ibOnuLaserOnTime is unknown.
        "
    ::= { ibOnuInfoEntry 5 }

ibOnuLaserOffTime OBJECT-TYPE
    SYNTAX      Integer32
    MAX-ACCESS  read-only
    STATUS      current
    DESCRIPTION
        "
        The ONU laser off time measured in TQ units.  If the object value is
        0x7FFFFFFF, it means ibOnuLaserOffTime is unknown.
        "
    ::= { ibOnuInfoEntry 6 }

ibOnuGrantFifoDep OBJECT-TYPE
    SYNTAX      Integer32(1..255|2147483647)
    MAX-ACCESS  read-only
    STATUS      current
    DESCRIPTION
        "
        Maximal number of grant records an ONU can store,
        relevant to ONU only.
        range: 1 - 255.
        0x7FFFFFFF: unknown value.
        "
    ::= { ibOnuInfoEntry 7 }

ibOnuWorkMode OBJECT-TYPE
    SYNTAX      INTEGER
        {
            other(1),
            on(2),
            pending(3),
            off(4)
        }
    MAX-ACCESS  read-only
    STATUS      current
    DESCRIPTION
        "
        The operation(activation) mode of an ONU.
        other(1)   - ONU is in another mode.
        on(2)      - ONU is registered and authorized to the
        network.  In this mode it works
        as a media converter.
        pending(3) - ONU has been registered to the PON, but
        not authorized to the network.
        off(4)     - ONU is not registered to the network.
        "
    ::= { ibOnuInfoEntry 8 }

ibOnuPCBVersion OBJECT-TYPE
    SYNTAX      OCTET STRING
    MAX-ACCESS  read-only
    STATUS      current
    DESCRIPTION
        "
        ONU PCB version.
        "
    ::= { ibOnuInfoEntry 9 }

ibOnuRtt OBJECT-TYPE
    SYNTAX      Unsigned32
    MAX-ACCESS  read-only
    STATUS      current
    DESCRIPTION
        "
        The signal round-trip-time(RTT) received.
        "
    ::= { ibOnuInfoEntry 10 }

ibOnuEEPROMVersion OBJECT-TYPE
    SYNTAX      OCTET STRING
    MAX-ACCESS  read-only
    STATUS      current
    DESCRIPTION
        "
        ONU EEPROM version.
        "
    ::= { ibOnuInfoEntry 11 }

ibOnuRegType OBJECT-TYPE
    SYNTAX      OCTET STRING
    MAX-ACCESS  read-only
    STATUS      current
    DESCRIPTION
        "
        ONU registered type.
        "
    ::= { ibOnuInfoEntry 12 }

ibOnuHostType OBJECT-TYPE
    SYNTAX      OCTET STRING
    MAX-ACCESS  read-only
    STATUS      current
    DESCRIPTION
        "
        ONU host type.
        "
    ::= { ibOnuInfoEntry 13 }

ibOnuDistance OBJECT-TYPE
    SYNTAX      Integer32
    MAX-ACCESS  read-only
    STATUS      current
    DESCRIPTION
        "
        The distance between OLT and ONU, measured in meter.
        "
    ::= { ibOnuInfoEntry 14 }

ibOnuLlid OBJECT-TYPE
    SYNTAX      Integer32
    MAX-ACCESS  read-only
    STATUS      current
    DESCRIPTION
        "
        The link layer identifier, which uniquely identifies the ONU
        of a specific OLT.
        "
    ::= { ibOnuInfoEntry 15 }

ibOnuVendorId OBJECT-TYPE
    SYNTAX      OCTET STRING
    MAX-ACCESS  read-only
    STATUS      current
    DESCRIPTION
        "
        ONU vendor ID.
        "
    ::= { ibOnuInfoEntry 16 }

ibOnuFirmwareVersion OBJECT-TYPE
    SYNTAX      OCTET STRING
    MAX-ACCESS  read-only
    STATUS      current
    DESCRIPTION
        "
        ONU firmware version.
        "
    ::= { ibOnuInfoEntry 17 }

ibOnuOpticalPowerReceivedByOlt OBJECT-TYPE
    SYNTAX     Integer32
    MAX-ACCESS read-only
    STATUS     current
    DESCRIPTION
        "
        The burst ONU optical power received by OLT,
        and when the ONU status is up the value is usable.
        It measured in 0.01 dBm unit.
        "
    ::= { ibOnuInfoEntry 18 }

ibOnuInfoMac OBJECT-TYPE
    SYNTAX     MacAddress
    MAX-ACCESS read-only
    STATUS     current
    DESCRIPTION
        "
        ONU's MAC.
        "
    ::= { ibOnuInfoEntry 19 }

ibOnuInfoLoid OBJECT-TYPE
    SYNTAX     OCTET STRING(SIZE(0..24))
    MAX-ACCESS read-only
    STATUS     current
    DESCRIPTION
        "
        ONU's LOID.
        "
    ::= { ibOnuInfoEntry 20 }

--
-- ibOnuMacAddrInfoTable
--

ibOnuMacAddrInfoTable OBJECT-TYPE
    SYNTAX      SEQUENCE OF IbOnuMacAddrInfoEntry
    MAX-ACCESS  not-accessible
    STATUS      current
    DESCRIPTION
        "
        This table used for getting MAC address information of ONU.
        "
    ::= { ibEponOnuMan 6 }

ibOnuMacAddrInfoEntry OBJECT-TYPE
    SYNTAX      IbOnuMacAddrInfoEntry
    MAX-ACCESS  not-accessible
    STATUS      current
    DESCRIPTION
        "
        The entry of the ibEponOnuMacAddrInfoTable.
        "
    INDEX
        {
            ifIndex,
            ibOnuMacIndex
        }
    ::= { ibOnuMacAddrInfoTable 1 }

IbOnuMacAddrInfoEntry ::= SEQUENCE
    {
        ibOnuMacIndex       Integer32,
        ibOnuMacAddrFlag    INTEGER,
        ibOnuMacAddress     MacAddress
    }

ibOnuMacIndex OBJECT-TYPE
    SYNTAX      Integer32
    MAX-ACCESS  not-accessible
    STATUS      current
    DESCRIPTION
        "
        The index of ONUs in one OLT.
        "
    ::= { ibOnuMacAddrInfoEntry 1 }

ibOnuMacAddrFlag OBJECT-TYPE
    SYNTAX      INTEGER
        {
            bound(1),
            registered(2),
            run(3),
            regIncorrect(4)
        }
    MAX-ACCESS  read-only
    STATUS      current
    DESCRIPTION
        "
        The flag of ONU status.
        1 - bound: The ONU is bound but not registered.
        2 - registered: The ONU is registered but not bound.
        3 - run: The ONU is registered and bound on one OLT.
        4 - regIncorrect: The ONU is bound on one OLT and registered on
        another OLT.
        "
    ::= { ibOnuMacAddrInfoEntry 2 }

ibOnuMacAddress OBJECT-TYPE
    SYNTAX      MacAddress
    MAX-ACCESS  read-only
    STATUS      current
    DESCRIPTION
        "
        The MAC address of ONU.
        "
    ::= { ibOnuMacAddrInfoEntry 3 }

--
-- ibOnuBindMacAddrTable
--

ibOnuBindMacAddrTable OBJECT-TYPE
    SYNTAX      SEQUENCE OF IbOnuBindMacAddrEntry
    MAX-ACCESS  not-accessible
    STATUS      current
    DESCRIPTION
        "
        This table implements the following functions for ONUs:
        Bind MAC of ONU.
        "
    ::= { ibEponOnuMan 7 }

ibOnuBindMacAddrEntry OBJECT-TYPE
    SYNTAX      IbOnuBindMacAddrEntry
    MAX-ACCESS  not-accessible
    STATUS      current
    DESCRIPTION
        "
        The entry of the table ibOnuBindMacAddrTable.
        "
    INDEX
        {
            ifIndex
        }
    ::= { ibOnuBindMacAddrTable 1 }

IbOnuBindMacAddrEntry ::= SEQUENCE
    {
        ibOnuBindMacAddress    MacAddress,
        ibOnuBindType          Integer32,
        ibOnuBindLoid          OCTET STRING,
        ibOnuBindPassword      OCTET STRING
    }

ibOnuBindMacAddress OBJECT-TYPE
    SYNTAX      MacAddress
    MAX-ACCESS  read-write
    STATUS      current
    DESCRIPTION
        "
        Bind the MAC of ONU.
        While the MAC is not bound, the ONU can not go into
        effect and configurations can not be set.
        Set 0-0-0 (MAC address) to the EPON device port will
        unbind the relationship with the original MAC and
        configurations will be set to default values.
        "
    ::= { ibOnuBindMacAddrEntry 1 }

ibOnuBindType OBJECT-TYPE
    SYNTAX      Integer32
    MAX-ACCESS  read-write
    STATUS      current
    DESCRIPTION
        "
        Set the binding type with the ONU which is confined
        to the index of ibEponOnuTypeDescr.
        "
    ::= { ibOnuBindMacAddrEntry 2 }

ibOnuBindLoid OBJECT-TYPE
    SYNTAX      OCTET STRING(SIZE(0..24))
    MAX-ACCESS  read-write
    STATUS      current
    DESCRIPTION
        "
        Bind the LOID of ONU.
        While the LOID is not bound, the ONU can not go into
        effect and configurations can not be set.
        "
    ::= { ibOnuBindMacAddrEntry 3 }

ibOnuBindPassword OBJECT-TYPE
    SYNTAX      OCTET STRING(SIZE(0..12))
    MAX-ACCESS  read-write
    STATUS      current
    DESCRIPTION
        "
        The password of LOID by using LOID-PASSWORD binding type to bind ONU.
        A zero-length string will be returned when reading.
        "
    ::= { ibOnuBindMacAddrEntry 4 }

--
-- ibOnuFirmwareUpdateTable
--

ibOnuFirmwareUpdateTable OBJECT-TYPE
    SYNTAX      SEQUENCE OF IbOnuFirmwareUpdateEntry
    MAX-ACCESS  not-accessible
    STATUS      current
    DESCRIPTION
        "
        This table implements the following functions for ONUs:
        1. Update the ONU firmware.
        2. Result of update ONU firmware.
        "
    ::= { ibEponOnuMan 8 }

ibOnuFirmwareUpdateEntry OBJECT-TYPE
    SYNTAX      IbOnuFirmwareUpdateEntry
    MAX-ACCESS  not-accessible
    STATUS      current
    DESCRIPTION
        "
        The entry of the table ibOnuFirmwareUpdateTable.
        "
    INDEX
        {
            ifIndex
        }
    ::= { ibOnuFirmwareUpdateTable 1 }

IbOnuFirmwareUpdateEntry ::= SEQUENCE
    {
        ibOnuUpdate            INTEGER,
        ibOnuUpdateResult      INTEGER,
        ibOnuUpdateFileName    OCTET STRING,
        ibOnuUpdateProtType    INTEGER,
        ibOnuUpdateStartTime   OCTET STRING,
        ibOnuUpdateDuration    Integer32
    }

ibOnuUpdate OBJECT-TYPE
    SYNTAX      INTEGER
        {
            update(1)
        }
    MAX-ACCESS  read-write
    STATUS      current
    DESCRIPTION
        "
        update(1): Update the ONU firmware.
        Config the MIB object module ibEponOnuUpdateFileName
        with the filename of ONU firmware first.
        "
    ::= { ibOnuFirmwareUpdateEntry 1 }

ibOnuUpdateResult OBJECT-TYPE
    SYNTAX      INTEGER
        {
            updating(1),
            ok(2),
            fail(3),
            fileNotExist(4),
            notSetFilename(5),
            fileNotMatchONU(6),
            timeout(7),
            otherError(8)
        }
    MAX-ACCESS  read-only
    STATUS      current
    DESCRIPTION
        "
        The ONU firmware update result.
        updating  - The ONU is updating firmware right now.
        ok     - The ONU update result is OK.
        fail   - The ONU update result is fail.
        fileNotExist - The ONU update failed because the file does not exist.
        notSetFilename - The ONU firmware filename is not set.
        fileNotMatchONU - The ONU firmware does not match the ONU.
        timeout - The ONU responses timeout.
        otherError - The ONU update result is unknown.
        "
    ::= { ibOnuFirmwareUpdateEntry 2 }

ibOnuUpdateFileName OBJECT-TYPE
    SYNTAX      OCTET STRING(SIZE(0..255))
    MAX-ACCESS  read-write
    STATUS      current
    DESCRIPTION
        "
        The filename of the ONU firmware to be updated.
        Note that the filename must contain the file path.
        "
    ::= { ibOnuFirmwareUpdateEntry 3 }

ibOnuUpdateProtType OBJECT-TYPE
    SYNTAX      INTEGER
        {
            private(0),
            ctc(1)
        }
    MAX-ACCESS  read-write
    STATUS      current
    DESCRIPTION
        "
        private(0): Using private protocol to update the ONU firmware.
        ctc(1): Using ctc standard protocol to update the ONU firmware.
        "
    DEFVAL { private }
    ::= { ibOnuFirmwareUpdateEntry 4 }

ibOnuUpdateStartTime OBJECT-TYPE
    SYNTAX      OCTET STRING(SIZE(0..5))
    MAX-ACCESS  read-write
    STATUS      current
    DESCRIPTION
        "
        The start time of the ONU update every day.
        Using HH:MM as format.
        "
    ::= { ibOnuFirmwareUpdateEntry 5 }

ibOnuUpdateDuration OBJECT-TYPE
    SYNTAX      Integer32(0..1439)
    MAX-ACCESS  read-write
    STATUS      current
    DESCRIPTION
        "
        The duration of the ONU update.
        "
    DEFVAL { 0 }
    ::= { ibOnuFirmwareUpdateEntry 6 }

ibOnuLinkTestFrameNumMinVal OBJECT-TYPE
    SYNTAX      Integer32
    MAX-ACCESS  read-only
    STATUS      current
    DESCRIPTION
        "The lower limit of measurement frames which is confined to
        ibOnuLinkTestFrameNum."
    ::= { ibEponOnuMan 9 }

ibOnuLinkTestFrameNumMaxVal OBJECT-TYPE
    SYNTAX      Integer32
    MAX-ACCESS  read-only
    STATUS      current
    DESCRIPTION
        "The upper limit of measurement frames which is confined to
        ibOnuLinkTestFrameNum."
    ::= { ibEponOnuMan 10 }

ibOnuSlaMaxBandWidthMinVal OBJECT-TYPE
    SYNTAX      Integer32
    MAX-ACCESS  read-only
    STATUS      current
    DESCRIPTION
        "
        The lower limit of maximum-bandwidth which is confined to
        ibOnuSlaMaxBandWidth."
    ::= { ibEponOnuMan 11 }

ibOnuSlaMaxBandWidthMaxVal OBJECT-TYPE
    SYNTAX      Integer32
    MAX-ACCESS  read-only
    STATUS      current
    DESCRIPTION
        "
        The upper limit of maximum-bandwidth which is confined to
        ibOnuSlaMaxBandWidth."
    ::= { ibEponOnuMan 12 }

ibOnuSlaMinBandWidthMinVal OBJECT-TYPE
    SYNTAX      Integer32
    MAX-ACCESS  read-only
    STATUS      current
    DESCRIPTION
        "
        The lower limit of minimum-bandwidth which is confined to
        ibOnuSlaMinBandWidth."
    ::= { ibEponOnuMan 13 }

ibOnuSlaMinBandWidthMaxVal OBJECT-TYPE
    SYNTAX      Integer32
    MAX-ACCESS  read-only
    STATUS      current
    DESCRIPTION
        "
        The upper limit of minimum-bandwidth which is confined to
        ibOnuSlaMinBandWidth."
    ::= { ibEponOnuMan 14 }

--
-- ibEponOnuTypeManTable
--

ibEponOnuTypeManTable OBJECT-TYPE
    SYNTAX      SEQUENCE OF IbEponOnuTypeManEntry
    MAX-ACCESS  not-accessible
    STATUS      current
    DESCRIPTION
        "
        This table is used for getting ONU bind type in current version.
        "
    ::= { ibEponOnuMan 15 }

ibEponOnuTypeManEntry OBJECT-TYPE
    SYNTAX      IbEponOnuTypeManEntry
    MAX-ACCESS  not-accessible
    STATUS      current
    DESCRIPTION
        "
        The entry of the ibEponOnuTypeManTable.
        "
    INDEX
        {
            ibEponOnuTypeIndex
        }
    ::= { ibEponOnuTypeManTable 1 }

IbEponOnuTypeManEntry ::= SEQUENCE
    {
        ibEponOnuTypeIndex    Integer32,
        ibEponOnuTypeDescr    OCTET STRING
    }

ibEponOnuTypeIndex OBJECT-TYPE
    SYNTAX      Integer32
    MAX-ACCESS  not-accessible
    STATUS      current
    DESCRIPTION
        "
        The ONU type index.
        "
    ::= { ibEponOnuTypeManEntry 1 }

ibEponOnuTypeDescr OBJECT-TYPE
    SYNTAX      OCTET STRING
    MAX-ACCESS  read-only
    STATUS      current
    DESCRIPTION
        "
        The ONU type description which can be used to bind ONU in current
        version.
        the value of ibOnuBindType can be configured by the index of
        ibEponOnuTypeDescr.
        "
    ::= { ibEponOnuTypeManEntry 2 }

ibOnuPacketManTable OBJECT-TYPE
    SYNTAX      SEQUENCE OF IbOnuPacketManEntry
    MAX-ACCESS  not-accessible
    STATUS      current
    DESCRIPTION
        "
        This table implements the following functions:
        (1)Manage packet priority trust mode.
        (2)Manage packet queue-scheduler mode.
        "
    ::= { ibEponOnuMan 16 }

ibOnuPacketManEntry OBJECT-TYPE
    SYNTAX      IbOnuPacketManEntry
    MAX-ACCESS  not-accessible
    STATUS      current
    DESCRIPTION
        "
        The entry of the ibOnuPacketManTable.
        "
    INDEX
        {
            ifIndex
        }
    ::= { ibOnuPacketManTable 1 }

IbOnuPacketManEntry ::= SEQUENCE
    {
        ibOnuPriorityTrust     INTEGER,
        ibOnuQueueScheduler    INTEGER
    }

ibOnuPriorityTrust OBJECT-TYPE
    SYNTAX      INTEGER
        {
            dscp(1),
            ipprecedence(2),
            cos(3)
        }
    MAX-ACCESS  read-write
    STATUS      current
    DESCRIPTION
        "
        The QOS mode which is assigned on ONU.
        dscp - The service dscp of politic Priority.
        ipprecedence - The service IP precedence of politic Priority.
        cos - The service cos of politic Priority.
        "
    DEFVAL { cos }
    ::= { ibOnuPacketManEntry 1 }

ibOnuQueueScheduler OBJECT-TYPE
    SYNTAX      INTEGER
        {
            spq(1),
            wfq(2)
        }
    MAX-ACCESS  read-write
    STATUS      current
    DESCRIPTION
        "
        The packet queue-scheduler mode which is assigned on ONU.
        spq - strict priority queuing.
        wfq - specifies the weights for weighted round-robin queuing.
        "
    DEFVAL { spq }
    ::= { ibOnuPacketManEntry 2 }

ibOnuProtocolTable OBJECT-TYPE
    SYNTAX      SEQUENCE OF IbOnuProtocolEntry
    MAX-ACCESS  not-accessible
    STATUS      current
    DESCRIPTION
        "
        This table implements the following functions:
        (1)Manage STP status.
        (2)Manage IGMP-snooping.
        (3)Manage DHCP-snooping.
        "
    ::= { ibEponOnuMan 17 }

ibOnuProtocolEntry OBJECT-TYPE
    SYNTAX      IbOnuProtocolEntry
    MAX-ACCESS  not-accessible
    STATUS      current
    DESCRIPTION
        "
        The entry of ibOnuProtocolTable.
        "
    INDEX
        {
            ifIndex
        }
    ::= { ibOnuProtocolTable 1 }

IbOnuProtocolEntry ::= SEQUENCE
    {
        ibOnuStpStatus                   TruthValue,
        ibOnuIgmpSnoopingStatus          TruthValue,
        ibOnuDhcpsnoopingOption82        TruthValue,
        ibOnuDhcpsnooping                TruthValue,
        ibOnuPppoe                       TruthValue,
        ibOnuIgmpSnoopingHostAgingT      Integer32,
        ibOnuIgmpSnoopingMaxRespT        Integer32,
        ibOnuIgmpSnoopingRouterAgingT    Integer32,
        ibOnuIgmpSnoopingAggReportS      TruthValue,
        ibOnuIgmpSnoopingAggLeaveS       TruthValue
    }

ibOnuStpStatus OBJECT-TYPE
    SYNTAX      TruthValue
    MAX-ACCESS  read-write
    STATUS      current
    DESCRIPTION
        "
        true(1)  - STP status enable on ONU.
        false(2) - STP status disable on ONU.
        "
    DEFVAL { true }
    ::= { ibOnuProtocolEntry 1 }

ibOnuIgmpSnoopingStatus OBJECT-TYPE
    SYNTAX      TruthValue
    MAX-ACCESS  read-write
    STATUS      current
    DESCRIPTION
        "
        true(1)  - IGMP snooping status enable on ONU.
        false(2) - IGMP snooping status disable on ONU.
        "
    DEFVAL { true }
    ::= { ibOnuProtocolEntry 2 }

ibOnuDhcpsnoopingOption82 OBJECT-TYPE
    SYNTAX      TruthValue
    MAX-ACCESS  read-write
    STATUS      current
    DESCRIPTION
        "
        true(1)  - DHCP snooping Option 82 status enable on ONU.
        false(2) - DHCP snooping Option 82 status disable on ONU.
        "
    DEFVAL { false }
    ::= { ibOnuProtocolEntry 3 }

ibOnuDhcpsnooping OBJECT-TYPE
    SYNTAX      TruthValue
    MAX-ACCESS  read-write
    STATUS      current
    DESCRIPTION
        "
        true(1)  - DHCP snooping status enable on ONU.
        false(2) - DHCP snooping status disable on ONU.
        "
    DEFVAL { false }
    ::= { ibOnuProtocolEntry 4 }

ibOnuPppoe OBJECT-TYPE
    SYNTAX      TruthValue
    MAX-ACCESS  read-write
    STATUS      current
    DESCRIPTION
        "
        true(1)  - PPPOE status enable on ONU.
        false(2) - PPPOE status disable on ONU.
        "
    DEFVAL { false }
    ::= { ibOnuProtocolEntry 5 }

ibOnuIgmpSnoopingHostAgingT OBJECT-TYPE
    SYNTAX      Integer32
    MAX-ACCESS  read-write
    STATUS      current
    DESCRIPTION
        "
        Set the host aging time of IGMP on ONU.
        "
    ::= { ibOnuProtocolEntry 6 }

ibOnuIgmpSnoopingMaxRespT OBJECT-TYPE
    SYNTAX      Integer32
    MAX-ACCESS  read-write
    STATUS      current
    DESCRIPTION
        "
        Set the max response time of IGMP on ONU.
        "
    ::= { ibOnuProtocolEntry 7 }

ibOnuIgmpSnoopingRouterAgingT OBJECT-TYPE
    SYNTAX      Integer32
    MAX-ACCESS  read-write
    STATUS      current
    DESCRIPTION
        "
        Set the router aging time of IGMP on ONU.
        "
    ::= { ibOnuProtocolEntry 8 }

ibOnuIgmpSnoopingAggReportS OBJECT-TYPE
    SYNTAX      TruthValue
    MAX-ACCESS  read-write
    STATUS      current
    DESCRIPTION
        "
        true(1)  - Igmp snooping aggregation report status enable on ONU.
        false(2) - Igmp snooping aggregation report status disable on ONU.
        "
    DEFVAL { false }
    ::= { ibOnuProtocolEntry 9 }

ibOnuIgmpSnoopingAggLeaveS OBJECT-TYPE
    SYNTAX      TruthValue
    MAX-ACCESS  read-write
    STATUS      current
    DESCRIPTION
        "
        true(1)  - Igmp snooping aggregation leave status enable on ONU.
        false(2) - Igmp snooping aggregation leave status disable on ONU.
        "
    DEFVAL { true }
    ::= { ibOnuProtocolEntry 10 }

ibOnuDot1xTable OBJECT-TYPE
    SYNTAX      SEQUENCE OF IbOnuDot1xEntry
    MAX-ACCESS  not-accessible
    STATUS      current
    DESCRIPTION
        "
        This table implements the following functions:
        (1)Manage 802.1x account.
        (2)Manage 802.1x password.
        ONU will be authorized to send and receive frames when the
        account and the password are all right, otherwise this ONU
        will be unavailable.
        "
    ::= { ibEponOnuMan 18 }

ibOnuDot1xEntry OBJECT-TYPE
    SYNTAX      IbOnuDot1xEntry
    MAX-ACCESS  not-accessible
    STATUS      current
    DESCRIPTION
        "
        The entry of the ibOnuDot1xTable.
        "
    INDEX
        {
            ifIndex
        }
    ::= { ibOnuDot1xTable 1 }

IbOnuDot1xEntry ::= SEQUENCE
    {
        ibOnuDot1xAccount     OCTET STRING,
        ibOnuDot1xPassword    OCTET STRING
    }

ibOnuDot1xAccount OBJECT-TYPE
    SYNTAX      OCTET STRING
    MAX-ACCESS  read-write
    STATUS      current
    DESCRIPTION
        "
        ONU 802.1X account.
        The object value cannot be set as 'a', 'al' or 'all'.
        The object should be set together with ibOnuDot1xPassword.
        "
    ::= { ibOnuDot1xEntry 1 }

ibOnuDot1xPassword OBJECT-TYPE
    SYNTAX      OCTET STRING
    MAX-ACCESS  read-write
    STATUS      current
    DESCRIPTION
        "
        ONU 802.1X password.
        The object should be set together with ibOnuDot1xAccount.
        "
    ::= { ibOnuDot1xEntry 2 }

ibEponBatchOperationMan OBJECT IDENTIFIER ::= { ibEponMibObjects 6 }

--
-- ibOnuPriorityQueueTable
--

ibOnuPriorityQueueTable OBJECT-TYPE
    SYNTAX      SEQUENCE OF IbOnuPriorityQueueEntry
    MAX-ACCESS  not-accessible
    STATUS      current
    DESCRIPTION
        "
        This table contains specific information of priority queue.
        "
    ::= { ibEponOnuMan 19 }

ibOnuPriorityQueueEntry OBJECT-TYPE
    SYNTAX      IbOnuPriorityQueueEntry
    MAX-ACCESS  not-accessible
    STATUS      current
    DESCRIPTION
        "
        The entry of ibOnuPriorityQueueTable.
        "
    INDEX
        {
            ifIndex,
            ibOnuQueueDirection,
            ibOnuQueueId
        }
    ::= { ibOnuPriorityQueueTable 1 }

IbOnuPriorityQueueEntry ::= SEQUENCE
    {
        ibOnuQueueDirection    INTEGER,
        ibOnuQueueId           Integer32,
        ibOnuQueueSize         Integer32
    }

ibOnuQueueDirection OBJECT-TYPE
    SYNTAX      INTEGER
        {
            inbound(1),
            outbound(2)
        }
    MAX-ACCESS  not-accessible
    STATUS      current
    DESCRIPTION
        "
        The direction of priority queue.
        "
    ::= { ibOnuPriorityQueueEntry 1 }

ibOnuQueueId OBJECT-TYPE
    SYNTAX      Integer32(0..7)
    MAX-ACCESS  not-accessible
    STATUS      current
    DESCRIPTION
        "
        The queue ID of priority queue.
        "
    ::= { ibOnuPriorityQueueEntry 2 }

ibOnuQueueSize OBJECT-TYPE
    SYNTAX      Integer32
    MAX-ACCESS  read-write
    STATUS      current
    DESCRIPTION
        "
        The size of priority queue, measured in percent.  The total length of
        all priority queues is a constant, by default, it is assigned to all
        of the priority queues evenly.  The length of each priority queue may
        be changed by changing the value of ibOnuPriorityQueueSize.
        The total size of the inbound or outbound priority queues should be
        not more than 100.
        "
    ::= { ibOnuPriorityQueueEntry 3 }

--
-- ibOnuCountTable
--

ibOnuCountTable OBJECT-TYPE
    SYNTAX      SEQUENCE OF IbOnuCountEntry
    MAX-ACCESS  not-accessible
    STATUS      current
    DESCRIPTION
        "
        This table contains statistics of ONU port.
        "
    ::= { ibEponOnuMan 20 }

ibOnuCountEntry OBJECT-TYPE
    SYNTAX      IbOnuCountEntry
    MAX-ACCESS  not-accessible
    STATUS      current
    DESCRIPTION
        "
        The entry of ibOnuCountTable.
        "
    INDEX
        {
            ifIndex
        }
    ::= { ibOnuCountTable 1 }

IbOnuCountEntry ::= SEQUENCE
    {
        ibOnuInCRCErrPkts        Counter64,
        ibOnuOutDroppedFrames    Counter64
    }

ibOnuInCRCErrPkts OBJECT-TYPE
    SYNTAX      Counter64
    MAX-ACCESS  read-only
    STATUS      current
    DESCRIPTION
        "
        The total number of frames received with bad CRC checksum.
        "
    ::= { ibOnuCountEntry 1 }

ibOnuOutDroppedFrames OBJECT-TYPE
    SYNTAX      Counter64
    MAX-ACCESS  read-only
    STATUS      current
    DESCRIPTION
        "
        The total number of frames dropped because of buffer failure.
        "
    ::= { ibOnuCountEntry 2 }

ibEponOnuScalarGroup OBJECT IDENTIFIER ::= { ibEponOnuMan 21 }

ibOnuPriorityQueueSizeMinVal OBJECT-TYPE
    SYNTAX      Integer32
    MAX-ACCESS  read-only
    STATUS      current
    DESCRIPTION
        "
        The lower limit of queue size which is confined to
        ibOnuQueueSize.
        "
    ::= { ibEponOnuScalarGroup 1 }

ibOnuPriorityQueueSizeMaxVal OBJECT-TYPE
    SYNTAX      Integer32
    MAX-ACCESS  read-only
    STATUS      current
    DESCRIPTION
        "
        The upper limit of queue size which is confined to
        ibOnuQueueSize.
        "
    ::= { ibEponOnuScalarGroup 2 }

ibOnuPriorityQueueBandwidthMinVal OBJECT-TYPE
    SYNTAX      Integer32
    MAX-ACCESS  read-only
    STATUS      current
    DESCRIPTION
        "
        The lower limit of ibOnuQueueMaxBandwidth.
        "
    ::= { ibEponOnuScalarGroup 3 }

ibOnuPriorityQueueBandwidthMaxVal OBJECT-TYPE
    SYNTAX      Integer32
    MAX-ACCESS  read-only
    STATUS      current
    DESCRIPTION
        "
        The upper limit of ibOnuQueueMaxBandwidth.
        "
    ::= { ibEponOnuScalarGroup 4 }

ibOnuPriorityQueueBurstsizeMinVal OBJECT-TYPE
    SYNTAX      Integer32
    MAX-ACCESS  read-only
    STATUS      current
    DESCRIPTION
        "
        The lower limit of ibOnuQueueMaxBurstsize.
        "
    ::= { ibEponOnuScalarGroup 5 }

ibOnuPriorityQueueBurstsizeMaxVal OBJECT-TYPE
    SYNTAX      Integer32
    MAX-ACCESS  read-only
    STATUS      current
    DESCRIPTION
        "
        The upper limit of ibOnuQueueMaxBurstsize.
        "
    ::= { ibEponOnuScalarGroup 6 }

ibOnuUpdateByTypeNextIndex OBJECT-TYPE
    SYNTAX      Integer32
    MAX-ACCESS  read-only
    STATUS      current
    DESCRIPTION
        "
        Offer a free index of ibOnuFirmwareUpdateByTypeTable.
        "
    ::= { ibEponOnuScalarGroup 7 }

--
-- ibOnuQueueBandwidthTable
--

ibOnuQueueBandwidthTable OBJECT-TYPE
    SYNTAX      SEQUENCE OF IbOnuQueueBandwidthEntry
    MAX-ACCESS  not-accessible
    STATUS      current
    DESCRIPTION
        "
        This table contains specific bandwidth information of ONU priority queue.
        "
    ::= { ibEponOnuMan 22 }

ibOnuQueueBandwidthEntry OBJECT-TYPE
    SYNTAX      IbOnuQueueBandwidthEntry
    MAX-ACCESS  not-accessible
    STATUS      current
    DESCRIPTION
        "
        The entry of ibOnuQueueBandwidthTable.
        "
    INDEX
        {
            ifIndex,
            ibOnuQueueDirection,
            ibOnuQueueId
        }
    ::= { ibOnuQueueBandwidthTable 1 }

IbOnuQueueBandwidthEntry ::= SEQUENCE
    {
        ibOnuQueueMaxBandwidth    Integer32,
        ibOnuQueueMaxBurstsize    Integer32,
        ibOnuQueuePolicyStatus    TruthValue
    }

ibOnuQueueMaxBandwidth OBJECT-TYPE
    SYNTAX      Integer32
    MAX-ACCESS  read-write
    STATUS      current
    DESCRIPTION
        "
        The maximum bandwidth of specific ONU priority queue,
        measured in 100Kbps.
        "
    ::= { ibOnuQueueBandwidthEntry 1 }

ibOnuQueueMaxBurstsize OBJECT-TYPE
    SYNTAX      Integer32
    MAX-ACCESS  read-write
    STATUS      current
    DESCRIPTION
        "
        The maximum burst size of specific ONU priority queue,
        measured in 64Bytes.
        "
    ::= { ibOnuQueueBandwidthEntry 2 }

ibOnuQueuePolicyStatus OBJECT-TYPE
    SYNTAX      TruthValue
    MAX-ACCESS  read-write
    STATUS      current
    DESCRIPTION
        "
        true - enable bandwidth policy
        false - disable bandwidth policy
        The bandwidth administrative status of specific ONU priority queue.
        "
    ::= { ibOnuQueueBandwidthEntry 3 }

--
-- ibOnuIpAddressTable
--

ibOnuIpAddressTable OBJECT-TYPE
    SYNTAX      SEQUENCE OF IbOnuIpAddressEntry
    MAX-ACCESS  not-accessible
    STATUS      current
    DESCRIPTION
        "
        ONU IP address table.
        "
    ::= { ibEponOnuMan 23 }

ibOnuIpAddressEntry OBJECT-TYPE
    SYNTAX      IbOnuIpAddressEntry
    MAX-ACCESS  not-accessible
    STATUS      current
    DESCRIPTION
        "
        The entry of ibOnuIpAddressTable.
        "
    INDEX
        {
            ifIndex
        }
    ::= { ibOnuIpAddressTable 1 }

IbOnuIpAddressEntry ::= SEQUENCE
    {
        ibOnuIpAddress           IpAddress,
        ibOnuIpAddressMask       IpAddress,
        ibOnuIpAddressGateway    IpAddress,
        ibOnuDhcpallocate        TruthValue,
        ibOnuManageVID           Integer32,
        ibOnuManageVlanIntfS     TruthValue
    }

ibOnuIpAddress OBJECT-TYPE
    SYNTAX      IpAddress
    MAX-ACCESS  read-write
    STATUS      current
    DESCRIPTION
        "
        The IP address assigned to the ONU.
        "
    ::= { ibOnuIpAddressEntry 1 }

ibOnuIpAddressMask OBJECT-TYPE
    SYNTAX      IpAddress
    MAX-ACCESS  read-write
    STATUS      current
    DESCRIPTION
        "
        The mask of IP address denoted by ibOnuIpAddress.
        "
    ::= { ibOnuIpAddressEntry 2 }

ibOnuIpAddressGateway OBJECT-TYPE
    SYNTAX      IpAddress
    MAX-ACCESS  read-write
    STATUS      current
    DESCRIPTION
        "
        The gateway of IP address denoted by ibOnuIpAddress.
        "
    ::= { ibOnuIpAddressEntry 3 }

ibOnuDhcpallocate OBJECT-TYPE
    SYNTAX      TruthValue
    MAX-ACCESS  read-write
    STATUS      current
    DESCRIPTION
        "
        true(1)  - ONU auto allocate IP address status enable.
        false(2) - ONU auto allocate IP address status disable.
        "
    ::= { ibOnuIpAddressEntry 4 }

ibOnuManageVID OBJECT-TYPE
    SYNTAX      Integer32
    MAX-ACCESS  read-write
    STATUS      current
    DESCRIPTION
        "
        The management VLAN of ONU denoted by ibOnuManageVID.
        "
    ::= { ibOnuIpAddressEntry 5 }

ibOnuManageVlanIntfS OBJECT-TYPE
    SYNTAX      TruthValue
    MAX-ACCESS  read-write
    STATUS      current
    DESCRIPTION
        "
        The management interface status of ONU denoted by ibOnuManageVlanIntfS.
        "
    ::= { ibOnuIpAddressEntry 6 }

--
-- ibOnuChipSetInfoTable
--

ibOnuChipSetInfoTable OBJECT-TYPE
    SYNTAX      SEQUENCE OF IbOnuChipSetInfoEntry
    MAX-ACCESS  not-accessible
    STATUS      current
    DESCRIPTION
        "
        ONU vendor specific information of ONU.
        "
    ::= { ibEponOnuMan 24 }

ibOnuChipSetInfoEntry OBJECT-TYPE
    SYNTAX      IbOnuChipSetInfoEntry
    MAX-ACCESS  not-accessible
    STATUS      current
    DESCRIPTION
        "
        The entry of ibOnuChipSetInfoTable.
        "
    INDEX
        {
            ifIndex
        }
    ::= { ibOnuChipSetInfoTable 1 }

IbOnuChipSetInfoEntry ::= SEQUENCE
    {
        ibOnuChipSetVendorId      OCTET STRING,
        ibOnuChipSetModel         OCTET STRING,
        ibOnuChipSetRevision      Integer32,
        ibOnuChipSetDesignDate    DateAndTime
    }

ibOnuChipSetVendorId OBJECT-TYPE
    SYNTAX      OCTET STRING(SIZE(0..255))
    MAX-ACCESS  read-only
    STATUS      current
    DESCRIPTION
        "
        Chipset vendor ID, which identifies the ONU's PON chip vendor
        according JEDEC ID code.
        "
    ::= { ibOnuChipSetInfoEntry 1 }

ibOnuChipSetModel OBJECT-TYPE
    SYNTAX      OCTET STRING(SIZE(0..255))
    MAX-ACCESS  read-only
    STATUS      current
    DESCRIPTION
        "
        Chip model, numbering(range from 0 to 0xFF) by the chip vendor.
        "
    ::= { ibOnuChipSetInfoEntry 2 }

ibOnuChipSetRevision OBJECT-TYPE
    SYNTAX      Integer32
    MAX-ACCESS  read-only
    STATUS      current
    DESCRIPTION
        "
        Chip revision.
        "
    ::= { ibOnuChipSetInfoEntry 3 }

ibOnuChipSetDesignDate OBJECT-TYPE
    SYNTAX      DateAndTime
    MAX-ACCESS  read-only
    STATUS      current
    DESCRIPTION
        "
        Chip design date.
        "
    ::= { ibOnuChipSetInfoEntry 4 }

--
-- ibOnuCapabilityTable
--

ibOnuCapabilityTable OBJECT-TYPE
    SYNTAX      SEQUENCE OF IbOnuCapabilityEntry
    MAX-ACCESS  not-accessible
    STATUS      current
    DESCRIPTION
        "
        Capability of ONU.
        "
    ::= { ibEponOnuMan 25 }

ibOnuCapabilityEntry OBJECT-TYPE
    SYNTAX      IbOnuCapabilityEntry
    MAX-ACCESS  not-accessible
    STATUS      current
    DESCRIPTION
        "
        The entry of the table ibOnuCapabilityTable.
        "
    INDEX
        {
            ifIndex
        }
    ::= { ibOnuCapabilityTable 1 }

IbOnuCapabilityEntry ::= SEQUENCE
    {
        ibOnuServiceSupported             BITS,
        ibOnuGEPortNumber                 Integer32,
        ibOnuFEPortNumber                 Integer32,
        ibOnuPOTSPortNumber               Integer32,
        ibOnuE1PortsNumber                Integer32,
        ibOnuUpstreamQueueNumber          Integer32,
        ibOnuMaxUpstreamQueuePerPort      Integer32,
        ibOnuDownstreamQueueNumber        Integer32,
        ibOnuMaxDownstreamQueuePerPort    Integer32,
        ibOnuBatteryBackup                TruthValue,
        ibOnuIgspFastLeaveSupported       TruthValue,
        ibOnuMCtrlFastLeaveSupported      TruthValue,
        ibOnuType                         Integer32,
        ibOnuMultiLLID                    Integer32,
        ibOnuProtectionType               Integer32,
        ibOnuPonIFNum                     Integer32,
        ibOnuSlotNum                      Integer32,
        ibOnuIPv6Supported                Integer32,
        ibOnuPowerSupplyControl           Integer32,
        ibOnuServiceSLA                   Integer32
    }

ibOnuServiceSupported OBJECT-TYPE
    SYNTAX      BITS
        {
            geinterfacesupport(0),
            feinterfacesupport(1),
            voipservicesupport(2),
            tdmservicesupport(3)
        }
    MAX-ACCESS  read-only
    STATUS      current
    DESCRIPTION
        "
        Services types supported by the ONU.
        These functional groups can be supported independently.
        geinterfacesupport - supporting (1)/not supporting(0)
        Gbit Ethernet GE interface.
        feinterfacesupport - supporting (1)/not supporting(0)
        100M Ethernet FE interface.(maximum rate is 100M, without GEinterface)
        voipservicesupport - supporting (1)/not supporting(0)VoIP service.
        tdmservicesupport - supporting (1)/not supporting(0)TDM CES service.
        "
    ::= { ibOnuCapabilityEntry 1 }

ibOnuGEPortNumber OBJECT-TYPE
    SYNTAX      Integer32
    MAX-ACCESS  read-only
    STATUS      current
    DESCRIPTION
        "
        The current  gigabit ethernet ports number supported by the ONU.
        "
    ::= { ibOnuCapabilityEntry 2 }

ibOnuFEPortNumber OBJECT-TYPE
    SYNTAX      Integer32
    MAX-ACCESS  read-only
    STATUS      current
    DESCRIPTION
        "
        the current fast ethernet ports number supported by the ONU.
        "
    ::= { ibOnuCapabilityEntry 3 }

ibOnuPOTSPortNumber OBJECT-TYPE
    SYNTAX      Integer32
    MAX-ACCESS  read-only
    STATUS      current
    DESCRIPTION
        "
        The current POTS ports number supported by the ONU
        "
    ::= { ibOnuCapabilityEntry 4 }

ibOnuE1PortsNumber OBJECT-TYPE
    SYNTAX      Integer32
    MAX-ACCESS  read-only
    STATUS      current
    DESCRIPTION
        "
        The current E1 ports number supported by the ONU.
        "
    ::= { ibOnuCapabilityEntry 5 }

ibOnuUpstreamQueueNumber OBJECT-TYPE
    SYNTAX      Integer32
    MAX-ACCESS  read-only
    STATUS      current
    DESCRIPTION
        "
        The number of upstream queues supported by the ONU.
        "
    ::= { ibOnuCapabilityEntry 6 }

ibOnuMaxUpstreamQueuePerPort OBJECT-TYPE
    SYNTAX      Integer32
    MAX-ACCESS  read-only
    STATUS      current
    DESCRIPTION
        "
        The number of maximum upstream queues per port of the ONU.
        "
    ::= { ibOnuCapabilityEntry 7 }

ibOnuDownstreamQueueNumber OBJECT-TYPE
    SYNTAX      Integer32
    MAX-ACCESS  read-only
    STATUS      current
    DESCRIPTION
        "
        The number of downstream queues supported by the ONU.
        "
    ::= { ibOnuCapabilityEntry 8 }

ibOnuMaxDownstreamQueuePerPort OBJECT-TYPE
    SYNTAX      Integer32
    MAX-ACCESS  read-only
    STATUS      current
    DESCRIPTION
        "
        The number of maximum downstream queues per port of the ONU.
        "
    ::= { ibOnuCapabilityEntry 9 }

ibOnuBatteryBackup OBJECT-TYPE
    SYNTAX      TruthValue
    MAX-ACCESS  read-only
    STATUS      current
    DESCRIPTION
        "
        true(1) - ONU supports a reserve battery.
        false(2) - ONU does not support a reserve battery.
        "
    ::= { ibOnuCapabilityEntry 10 }

ibOnuIgspFastLeaveSupported OBJECT-TYPE
    SYNTAX      TruthValue
    MAX-ACCESS  read-only
    STATUS      current
    DESCRIPTION
        "
        true(1) -  ONU supports fast leave in igsp mode.
        false(2) - ONU does not support fast leave in igsp mode.
        "
    ::= { ibOnuCapabilityEntry 11 }

ibOnuMCtrlFastLeaveSupported OBJECT-TYPE
    SYNTAX      TruthValue
    MAX-ACCESS  read-only
    STATUS      current
    DESCRIPTION
        "
        true(1) -  ONU supports fast leave in multicast control mode.
        false(2) - ONU does not support fast leave in multicast control mode.
        "
    ::= { ibOnuCapabilityEntry 12 }

ibOnuType OBJECT-TYPE
    SYNTAX      Integer32
    MAX-ACCESS  read-only
    STATUS      current
    DESCRIPTION
        "
        ONU type:
        SFU(0)
        HGU(1)
        SBU(2)
        MDU(3) which is cassette equipment and uses Ethernet access as broadband
        MDU(4) which is small card equipment and uses Ethernet access as broadband
        MDU(5) which is small card equipment and uses DSL access as broadband
        MDU(6) which is middle card equipment and uses DSL access as broadband
        MDU(7) which is card equipment and can use both Ethernet and DSL access as broadband
        MTU(8)
        "
    ::= { ibOnuCapabilityEntry 13 }

ibOnuMultiLLID OBJECT-TYPE
    SYNTAX      Integer32
    MAX-ACCESS  read-only
    STATUS      current
    DESCRIPTION
        "
        (0) - Invalid value.
        (1) - ONU supports one LLID.
        other - ONU supports multiple LLIDs.
        "
    ::= { ibOnuCapabilityEntry 14 }

ibOnuProtectionType OBJECT-TYPE
    SYNTAX      Integer32
    MAX-ACCESS  read-only
    STATUS      current
    DESCRIPTION
        "
        (0) - Not supported.
        (1) - ONU supports type C optical link protection.
        (2) - ONU supports type D optical link protection.
        "
    ::= { ibOnuCapabilityEntry 15 }

ibOnuPonIFNum OBJECT-TYPE
    SYNTAX      Integer32
    MAX-ACCESS  read-only
    STATUS      current
    DESCRIPTION
        "
        (1) - ONU support one PON interface.
        (2) - ONU support two PON interfaces.
        "
    ::= { ibOnuCapabilityEntry 16 }

ibOnuSlotNum OBJECT-TYPE
    SYNTAX      Integer32
    MAX-ACCESS  read-only
    STATUS      current
    DESCRIPTION
        "
        The slot number of a card ONU.
        If the ONU is not card equipment, 0 is returned.
        "
    ::= { ibOnuCapabilityEntry 17 }

ibOnuIPv6Supported OBJECT-TYPE
    SYNTAX      Integer32
    MAX-ACCESS  read-only
    STATUS      current
    DESCRIPTION
        "
        (0) - ONU supports IPv6.
        (1) - ONU does not support IPv6.
        "
    ::= { ibOnuCapabilityEntry 18 }

ibOnuPowerSupplyControl OBJECT-TYPE
    SYNTAX      Integer32
    MAX-ACCESS  read-only
    STATUS      current
    DESCRIPTION
        "
        (0) - ONU does not support ONU power supply control.
        (1) - ONU supports Tx power supply control only.
        The Tx and Rx power supply can only be controlled together
        whereby Rx power supply is also shutdown when Tx power supply is shutdown.
        (2) - ONU supports both Tx and Rx power supply control.
        In this case, Tx and Rx power supply can be controlled separately whereby
        Rx power supply is still on while Tx power supply is shutdown.
        "
    ::= { ibOnuCapabilityEntry 19 }

ibOnuServiceSLA OBJECT-TYPE
    SYNTAX      Integer32
    MAX-ACCESS  read-only
    STATUS      current
    DESCRIPTION
        "
        (1) - ONU does not support SLA services.
        (2~8) - ONU supports 2~8 SLA services.
        "
    ::= { ibOnuCapabilityEntry 20 }

--
-- ibOnuDbaReportTable
--

ibOnuDbaReportTable OBJECT-TYPE
    SYNTAX      SEQUENCE OF IbOnuDbaReportEntry
    MAX-ACCESS  not-accessible
    STATUS      current
    DESCRIPTION
        "
        This table defines the information of DBA(dynamic bandwidth allocation)
        report threshold contained in the MPCP report frames.
        "
    ::= { ibEponOnuMan 26 }

ibOnuDbaReportEntry OBJECT-TYPE
    SYNTAX      IbOnuDbaReportEntry
    MAX-ACCESS  not-accessible
    STATUS      current
    DESCRIPTION
        "
        The entry of the table ibOnuDbaReportTable.
        "
    INDEX
        {
            ifIndex,
            ibOnuDbaReportQueueId
        }
    ::= { ibOnuDbaReportTable 1 }

IbOnuDbaReportEntry ::= SEQUENCE
    {
        ibOnuDbaReportQueueId      Integer32,
        ibOnuDbaReportThreshold    Integer32,
        ibOnuDbaReportStatus       INTEGER
    }

ibOnuDbaReportQueueId OBJECT-TYPE
    SYNTAX      Integer32
    MAX-ACCESS  not-accessible
    STATUS      current
    DESCRIPTION
        "
        The DBA report queue ID.
        "
    ::= { ibOnuDbaReportEntry 1 }

ibOnuDbaReportThreshold OBJECT-TYPE
    SYNTAX      Integer32
    MAX-ACCESS  read-write
    STATUS      current
    DESCRIPTION
        "
        The threshold of the DBA report queue.
        the following is the queue ID and
        the related default threshold setting.
        1 - 0
        2 - 0
        3 - 0
        4 - 65535
        5 - 65535
        6 - 0
        7 - 0
        8 - 0
        "
    ::= { ibOnuDbaReportEntry 2 }

ibOnuDbaReportStatus OBJECT-TYPE
    SYNTAX      INTEGER
        {
            enable(1),
            disable(2)
        }
    MAX-ACCESS  read-write
    STATUS      current
    DESCRIPTION
        "
        enable  -threshold configuration is active for the queue.
        disable -threshold configuration is not active for the queue.
        "
    DEFVAL { disable }
    ::= { ibOnuDbaReportEntry 3 }

--
-- ibOnuCosToLocalPrecedenceTable
--

ibOnuCosToLocalPrecedenceTable OBJECT-TYPE
    SYNTAX      SEQUENCE OF IbOnuCosToLocalPrecedenceEntry
    MAX-ACCESS  not-accessible
    STATUS      current
    DESCRIPTION
        "Table of map of the COS to local-precedence."
    ::= { ibEponOnuMan 27 }

ibOnuCosToLocalPrecedenceEntry OBJECT-TYPE
    SYNTAX      IbOnuCosToLocalPrecedenceEntry
    MAX-ACCESS  not-accessible
    STATUS      current
    DESCRIPTION
        "Configuration information of map of the COS to local precedence."
    INDEX
        {
            ifIndex,
            ibOnuCosToLocalPrecedenceCosIndex
        }
    ::= { ibOnuCosToLocalPrecedenceTable 1 }

IbOnuCosToLocalPrecedenceEntry ::= SEQUENCE
    {
        ibOnuCosToLocalPrecedenceCosIndex    Integer32,
        ibOnuCosToLocalPrecedenceValue       Integer32
    }

ibOnuCosToLocalPrecedenceCosIndex OBJECT-TYPE
    SYNTAX      Integer32(0..7)
    MAX-ACCESS  read-only
    STATUS      current
    DESCRIPTION
        "Index of the map, obtains from packet cos value."
    ::={ ibOnuCosToLocalPrecedenceEntry 1 }

ibOnuCosToLocalPrecedenceValue OBJECT-TYPE
    SYNTAX      Integer32(0..3)
    MAX-ACCESS  read-write
    STATUS      current
    DESCRIPTION
        "Value of local precedence."
    ::={ ibOnuCosToLocalPrecedenceEntry 2 }

--
-- ibEponOnuStpPortTable
--

ibEponOnuStpPortTable OBJECT-TYPE
    SYNTAX      SEQUENCE OF IbEponOnuStpPortEntry
    MAX-ACCESS  not-accessible
    STATUS      current
    DESCRIPTION
        "Table of ONU STP ports."
    ::= { ibEponOnuMan 28 }

ibEponOnuStpPortEntry OBJECT-TYPE
    SYNTAX      IbEponOnuStpPortEntry
    MAX-ACCESS  not-accessible
    STATUS      current
    DESCRIPTION
        "Configuration information of ONU STP ports."
    INDEX
        {
            ifIndex,
            ibEponStpPortIndex
        }
    ::= { ibEponOnuStpPortTable 1 }

IbEponOnuStpPortEntry ::= SEQUENCE
    {
        ibEponStpPortIndex     Integer32,
        ibEponStpPortDescr     OCTET STRING,
        ibEponStpPortState     INTEGER
    }

ibEponStpPortIndex OBJECT-TYPE
    SYNTAX      Integer32(0..144)
    MAX-ACCESS  accessible-for-notify
    STATUS      current
    DESCRIPTION
        "The index of the STP ports."
    ::={ ibEponOnuStpPortEntry 1 }

ibEponStpPortDescr OBJECT-TYPE
    SYNTAX      OCTET STRING
    MAX-ACCESS  read-only
    STATUS      current
    DESCRIPTION
        "The description of the STP ports."
    ::={ ibEponOnuStpPortEntry 2 }

ibEponStpPortState OBJECT-TYPE
    SYNTAX      INTEGER
        {
            disabled(1),
            discarding(2),
            learning(3),
            forwarding(4)
        }
    MAX-ACCESS  read-only
    STATUS      current
    DESCRIPTION
        "The current state of the port (i.e. disabled, discarding,
         learning and forwarding)."
    ::={ ibEponOnuStpPortEntry 3 }

--
-- ibOnuPhysicalTable
--

ibOnuPhysicalTable OBJECT-TYPE
    SYNTAX      SEQUENCE OF IbOnuPhysicalEntry
    MAX-ACCESS  not-accessible
    STATUS      current
    DESCRIPTION
        "
        This table is used for getting ONU physical information.
        "
    ::= { ibEponOnuMan 29 }

ibOnuPhysicalEntry OBJECT-TYPE
    SYNTAX      IbOnuPhysicalEntry
    MAX-ACCESS  not-accessible
    STATUS      current
    DESCRIPTION
        "
        The entry of the ibOnuPhysicalTable.
        "
    INDEX
        {
            ifIndex
        }
    ::= { ibOnuPhysicalTable 1 }

IbOnuPhysicalEntry ::= SEQUENCE
    {
        ibOnuBridgeMac         MacAddress,
        ibOnuFirstPonMac       MacAddress,
        ibOnuFirstPonRegState  INTEGER,
        ibOnuSecondPonMac      MacAddress,
        ibOnuSecondPonRegState INTEGER
    }

ibOnuBridgeMac OBJECT-TYPE
    SYNTAX      MacAddress
    MAX-ACCESS  read-only
    STATUS      current
    DESCRIPTION
        "
        The bridge MAC address of ONU.
        "
    ::= { ibOnuPhysicalEntry 1 }

ibOnuFirstPonMac OBJECT-TYPE
    SYNTAX      MacAddress
    MAX-ACCESS  read-only
    STATUS      current
    DESCRIPTION
        "
        The MAC address of ONU first PON port.
        "
    ::= { ibOnuPhysicalEntry 2 }

ibOnuFirstPonRegState OBJECT-TYPE
    SYNTAX      INTEGER
        {
            notExist(1),
            absent(2),
            offline(3),
            silent(4),
            down(5),
            up(6)
        }
    MAX-ACCESS  read-only
    STATUS      current
    DESCRIPTION
        "
        The register state of ONU first PON port.
        "
    ::= { ibOnuPhysicalEntry 3 }

ibOnuSecondPonMac OBJECT-TYPE
    SYNTAX      MacAddress
    MAX-ACCESS  read-only
    STATUS      current
    DESCRIPTION
        "
        The MAC address of ONU second PON port.
        "
    ::= { ibOnuPhysicalEntry 4 }

ibOnuSecondPonRegState OBJECT-TYPE
    SYNTAX      INTEGER
        {
            notExist(1),
            absent(2),
            offline(3),
            silent(4),
            down(5),
            up(6)
        }
    MAX-ACCESS  read-only
    STATUS      current
    DESCRIPTION
        "
        The register state of ONU second PON port.
        "
    ::= { ibOnuPhysicalEntry 5 }

--
-- ibOnuSmlkTable
--

ibOnuSmlkTable OBJECT-TYPE
    SYNTAX      SEQUENCE OF IbOnuSmlkEntry
    MAX-ACCESS  not-accessible
    STATUS      current
    DESCRIPTION
        "
        This table is used for getting ONU SMLK information.
        "
    ::= { ibEponOnuMan 30 }

ibOnuSmlkEntry OBJECT-TYPE
    SYNTAX      IbOnuSmlkEntry
    MAX-ACCESS  not-accessible
    STATUS      current
    DESCRIPTION
        "
        The entry of the ibOnuSmlkTable.
        "
    INDEX
        {
            ifIndex,
            ibOnuSmlkGroupID
        }
    ::= { ibOnuSmlkTable 1 }

IbOnuSmlkEntry ::= SEQUENCE
    {
        ibOnuSmlkGroupID            Integer32,
        ibOnuSmlkFirstPonRole       INTEGER,
        ibOnuSmlkFirstPonStatus     INTEGER,
        ibOnuSmlkSecondPonRole      INTEGER,
        ibOnuSmlkSecondPonStatus    INTEGER
    }

ibOnuSmlkGroupID OBJECT-TYPE
    SYNTAX      Integer32
    MAX-ACCESS  read-only
    STATUS      current
    DESCRIPTION
        "
        The SMLK group ID of ONU.
        "
    ::= { ibOnuSmlkEntry 1 }

ibOnuSmlkFirstPonRole OBJECT-TYPE
    SYNTAX      INTEGER
        {
            master(1),
            slave(2),
            null(3)
        }
    MAX-ACCESS  read-only
    STATUS      current
    DESCRIPTION
        "
        The role of ONU first PON port in a SMLK group.
        "
    ::= { ibOnuSmlkEntry 2 }

ibOnuSmlkFirstPonStatus OBJECT-TYPE
    SYNTAX      INTEGER
        {
            active(1),
            standby(2),
            down(3),
            null(4)
        }
    MAX-ACCESS  read-only
    STATUS      current
    DESCRIPTION
        "
        The transmitting status of ONU first PON port in a SMLK group.
        "
    ::= { ibOnuSmlkEntry 3 }

ibOnuSmlkSecondPonRole OBJECT-TYPE
    SYNTAX      INTEGER
        {
            master(1),
            slave(2),
            null(3)
        }
    MAX-ACCESS  read-only
    STATUS      current
    DESCRIPTION
        "
        The role of ONU second PON port in a SMLK group.
        "
    ::= { ibOnuSmlkEntry 4 }

ibOnuSmlkSecondPonStatus OBJECT-TYPE
    SYNTAX      INTEGER
        {
            active(1),
            standby(2),
            down(3),
            null(4)
        }
    MAX-ACCESS  read-only
    STATUS      current
    DESCRIPTION
        "
        The transmitting status of ONU second PON port in a SMLK group.
        "
    ::= { ibOnuSmlkEntry 5 }

--
-- ibOnuRS485PropertiesTable
--

ibOnuRS485PropertiesTable OBJECT-TYPE
    SYNTAX      SEQUENCE OF IbOnuRS485PropertiesEntry
    MAX-ACCESS  not-accessible
    STATUS      current
    DESCRIPTION
            "Property table."
    ::= { ibEponOnuMan 31 }

ibOnuRS485PropertiesEntry OBJECT-TYPE
    SYNTAX          IbOnuRS485PropertiesEntry
    MAX-ACCESS      not-accessible
    STATUS          current
    DESCRIPTION
            "The entry of property table."
    INDEX      {
                ifIndex,
                ibOnuRS485SerialIndex
               }
    ::= { ibOnuRS485PropertiesTable 1 }

IbOnuRS485PropertiesEntry ::=
    SEQUENCE{
        ibOnuRS485SerialIndex
            Integer32,
        ibOnuRS485BaudRate
            INTEGER,
        ibOnuRS485DataBits
            INTEGER,
        ibOnuRS485Parity
            INTEGER,
        ibOnuRS485StopBits
            INTEGER,
        ibOnuRS485FlowControl
            INTEGER,
        ibOnuRS485TXOctets
            Integer32,
        ibOnuRS485RXOctets
            Integer32,
        ibOnuRS485TXErrOctets
            Integer32,
        ibOnuRS485RXErrOctets
            Integer32,
        ibOnuRS485ResetStatistics
            INTEGER
    }

ibOnuRS485SerialIndex OBJECT-TYPE
    SYNTAX          Integer32 (1..64)
    MAX-ACCESS      not-accessible
    STATUS          current
    DESCRIPTION
        "The index of serial port."
    ::= { ibOnuRS485PropertiesEntry 1 }

ibOnuRS485BaudRate OBJECT-TYPE
    SYNTAX          INTEGER {
                        baudRate300(1),
                        baudRate600(2),
                        baudRate1200(3),
                        baudRate2400(4),
                        baudRate4800(5),
                        baudRate9600(6),
                        baudRate19200(7),
                        baudRate38400(8),
                        baudRate57600(9),
                        baudRate115200(10)
                        }
    MAX-ACCESS      read-write
    STATUS          current
    DESCRIPTION
            "The port baud rate."
    DEFVAL          { baudRate9600 }
    ::= { ibOnuRS485PropertiesEntry 2 }

ibOnuRS485DataBits OBJECT-TYPE
    SYNTAX          INTEGER {
                        five(1),            -- 5 data bits
                        six(2),             -- 6 data bits
                        seven(3),           -- 7 data bits
                        eight(4)            -- 8 data bits
                    }
    UNITS           "bit"
    MAX-ACCESS      read-write
    STATUS          current
    DESCRIPTION
            "The port number of data bits in a character."
    DEFVAL          { eight }
    ::= { ibOnuRS485PropertiesEntry 3 }

ibOnuRS485Parity OBJECT-TYPE
    SYNTAX          INTEGER {
                        none(1),
                        odd(2),
                        even(3),
                        mark(4),
                        space(5)
                    }
    MAX-ACCESS      read-write
    STATUS          current
    DESCRIPTION
            "The port sense of a character parity bit."
    DEFVAL          { none }
    ::= { ibOnuRS485PropertiesEntry 4 }

ibOnuRS485StopBits OBJECT-TYPE
    SYNTAX          INTEGER {
                        one(1),               -- 1 stop bit
                        two(2),               -- 2 stop bits
                        oneAndHalf(3)         -- 1.5 stop bits
                    }
    UNITS           "bit"
    MAX-ACCESS      read-write
    STATUS          current
    DESCRIPTION
            "The port number of stop bits."
    DEFVAL          { one }
    ::= { ibOnuRS485PropertiesEntry 5 }

ibOnuRS485FlowControl OBJECT-TYPE
    SYNTAX          INTEGER{
                        none(1),
                        hardware(2),
                        xonOrxoff(3)
                    }
    MAX-ACCESS      read-write
    STATUS          current
    DESCRIPTION
            "The port type of input flow control.
             'none' indicates no flow control at this level.
             'hardware' indicates using hardware signals.
             'xonOrxoff' indicates using software function."
    DEFVAL          { none }
    ::= { ibOnuRS485PropertiesEntry 6 }

ibOnuRS485TXOctets OBJECT-TYPE
    SYNTAX          Integer32
    MAX-ACCESS      read-only
    STATUS          current
    DESCRIPTION
            "The number of output octets about the port.
             The unit is byte."
    ::= { ibOnuRS485PropertiesEntry 7 }

ibOnuRS485RXOctets OBJECT-TYPE
    SYNTAX          Integer32
    MAX-ACCESS      read-only
    STATUS          current
    DESCRIPTION
            "The number of input octets about the port.
             The unit is byte."
    ::= { ibOnuRS485PropertiesEntry 8 }

ibOnuRS485TXErrOctets OBJECT-TYPE
    SYNTAX          Integer32
    MAX-ACCESS      read-only
    STATUS          current
    DESCRIPTION
            "The number of output error octets about the port.
             The unit is byte."
    ::= { ibOnuRS485PropertiesEntry 9 }

ibOnuRS485RXErrOctets OBJECT-TYPE
    SYNTAX          Integer32
    MAX-ACCESS      read-only
    STATUS          current
    DESCRIPTION
            "The number of input error octets about the port.
             The unit is byte."
    ::= { ibOnuRS485PropertiesEntry 10 }

ibOnuRS485ResetStatistics OBJECT-TYPE
    SYNTAX          INTEGER {
                        counting(1),
                        clear(2)
                    }
    MAX-ACCESS      read-write
    STATUS          current
    DESCRIPTION
            "Reset the counters to zero, including ibOnuRS485TXOctets,
             ibOnuRS485RXOctets, ibOnuRS485TXErrOctets and
             ibOnuRS485RXErrOctets."
    DEFVAL          { counting }
    ::= { ibOnuRS485PropertiesEntry 11 }

--
-- ibOnuRS485SessionSummaryTable
--

ibOnuRS485SessionSummaryTable OBJECT-TYPE
    SYNTAX      SEQUENCE OF IbOnuRS485SessionSummaryEntry
    MAX-ACCESS  not-accessible
    STATUS      current
    DESCRIPTION
            "Session summary table."
    ::= { ibEponOnuMan 32 }

ibOnuRS485SessionSummaryEntry OBJECT-TYPE
    SYNTAX          IbOnuRS485SessionSummaryEntry
    MAX-ACCESS      not-accessible
    STATUS          current
    DESCRIPTION
            "The entry of session summary table."
    INDEX      {
                ifIndex,
                ibOnuRS485SerialIndex
               }
    ::= { ibOnuRS485SessionSummaryTable 1 }

IbOnuRS485SessionSummaryEntry ::=
    SEQUENCE{
        ibOnuRS485SessionMaxNum
            Integer32,
        ibOnuRS485SessionNextIndex
            Integer32
            }

ibOnuRS485SessionMaxNum OBJECT-TYPE
    SYNTAX          Integer32 (1..64)
    MAX-ACCESS      read-only
    STATUS          current
    DESCRIPTION
            "The max session number of every serial port
             which can be supported."
    ::= { ibOnuRS485SessionSummaryEntry 1 }

ibOnuRS485SessionNextIndex OBJECT-TYPE
    SYNTAX          Integer32 (0..64)
    MAX-ACCESS      read-only
    STATUS          current
    DESCRIPTION
            "The next valid index used for creating a new session raw.
             When there is no valid index left, it will return 0.
            "
    ::= { ibOnuRS485SessionSummaryEntry 2 }

--
-- ibOnuRS485SessionTable
--

ibOnuRS485SessionTable OBJECT-TYPE
    SYNTAX      SEQUENCE OF IbOnuRS485SessionEntry
    MAX-ACCESS  not-accessible
    STATUS      current
    DESCRIPTION
            "RS485 raw session table.  Data received from RS485 will be sent
            to the destination by raw sockets.
            "
    ::= { ibEponOnuMan 33 }

ibOnuRS485SessionEntry OBJECT-TYPE
    SYNTAX          IbOnuRS485SessionEntry
    MAX-ACCESS      not-accessible
    STATUS          current
    DESCRIPTION
            "The entry of session table."
    INDEX      {
                ifIndex,
                ibOnuRS485SerialIndex,
                ibOnuRS485SessionIndex
               }
    ::= { ibOnuRS485SessionTable 1 }

IbOnuRS485SessionEntry ::=
    SEQUENCE{
        ibOnuRS485SessionIndex
            Integer32,
        ibOnuRS485SessionType
            INTEGER,
        ibOnuRS485SessionAddType
            InetAddressType,
        ibOnuRS485SessionRemoteIP
            InetAddress,
        ibOnuRS485SessionRemotePort
            Integer32,
        ibOnuRS485SessionLocalPort
            Integer32,
        ibOnuRS485SessionRowStatus
            RowStatus
    }

ibOnuRS485SessionIndex OBJECT-TYPE
    SYNTAX          Integer32 (1..64)
    MAX-ACCESS      not-accessible
    STATUS          current
    DESCRIPTION
            "Raw session index."
    ::= { ibOnuRS485SessionEntry 1 }

ibOnuRS485SessionType OBJECT-TYPE
    SYNTAX          INTEGER {
                        udp(1),
                        tcpClient(2),
                        tcpServer(3)
                    }
    MAX-ACCESS      read-create
    STATUS          current
    DESCRIPTION
            "The type of a session.
             A session can use UDP socket, TCP socket as a client,
             or TCP socket as a server."
    ::= { ibOnuRS485SessionEntry 2 }

ibOnuRS485SessionAddType OBJECT-TYPE
    SYNTAX          InetAddressType
    MAX-ACCESS      read-create
    STATUS          current
    DESCRIPTION
            "This object indicates the transport type of the
             address contained in ibOnuRS485SessionRemoteIP object."
    ::= { ibOnuRS485SessionEntry 3 }

ibOnuRS485SessionRemoteIP OBJECT-TYPE
    SYNTAX          InetAddress
    MAX-ACCESS      read-create
    STATUS          current
    DESCRIPTION
            "The IP of remote landing.
            When session type is 'udp', this is the peer IP.
            When session type is 'tcpClient', this is the server IP.
            When session type is 'tcpServer', this is invalid.
            "
    ::= { ibOnuRS485SessionEntry 4 }

ibOnuRS485SessionRemotePort OBJECT-TYPE
    SYNTAX          Integer32 (1024..65535)
    MAX-ACCESS      read-create
    STATUS          current
    DESCRIPTION
            "The port of remote landing.
            When session type is 'udp', this is the peer port.
            When session type is 'tcpClient', this is the server port.
            When session type is 'tcpServer', this is invalid.
            "
    ::= { ibOnuRS485SessionEntry 5 }

ibOnuRS485SessionLocalPort OBJECT-TYPE
    SYNTAX          Integer32 (1024..65535)
    MAX-ACCESS      read-create
    STATUS          current
    DESCRIPTION
            "Local socket port.
            When session type is 'udp', this is local UDP socket port.
            When session type is 'tcpClient', this is invalid.
            When session type is 'tcpServer', this is the local port which
            will be listened.
            "
    ::= { ibOnuRS485SessionEntry 6 }

ibOnuRS485SessionRowStatus OBJECT-TYPE
    SYNTAX          RowStatus
    MAX-ACCESS      read-create
    STATUS          current
    DESCRIPTION
            "The status used for creating,
            modifying, and deleting instances of
            the columnar objects in raw session table."
    ::= { ibOnuRS485SessionEntry 7 }

--
-- ibOnuRS485SessionErrInfoTable
--

ibOnuRS485SessionErrInfoTable OBJECT-TYPE
    SYNTAX      SEQUENCE OF IbOnuRS485SessionErrInfoEntry
    MAX-ACCESS  not-accessible
    STATUS      current
    DESCRIPTION
            "Error information table.  When failed to create a session,
             error information can be got from this table."
    ::= { ibEponOnuMan 34 }

ibOnuRS485SessionErrInfoEntry OBJECT-TYPE
    SYNTAX          IbOnuRS485SessionErrInfoEntry
    MAX-ACCESS      not-accessible
    STATUS          current
    DESCRIPTION
            "The entry of error information table."
    INDEX      {
                ifIndex,
                ibOnuRS485SerialIndex,
                ibOnuRS485SessionIndex
               }
    ::= { ibOnuRS485SessionErrInfoTable 1 }

IbOnuRS485SessionErrInfoEntry ::=
    SEQUENCE{
        ibOnuRS485SessionErrInfo
            DisplayString
    }

ibOnuRS485SessionErrInfo OBJECT-TYPE
    SYNTAX          DisplayString
    MAX-ACCESS      read-only
    STATUS          current
    DESCRIPTION
        "Error information string.  When a response with 'noCreeation' for
        row creation in table ibOnuRS485SessionTable,
        the error reason can be got from this object."
    ::= { ibOnuRS485SessionErrInfoEntry 1 }

--
-- ibOnuDbaReport2Table
--

ibOnuDbaReport2Table OBJECT-TYPE
    SYNTAX      SEQUENCE OF IbOnuDbaReport2Entry
    MAX-ACCESS  not-accessible
    STATUS      current
    DESCRIPTION
        "
        This table defines the information of DBA(dynamic bandwidth allocation)
        report threshold contained in the MPCP report frames.
        "
    ::= { ibEponOnuMan 35 }

ibOnuDbaReport2Entry OBJECT-TYPE
    SYNTAX      IbOnuDbaReport2Entry
    MAX-ACCESS  not-accessible
    STATUS      current
    DESCRIPTION
        "
        The entry of the table ibOnuDbaReport2Table.
        "
    INDEX
        {
            ifIndex,
            ibOnuDbaReport2QueueSetId,
            ibOnuDbaReport2QueueId
        }
    ::= { ibOnuDbaReport2Table 1 }

IbOnuDbaReport2Entry ::= SEQUENCE
    {
        ibOnuDbaReport2QueueSetId   Integer32,
        ibOnuDbaReport2QueueId      Integer32,
        ibOnuDbaReport2Threshold    Integer32,
        ibOnuDbaReport2Status       TruthValue
    }

ibOnuDbaReport2QueueSetId OBJECT-TYPE
    SYNTAX      Integer32 (1..3)
    MAX-ACCESS  not-accessible
    STATUS      current
    DESCRIPTION
        "
        The DBA report queue set ID.
        "
    ::= { ibOnuDbaReport2Entry 1 }

ibOnuDbaReport2QueueId OBJECT-TYPE
    SYNTAX      Integer32 (1..8)
    MAX-ACCESS  not-accessible
    STATUS      current
    DESCRIPTION
        "
        The DBA report queue ID.
        "
    ::= { ibOnuDbaReport2Entry 2 }

ibOnuDbaReport2Threshold OBJECT-TYPE
    SYNTAX      Integer32
    MAX-ACCESS  read-write
    STATUS      current
    DESCRIPTION
        "
        The thresholds of the DBA report queue.
        The following are the queue ID and
        the related default threshold settings.
        1 - 0
        2 - 0
        3 - 0
        4 - 65535
        5 - 65535
        6 - 0
        7 - 0
        8 - 0
        "
    ::= { ibOnuDbaReport2Entry 3 }

ibOnuDbaReport2Status OBJECT-TYPE
    SYNTAX      TruthValue
    MAX-ACCESS  read-write
    STATUS      current
    DESCRIPTION
        "
        true  -threshold configuration is active for the queue.
        false -threshold configuration is not active for the queue.
        "
    ::= { ibOnuDbaReport2Entry 4 }

--
-- ibOnuLoidInfoTable
--

ibOnuLoidInfoTable OBJECT-TYPE
    SYNTAX      SEQUENCE OF IbOnuLoidInfoEntry
    MAX-ACCESS  not-accessible
    STATUS      current
    DESCRIPTION
        "
        This table is used for getting LOID information of an ONU.
        "
    ::= { ibEponOnuMan 36 }

ibOnuLoidInfoEntry OBJECT-TYPE
    SYNTAX      IbOnuLoidInfoEntry
    MAX-ACCESS  not-accessible
    STATUS      current
    DESCRIPTION
        "
        The entry of the ibOnuLoidInfoTable.
        "
    INDEX
        {
            ifIndex,
            ibOnuLoidIndex
        }
    ::= { ibOnuLoidInfoTable 1 }

IbOnuLoidInfoEntry ::= SEQUENCE
    {
        ibOnuLoidIndex      Integer32,
        ibOnuLoidFlag       INTEGER,
        ibOnuLoid           OCTET STRING
    }

ibOnuLoidIndex OBJECT-TYPE
    SYNTAX      Integer32
    MAX-ACCESS  not-accessible
    STATUS      current
    DESCRIPTION
        "
        The index of an ONU in one OLT.
        "
    ::= { ibOnuLoidInfoEntry 1 }

ibOnuLoidFlag OBJECT-TYPE
    SYNTAX      INTEGER
        {
            bound(1),
            registered(2),
            run(3),
            regIncorrect(4)
        }
    MAX-ACCESS  read-only
    STATUS      current
    DESCRIPTION
        "
        The flag of ONU status.
        1 - bound: The ONU is bound but not registered.
        2 - registered: The ONU is registered but not bound.
        3 - run: The ONU is registered and bound on one OLT.
        4 - regIncorrect: The ONU is bound on one OLT and registered on
        another OLT.
        "
    ::= { ibOnuLoidInfoEntry 2 }

ibOnuLoid OBJECT-TYPE
    SYNTAX      OCTET STRING(SIZE(1..24))
    MAX-ACCESS  read-only
    STATUS      current
    DESCRIPTION
        "
        The LOID of an ONU.
        "
    ::= { ibOnuLoidInfoEntry 3 }

--
-- ibOnuStatisticsTable
--

ibOnuStatisticsTable OBJECT-TYPE
    SYNTAX      SEQUENCE OF IbOnuStatisticsEntry
    MAX-ACCESS  not-accessible
    STATUS      current
    DESCRIPTION
        "
        This table is used for enabling or disabling statistics and setting period of a PON.
        "
    ::= { ibEponOnuMan 37 }

ibOnuStatisticsEntry OBJECT-TYPE
    SYNTAX      IbOnuStatisticsEntry
    MAX-ACCESS  not-accessible
    STATUS      current
    DESCRIPTION
        "
        The entry of the ibOnuStatisticsTable.
        "
    INDEX
        {
            ifIndex
        }
    ::= { ibOnuStatisticsTable 1 }

IbOnuStatisticsEntry ::= SEQUENCE
    {
        ibOnuStatisticsPeriodVal  Unsigned32,
        ibOnuStatisticsEnable     TruthValue
    }

ibOnuStatisticsPeriodVal OBJECT-TYPE
    SYNTAX      Unsigned32
    MAX-ACCESS  read-write
    STATUS      current
    DESCRIPTION
        "
        PON statistics period value.
        "
    ::= { ibOnuStatisticsEntry 1 }

ibOnuStatisticsEnable OBJECT-TYPE
    SYNTAX      TruthValue
    MAX-ACCESS  read-write
    STATUS      current
    DESCRIPTION
        "
        Enable or disable statistics of a PON.
        true(1)  - alarm enable.
        false(2) - alarm disable.
        "
    ::= { ibOnuStatisticsEntry 2 }

ibOnuSlaMaxBandWidthMinVal10G OBJECT-TYPE
    SYNTAX      Integer32
    MAX-ACCESS  read-only
    STATUS      current
    DESCRIPTION
        "
        The lower limit of maximum-bandwidth which is confined to
        ibOnuSlaMaxBandWidth for 10G EPON."
    ::= { ibEponOnuMan 38 }

ibOnuSlaMaxBandWidthMaxVal10G OBJECT-TYPE
    SYNTAX      Integer32
    MAX-ACCESS  read-only
    STATUS      current
    DESCRIPTION
        "
        The upper limit of maximum-bandwidth which is confined to
        ibOnuSlaMaxBandWidth for 10G EPON."
    ::= { ibEponOnuMan 39 }

ibOnuSlaMinBandWidthMinVal10G OBJECT-TYPE
    SYNTAX      Integer32
    MAX-ACCESS  read-only
    STATUS      current
    DESCRIPTION
        "
        The lower limit of minimum-bandwidth which is confined to
        ibOnuSlaMinBandWidth for 10G EPON."
    ::= { ibEponOnuMan 40 }

ibOnuSlaMinBandWidthMaxVal10G OBJECT-TYPE
    SYNTAX      Integer32
    MAX-ACCESS  read-only
    STATUS      current
    DESCRIPTION
        "
        The upper limit of minimum-bandwidth which is confined to
        ibOnuSlaMinBandWidth for 10G EPON."
    ::= { ibEponOnuMan 41 }

--
-- ibOnuServiceSlaTable
--

ibOnuServiceSlaTable OBJECT-TYPE
    SYNTAX      SEQUENCE OF IbOnuServiceSlaEntry
    MAX-ACCESS  not-accessible
    STATUS      current
    DESCRIPTION
        "
        This table is used for setting the service SLA mode and applying the service SLA to an ONU.
        "
    ::= { ibEponOnuMan 42 }

ibOnuServiceSlaEntry OBJECT-TYPE
    SYNTAX      IbOnuServiceSlaEntry
    MAX-ACCESS  not-accessible
    STATUS      current
    DESCRIPTION
        "
        The entry of the ibOnuServiceSlaTable.
        "
    INDEX
        {
            ifIndex
        }
    ::= { ibOnuServiceSlaTable 1 }

IbOnuServiceSlaEntry ::= SEQUENCE
    {
        ibSlaSchedulingMode       INTEGER,
        ibSlaHighPrioBoundary     Integer32,
        ibSlaCycleLength          Integer32,
        ibSlaApply                TruthValue
    }

ibSlaSchedulingMode OBJECT-TYPE
    SYNTAX      INTEGER
        {
            sp(0),
            wrr(1),
            spWrr(2),
            invalid(3)
        }
    MAX-ACCESS  read-write
    STATUS      current
    DESCRIPTION
        "
        Service SLA scheduling mode.
        "
    DEFVAL { invalid }
    ::= { ibOnuServiceSlaEntry 1 }

ibSlaHighPrioBoundary OBJECT-TYPE
    SYNTAX      Integer32
    MAX-ACCESS  read-write
    STATUS      current
    DESCRIPTION
        "
        Service SLA high priority boundary in SP-WRR mode.
        "
    ::= { ibOnuServiceSlaEntry 2 }

ibSlaCycleLength OBJECT-TYPE
    SYNTAX      Integer32(200..16777215)
    UNITS       "time quantums"
    MAX-ACCESS  read-write
    STATUS      current
    DESCRIPTION
        "
        Service SLA cycle length in time quantums.
        "
    DEFVAL { 62500 }
    ::= { ibOnuServiceSlaEntry 3 }

ibSlaApply OBJECT-TYPE
    SYNTAX      TruthValue
    MAX-ACCESS  read-write
    STATUS      current
    DESCRIPTION
        "
        Apply service SLA configuration.
        true(1)  - Apply.
        false(2) - Not apply.
        "
    DEFVAL { false }
    ::= { ibOnuServiceSlaEntry 4 }

--
-- ibOnuServiceSlaQueTable
--

ibOnuServiceSlaQueTable OBJECT-TYPE
    SYNTAX      SEQUENCE OF IbOnuServiceSlaQueEntry
    MAX-ACCESS  not-accessible
    STATUS      current
    DESCRIPTION
        "
        This table is used for configuring service SLA queues.
        "
    ::= { ibEponOnuMan 43 }

ibOnuServiceSlaQueEntry OBJECT-TYPE
    SYNTAX      IbOnuServiceSlaQueEntry
    MAX-ACCESS  not-accessible
    STATUS      current
    DESCRIPTION
        "
        The entry of the ibOnuServiceSlaQueTable.
        "
    INDEX
        {
            ifIndex,
            ibSlaQueId
        }
    ::= { ibOnuServiceSlaQueTable 1 }

IbOnuServiceSlaQueEntry ::= SEQUENCE
    {
        ibSlaQueId                Integer32,
        ibSlaQueMode              INTEGER,
        ibSlaQueWeight            Integer32,
        ibSlaQueFixPktSize        Integer32,
        ibSlaQueFixBandwidth      Integer32,
        ibSlaQueGuaBandwidth      Integer32,
        ibSlaQueBstBandwidth      Integer32,
        ibSlaQueRowStatus         RowStatus
    }

ibSlaQueId OBJECT-TYPE
    SYNTAX      Integer32
    MAX-ACCESS  not-accessible
    STATUS      current
    DESCRIPTION
        "
        Service SLA queue ID.
        "
    ::= { ibOnuServiceSlaQueEntry 1 }

ibSlaQueMode OBJECT-TYPE
    SYNTAX      INTEGER
        {
            sp(0),
            wrr(1)
        }
    MAX-ACCESS  read-create
    STATUS      current
    DESCRIPTION
        "
        Service SLA queue mode.
        "
    ::= { ibOnuServiceSlaQueEntry 2 }

ibSlaQueWeight OBJECT-TYPE
    SYNTAX      Integer32(0..100)
    MAX-ACCESS  read-create
    STATUS      current
    DESCRIPTION
        "
        Service SLA queue weight in WRR mode.
        "
    ::= { ibOnuServiceSlaQueEntry 3 }

ibSlaQueFixPktSize OBJECT-TYPE
    SYNTAX      Integer32(0..2000)
    UNITS       "bytes"
    MAX-ACCESS  read-create
    STATUS      current
    DESCRIPTION
        "
        Service SLA queue fixed packet size in bytes.
        "
    DEFVAL { 0 }
    ::= { ibOnuServiceSlaQueEntry 4 }

ibSlaQueFixBandwidth OBJECT-TYPE
    SYNTAX      Integer32
    UNITS       "kbps"
    MAX-ACCESS  read-create
    STATUS      current
    DESCRIPTION
        "
        Service SLA queue fixed bandwidth in kbps,
        which will be rounded down to the nearest multiple of 256.
        "
    ::= { ibOnuServiceSlaQueEntry 5 }

ibSlaQueGuaBandwidth OBJECT-TYPE
    SYNTAX      Integer32
    UNITS       "kbps"
    MAX-ACCESS  read-create
    STATUS      current
    DESCRIPTION
        "
        Service SLA queue guaranteed bandwidth in kbps,
        which will be rounded down to the nearest multiple of 256.
        "
    ::= { ibOnuServiceSlaQueEntry 6 }

ibSlaQueBstBandwidth OBJECT-TYPE
    SYNTAX      Integer32
    UNITS       "kbps"
    MAX-ACCESS  read-create
    STATUS      current
    DESCRIPTION
        "
        Service SLA queue best effort bandwidth in kbps,
        which will be rounded down to the nearest multiple of 256.
        "
    ::= { ibOnuServiceSlaQueEntry 7 }

ibSlaQueRowStatus OBJECT-TYPE
    SYNTAX      RowStatus
    MAX-ACCESS  read-create
    STATUS      current
    DESCRIPTION
        "
        The status of this table entry. Only active,
        createAndGo, and destroy are supported.
        "
    ::= { ibOnuServiceSlaQueEntry 8 }

--
-- ibOnuPoeTable
--

ibOnuPoeTable OBJECT-TYPE
    SYNTAX      SEQUENCE OF IbOnuPoeEntry
    MAX-ACCESS  not-accessible
    STATUS      current
    DESCRIPTION
        "
        This table is used for configuring the PoE function for ONUs.
        "
    ::= { ibEponOnuMan 44 }

ibOnuPoeEntry OBJECT-TYPE
    SYNTAX      IbOnuPoeEntry
    MAX-ACCESS  not-accessible
    STATUS      current
    DESCRIPTION
        "
        The entry of the ibOnuPoeTable.
        "
    INDEX
        {
            ifIndex
        }
    ::= { ibOnuPoeTable 1 }

IbOnuPoeEntry ::= SEQUENCE
    {
        ibOnuPoeEnable            TruthValue,
        ibOnuPoeMode              INTEGER,
        ibOnuPoeMaxPowerClass     INTEGER,
        ibOnuPoeMaxPowerValue     Integer32,
        ibOnuPoeLegacyEnable      TruthValue
    }

ibOnuPoeEnable OBJECT-TYPE
    SYNTAX      TruthValue
    MAX-ACCESS  read-write
    STATUS      current
    DESCRIPTION
        "
        Enable PoE for an ONU.
        "
    DEFVAL { true }
    ::= { ibOnuPoeEntry 1 }

ibOnuPoeMode OBJECT-TYPE
    SYNTAX      INTEGER
        {
            signal(0),
            spare(1)
        }
    MAX-ACCESS  read-write
    STATUS      current
    DESCRIPTION
        "
        Set the PoE mode for an ONU.
        "
    DEFVAL { 0 }
    ::= { ibOnuPoeEntry 2 }

ibOnuPoeMaxPowerClass OBJECT-TYPE
    SYNTAX      INTEGER
        {
            default(0),
            class0(1),
            class1(2),
            class2(3),
            class3(4),
            class4(5),
            undefined(255)
        }
    MAX-ACCESS  read-write
    STATUS      current
    DESCRIPTION
        "
        Set the PoE max power class for an ONU.
        "
    DEFVAL { 0 }
    ::= { ibOnuPoeEntry 3 }

ibOnuPoeMaxPowerValue OBJECT-TYPE
    SYNTAX      Integer32
    UNITS       "mW"
    MAX-ACCESS  read-write
    STATUS      current
    DESCRIPTION
        "
        Set the PoE max power value for an ONU.
        "
    DEFVAL { 0 }
    ::= { ibOnuPoeEntry 4 }

ibOnuPoeLegacyEnable OBJECT-TYPE
    SYNTAX      TruthValue
    MAX-ACCESS  read-write
    STATUS      current
    DESCRIPTION
        "
        Enable the PoE legacy PD detection for an ONU.
        "
    ::= { ibOnuPoeEntry 5 }

--
-- ibEponBatchOperationBySlotTable
--

ibEponBatchOperationBySlotTable OBJECT-TYPE
    SYNTAX      SEQUENCE OF IbEponBatchOperationBySlotEntry
    MAX-ACCESS  not-accessible
    STATUS      current
    DESCRIPTION
        "
        This table is used for batch operation by slot.
        "
    ::= { ibEponBatchOperationMan 1 }

ibEponBatchOperationBySlotEntry OBJECT-TYPE
    SYNTAX      IbEponBatchOperationBySlotEntry
    MAX-ACCESS  not-accessible
    STATUS      current
    DESCRIPTION
        "
        The entry of the ibEponBatchOperationBySlotTable.
        "
    INDEX
        {
            ibEponBatchOperationBySlotIndex
        }
    ::= { ibEponBatchOperationBySlotTable 1 }

IbEponBatchOperationBySlotEntry ::= SEQUENCE
    {
        ibEponBatchOperationBySlotIndex     Integer32,
        ibEponBatchOperationBySlotType      INTEGER,
        ibEponBatchOperationBySlot          INTEGER,
        ibEponBatchOperationBySlotResult    Integer32,
        ibEponBatchOpBySlotBindType         BITS
    }

ibEponBatchOperationBySlotIndex OBJECT-TYPE
    SYNTAX      Integer32
    MAX-ACCESS  not-accessible
    STATUS      current
    DESCRIPTION
        "
        The EPON board index.
        "
    ::= { ibEponBatchOperationBySlotEntry 1 }

ibEponBatchOperationBySlotType OBJECT-TYPE
    SYNTAX      INTEGER
        {
            resetUnknown(1),
            updateDba(9),
            updateONU(10)
        }
    MAX-ACCESS  read-write
    STATUS      current
    DESCRIPTION
        "
        The types of batch operation by slot:
        1  - resetUnknown, the object value is not set.
        9  - updateDba, update OLT DBA algorithm.
        Config the MIB object module ibEponDbaUpdateFileName.
        10 - updateONU, update ONU firmware.
        Config the MIB object module ibEponOnuUpdateFileName
        with the filename of ONU firmware first.
        "
    ::= { ibEponBatchOperationBySlotEntry 2 }

ibEponBatchOperationBySlot OBJECT-TYPE
    SYNTAX      INTEGER
        {
            batOpBySlot(1)
        }
    MAX-ACCESS  read-write
    STATUS      current
    DESCRIPTION
        "
        Execute batch operation.
        "
    ::= { ibEponBatchOperationBySlotEntry 3 }

ibEponBatchOperationBySlotResult OBJECT-TYPE
    SYNTAX      Integer32
    MAX-ACCESS  read-only
    STATUS      current
    DESCRIPTION
        "
        The result of batch operation.
        0xFFFF - other, general error.
        1 - working, operation is not completed.
        2 - successful, completed successfully.
        3 - failed because the DBA source file does not exist.
        4 - failed because the ONU firmware file does not exist.
        5 - failed because of not set the filename of DBA source.
        6 - failed because of not set the filename of ONU firmware.
        7 - failed because of not set slottype.
        "
    ::= { ibEponBatchOperationBySlotEntry 4 }

ibEponBatchOpBySlotBindType OBJECT-TYPE
    SYNTAX      BITS
        {
            mac(0),
            loid(1),
            loidPassword(2)
        }
    MAX-ACCESS  read-write
    STATUS      current
    DESCRIPTION
        "
        Set batch binding type, which can only be assigned one type.
        "
    ::= { ibEponBatchOperationBySlotEntry 5 }

--
-- ibEponBatchOperationByOLTTable
--

ibEponBatchOperationByOLTTable OBJECT-TYPE
    SYNTAX      SEQUENCE OF IbEponBatchOperationByOLTEntry
    MAX-ACCESS  not-accessible
    STATUS      current
    DESCRIPTION
        "
        This table is used for batch operation by OLT.
        "
    ::= { ibEponBatchOperationMan 2 }

ibEponBatchOperationByOLTEntry OBJECT-TYPE
    SYNTAX      IbEponBatchOperationByOLTEntry
    MAX-ACCESS  not-accessible
    STATUS      current
    DESCRIPTION
        "
        The entry of the ibEponBatchOperationByOLTTable.
        "
    INDEX
        {
            ifIndex
        }
    ::= { ibEponBatchOperationByOLTTable 1 }

IbEponBatchOperationByOLTEntry ::= SEQUENCE
    {
        ibEponBatchOperationByOLTType      INTEGER,
        ibEponBatchOperationByOLT          INTEGER,
        ibEponBatchOperationByOLTResult    Integer32
    }

ibEponBatchOperationByOLTType OBJECT-TYPE
    SYNTAX      INTEGER
        {
            resetUnknown(1),
            updateONU(5)
        }
    MAX-ACCESS  read-write
    STATUS      current
    DESCRIPTION
        "
        The types of batch operation by OLT(operation for all ONUs in the
        OLT):
        1 -- resetUnknown, the object value is not set.
        5 -- updateONU, update ONU firmware.
        configure the MIB object module ibEponOnuUpdateFileName
        with the filename of ONU firmware first.
        "
    ::= { ibEponBatchOperationByOLTEntry 1 }

ibEponBatchOperationByOLT OBJECT-TYPE
    SYNTAX      INTEGER
        {
            batOpByOlt(1)
        }
    MAX-ACCESS  read-write
    STATUS      current
    DESCRIPTION
        "
        Execute batch operation.
        "
    ::= { ibEponBatchOperationByOLTEntry 2 }

ibEponBatchOperationByOLTResult OBJECT-TYPE
    SYNTAX      Integer32
    MAX-ACCESS  read-only
    STATUS      current
    DESCRIPTION
        "
        The result of batch operation:
        0xFFFF -- other, general error.
        1 -- working, operation is not completed.
        2 -- successful, operation completed successfully.
        4 -- failed because the ONU firmware file does not exist.
        6 -- failed because of not set the filename of ONU firmware.
        7 -- failed because of not set olttype.
        "
    ::= { ibEponBatchOperationByOLTEntry 3 }

--
-- ibOnuFirmwareUpdateByTypeTable
--

ibOnuFirmwareUpdateByTypeTable OBJECT-TYPE
    SYNTAX      SEQUENCE OF IbOnuFirmwareUpdateByTypeEntry
    MAX-ACCESS  not-accessible
    STATUS      current
    DESCRIPTION
        "
        This table is used to update ONU by ONU type.
        "
    ::= { ibEponBatchOperationMan 3 }

ibOnuFirmwareUpdateByTypeEntry OBJECT-TYPE
    SYNTAX      IbOnuFirmwareUpdateByTypeEntry
    MAX-ACCESS  not-accessible
    STATUS      current
    DESCRIPTION
        "
        The entry of the ibOnuFirmwareUpdateByTypeTable.
        "
    INDEX
        {
            ibOnuUpdateByOnuTypeIndex
        }
    ::= { ibOnuFirmwareUpdateByTypeTable 1 }

IbOnuFirmwareUpdateByTypeEntry ::= SEQUENCE
    {
        ibOnuUpdateByOnuTypeIndex     Integer32,
        ibOnuUpdateByTypeOnuType      OCTET STRING,
        ibOnuUpdateByTypeFileName     OCTET STRING,
        ibOnuUpdateByTypeRowStatus    RowStatus,
        ibOnuUpdateByTypeProtType     INTEGER,
        ibOnuUpdateByTypeStartTime    OCTET STRING,
        ibOnuUpdateByTypeDuration     Integer32
    }

ibOnuUpdateByOnuTypeIndex OBJECT-TYPE
    SYNTAX      Integer32
    MAX-ACCESS  not-accessible
    STATUS      current
    DESCRIPTION
        "
        The type and file relationship table entry index.
        "
    ::= { ibOnuFirmwareUpdateByTypeEntry 1 }

ibOnuUpdateByTypeOnuType OBJECT-TYPE
    SYNTAX      OCTET STRING(SIZE(0..15))
    MAX-ACCESS  read-create
    STATUS      current
    DESCRIPTION
        "
        The type of ONUs.
        "
    ::= { ibOnuFirmwareUpdateByTypeEntry 2 }

ibOnuUpdateByTypeFileName OBJECT-TYPE
    SYNTAX      OCTET STRING(SIZE(0..255))
    MAX-ACCESS  read-create
    STATUS      current
    DESCRIPTION
        "
        The file to be updated for the type of ONUs.
        "
    ::= { ibOnuFirmwareUpdateByTypeEntry 3 }

ibOnuUpdateByTypeRowStatus OBJECT-TYPE
    SYNTAX      RowStatus
    MAX-ACCESS  read-create
    STATUS      current
    DESCRIPTION
        "
        The status of this table entry.
        Only createAndGo and destroy actions are supported.
        "
    ::= { ibOnuFirmwareUpdateByTypeEntry 4 }

ibOnuUpdateByTypeProtType OBJECT-TYPE
    SYNTAX      INTEGER
        {
            private(0),
            ctc(1)
        }
    MAX-ACCESS  read-write
    STATUS      current
    DESCRIPTION
        "
        private(0): Using private protocol to update the ONU firmware.
        ctc(1): Using ctc standard protocol to update the ONU firmware.
        "
    DEFVAL { private }
    ::= { ibOnuFirmwareUpdateByTypeEntry 5 }

ibOnuUpdateByTypeStartTime OBJECT-TYPE
    SYNTAX      OCTET STRING(SIZE(0..5))
    MAX-ACCESS  read-write
    STATUS      current
    DESCRIPTION
        "
        The start time of the ONU update every day.
        Using HH:MM as format.
        "
    ::= { ibOnuFirmwareUpdateByTypeEntry 6 }

ibOnuUpdateByTypeDuration OBJECT-TYPE
    SYNTAX      Integer32(0..1439)
    MAX-ACCESS  read-write
    STATUS      current
    DESCRIPTION
        "
        The duration of the ONU update.
        "
    DEFVAL { 0 }
    ::= { ibOnuFirmwareUpdateByTypeEntry 7 }

ibEponErrorInfo OBJECT IDENTIFIER ::= { ibEponMibObjects 7 }

ibEponSoftwareErrorCode OBJECT-TYPE
    SYNTAX      Integer32
    MAX-ACCESS  accessible-for-notify
    STATUS      current
    DESCRIPTION
        "
        OLT software error code.
        "
    ::= { ibEponErrorInfo 1 }

ibOamVendorSpecificAlarmCode OBJECT-TYPE
    SYNTAX      Integer32
    MAX-ACCESS  accessible-for-notify
    STATUS      current
    DESCRIPTION
        "
        Alarm code of the vendor.
        "
    ::= { ibEponErrorInfo 2 }

ibEponOnuRegErrorMacAddr OBJECT-TYPE
    SYNTAX      OCTET STRING
    MAX-ACCESS  accessible-for-notify
    STATUS      current
    DESCRIPTION
        "
        The MAC of ONU registered error.
        "
    ::= { ibEponErrorInfo 3 }

ibOamEventLogType OBJECT-TYPE
    SYNTAX      Unsigned32
    MAX-ACCESS  accessible-for-notify
    STATUS      current
    DESCRIPTION
        "
        The type of event that generated this entry in the event log.
        "
    ::= { ibEponErrorInfo 4 }

ibOamEventLogLocation OBJECT-TYPE
    SYNTAX      INTEGER{local(1),remote(2)}
    MAX-ACCESS  accessible-for-notify
    STATUS      current
    DESCRIPTION
        "
        Whether this event occurred locally, or was received from the
        OAM peer via Ethernet OAM.
        "
    ::= { ibEponErrorInfo 5 }

ibEponLoopbackPortIndex OBJECT-TYPE
    SYNTAX      Integer32
    MAX-ACCESS  accessible-for-notify
    STATUS      current
    DESCRIPTION
        "
        The index of port which generate loop back event.
        "
    ::= { ibEponErrorInfo 6 }

ibEponLoopbackPortDescr OBJECT-TYPE
    SYNTAX      OCTET STRING(SIZE(0..255))
    MAX-ACCESS  accessible-for-notify
    STATUS      current
    DESCRIPTION
        "
        A textual string containing information about the
        port generated loop back event.
        "
    ::= { ibEponErrorInfo 7 }

ibOltPortAlarmLlidMisFrames OBJECT-TYPE
    SYNTAX      Unsigned32
    MAX-ACCESS  accessible-for-notify
    STATUS      current
    DESCRIPTION
        "
        the amount of mismatched frames about the LLID mismatch alarm.
        "
    ::= { ibEponErrorInfo 8 }

ibOltPortAlarmBer OBJECT-TYPE
    SYNTAX      Unsigned32
    MAX-ACCESS  accessible-for-notify
    STATUS      current
    DESCRIPTION
        "
        error bit rate.
        "
    ::= { ibEponErrorInfo 9 }

ibOltPortAlarmFer OBJECT-TYPE
    SYNTAX      Unsigned32
    MAX-ACCESS  accessible-for-notify
    STATUS      current
    DESCRIPTION
        "
        error frames rate.
        "
    ::= { ibEponErrorInfo 10 }

ibEponOnuRegSilentMac OBJECT-TYPE
    SYNTAX      OCTET STRING
    MAX-ACCESS  accessible-for-notify
    STATUS      current
    DESCRIPTION
        "
        The MAC of silent ONU.
        "
    ::= { ibEponErrorInfo 11 }

ibEponOperationResult OBJECT-TYPE
    SYNTAX      OCTET STRING(SIZE(0..255))
    MAX-ACCESS  accessible-for-notify
    STATUS      current
    DESCRIPTION
        "
        The result of EPON operation.
        "
    ::= { ibEponErrorInfo 12 }

ibEponOnuLaserState OBJECT-TYPE
    SYNTAX      INTEGER
    {
        normal(1),
        laserAlwaysOn(2),
        signalDegradation(3),
        endOfLife(4)
    }
    MAX-ACCESS  accessible-for-notify
    STATUS      current
    DESCRIPTION
        "
        The state of ONU laser.
        "
    ::= { ibEponErrorInfo 13 }

ibEponOnuRegSilentBindType OBJECT-TYPE
    SYNTAX      BITS
        {
            mac(0),
            loid(1),
            loidPassword(2)
        }
    MAX-ACCESS  accessible-for-notify
    STATUS      current
    DESCRIPTION
        "
        The binding type of a silent ONU.
        "
    ::= { ibEponErrorInfo 14 }

ibEponOnuRegSilentLoid OBJECT-TYPE
    SYNTAX      OCTET STRING
    MAX-ACCESS  accessible-for-notify
    STATUS      current
    DESCRIPTION
        "
        The LOID of a silent ONU.
        "
    ::= { ibEponErrorInfo 15 }

ibEponOnuRegSilentLoidPwd OBJECT-TYPE
    SYNTAX      OCTET STRING
    MAX-ACCESS  accessible-for-notify
    STATUS      current
    DESCRIPTION
        "
        The LOID's password of a silent ONU.
        A zero-length string will be returned when reading.
        "
    ::= { ibEponErrorInfo 16 }

ibEponOnuRegErrorLoid OBJECT-TYPE
    SYNTAX      OCTET STRING
    MAX-ACCESS  accessible-for-notify
    STATUS      current
    DESCRIPTION
        "
        The LOID of an ONU with registration error.
        "
    ::= { ibEponErrorInfo 17 }

ibEponOnuRegErrorLoidCode OBJECT-TYPE
    SYNTAX      INTEGER
    {
        loidNotExist(1),
        wrongPassword(2),
        conflictLoid(3),
        notSupport(4),
        mismatch(5)
    }
    MAX-ACCESS  accessible-for-notify
    STATUS      current
    DESCRIPTION
        "
        The reason of ONU registration failure.
        "
    ::= { ibEponErrorInfo 18 }

--
-- ibEpon NOTIFICATION
--

ibEponTrap OBJECT IDENTIFIER ::= { ibEponMibObjects 8 }

ibEponTrapPrefix OBJECT IDENTIFIER ::= { ibEponTrap 0 }

ibEponPortAlarmBerTrap NOTIFICATION-TYPE
    OBJECTS
        {
            ifIndex,
            ifDescr,
            ibOltPortAlarmBerDirect,
            ibOltPortAlarmBer,
            ibOltPortAlarmBerThreshold
        }
    STATUS      current
    DESCRIPTION
        "
        A ibEponPortAlarmBerTrap notification is sent when
        a BER threshold crossing event is detected.
        "
    ::= { ibEponTrapPrefix 1 }

ibEponPortAlarmFerTrap NOTIFICATION-TYPE
    OBJECTS
        {
            ifIndex,
            ifDescr,
            ibOltPortAlarmFerDirect,
            ibOltPortAlarmFer,
            ibOltPortAlarmFerThreshold
        }
    STATUS      current
    DESCRIPTION
        "
        A ibEponPortAlarmFerTrap notification is sent when
        a frame error rate threshold crossing event is detected.
        "
    ::= { ibEponTrapPrefix 2 }

ibEponErrorLLIDFrameTrap NOTIFICATION-TYPE
    OBJECTS
        {
            ifIndex,
            ifDescr,
            ibOltPortAlarmLlidMisFrames,
            ibOltPortAlarmLlidMismatchThreshold
        }
    STATUS      current
    DESCRIPTION
        "
        A ibEponErrorLLIDFrameTrap notification is sent when a
        LLID mismatched frames rate threshold crossing event is detected.
        "
    ::= { ibEponTrapPrefix 3 }

ibEponLoopBackEnableTrap NOTIFICATION-TYPE
    OBJECTS
        {
            ifIndex,
            ifDescr,
            ibEponLoopbackPortIndex,
            ibEponLoopbackPortDescr
        }
    STATUS      current
    DESCRIPTION
        "
        A ibEponLoopBackEnableTrap notification is sent when
        the loop back command is committed.
        "
    ::= { ibEponTrapPrefix 4 }

ibEponOnuRegistrationErrTrap NOTIFICATION-TYPE
    OBJECTS
        {
            ifIndex,
            ifDescr,
            ibEponOnuRegErrorMacAddr
        }
    STATUS      current
    DESCRIPTION
        "
        A ibEponOnuRegistrationErrTrap notification is sent when a
        ONU register failed.
        "
    ::= { ibEponTrapPrefix 5 }

ibEponOamDisconnectionTrap NOTIFICATION-TYPE
    OBJECTS
        {
            ifIndex,
            ifDescr
        }
    STATUS      current
    DESCRIPTION
        "
        A ibEponOamDisconnectionTrap notification is sent when
        LLID's OAM link is disconnected.
        "
    ::= { ibEponTrapPrefix 6 }

ibEponEncryptionKeyErrTrap NOTIFICATION-TYPE
    OBJECTS
        {
            ifIndex,
            ifDescr
        }
    STATUS      current
    DESCRIPTION
        "
        A ibEponEncryptionKeyErrTrap notification is sent when
        LLID's encryption key is bad.
        "
    ::= { ibEponTrapPrefix 7 }

ibEponRemoteStableTrap NOTIFICATION-TYPE
    OBJECTS
        {
            ifIndex,
            ifDescr
        }
    STATUS      current
    DESCRIPTION
        "
        A ibEponRemoteStableTrap notification is sent when
        remote Data Terminal Equipment(DTE) has not seen or
        is unsatisfied with local state information.
        "
    ::= { ibEponTrapPrefix 8 }

ibEponLocalStableTrap NOTIFICATION-TYPE
    OBJECTS
        {
            ifIndex,
            ifDescr
        }
    STATUS      current
    DESCRIPTION
        "
        A ibEponLocalStableTrap notification is sent when
        DTE has not seen or is unsatisfied with remote state
        information.
        "
    ::= { ibEponTrapPrefix 9 }

ibEponOamVendorSpecificTrap NOTIFICATION-TYPE
    OBJECTS
        {
            ifIndex,
            ifDescr,
            ibOamVendorSpecificAlarmCode
        }
    STATUS      current
    DESCRIPTION
        "
        A ibEponOamVendorSpecificTrap notification is sent when
        system vendor specific OAM alarm raised.
        "
    ::= { ibEponTrapPrefix 10 }

ibEponSoftwareErrTrap NOTIFICATION-TYPE
    OBJECTS
        {
            ibLswFrameIndex,
            ibLswSlotIndex,
            ibEponSoftwareErrorCode
        }
    STATUS      current
    DESCRIPTION
        "
        A ibEponSoftwareErrTrap notification is sent when
        a PAS-SOFT internal error occurs.
        "
    ::= { ibEponTrapPrefix 11 }

ibEponPortAlarmBerRecoverTrap NOTIFICATION-TYPE
    OBJECTS
        {
            ifIndex,
            ifDescr,
            ibOltPortAlarmBerDirect
        }
    STATUS      current
    DESCRIPTION
        "
        A ibEponPortAlarmBerRecoverTrap notification is sent when
        a BER threshold crossing event is detected and then recovered.
        "
    ::= { ibEponTrapPrefix 12 }

ibEponPortAlarmFerRecoverTrap NOTIFICATION-TYPE
    OBJECTS
        {
            ifIndex,
            ifDescr,
            ibOltPortAlarmFerDirect
        }
    STATUS      current
    DESCRIPTION
        "
        A ibEponPortAlarmFerRecoverTrap notification is sent when
        a frame error rate threshold crossing event is detected and then
        recovered.
        "
    ::= { ibEponTrapPrefix 13 }

ibEponErrorLLIDFrameRecoverTrap NOTIFICATION-TYPE
    OBJECTS
        {
            ifIndex,
            ifDescr
        }
    STATUS      current
    DESCRIPTION
        "
        A ibEponErrorLLIDFrameRecoverTrap notification is sent when a
        LLID mismatched frames rate threshold crossing event is detected
        and then recovered.
        "
    ::= { ibEponTrapPrefix 14 }

ibEponLoopBackEnableRecoverTrap NOTIFICATION-TYPE
    OBJECTS
        {
            ifIndex,
            ifDescr
        }
    STATUS      current
    DESCRIPTION
        "
        A ibEponLoopBackEnableRecoverTrap notification is sent when
        the loop back is detected and then recovered.
        "
    ::= { ibEponTrapPrefix 15 }

ibEponOnuRegistrationErrRecoverTrap NOTIFICATION-TYPE
    OBJECTS
        {
            ifIndex,
            ifDescr,
            ibEponOnuRegErrorMacAddr
        }
    STATUS      current
    DESCRIPTION
        "
        A ibEponOnuRegistrationErrRecoverTrap notification is sent when an
        ONU register failed and then register successful again.
        "
    ::= { ibEponTrapPrefix 16 }

ibEponOamDisconnectionRecoverTrap NOTIFICATION-TYPE
    OBJECTS
        {
            ifIndex,
            ifDescr
        }
    STATUS      current
    DESCRIPTION
        "
        A ibEponOamDisconnectionRecoverTrap notification is sent when
        LLID's OAM link is disconnected and then connected.
        "
    ::= { ibEponTrapPrefix 17 }

ibEponEncryptionKeyErrRecoverTrap NOTIFICATION-TYPE
    OBJECTS
        {
            ifIndex,
            ifDescr
        }
    STATUS      current
    DESCRIPTION
        "
        A ibEponEncryptionKeyErrRecoverTrap notification is sent when
        LLID's encryption key is bad and then right.
        "
    ::= { ibEponTrapPrefix 18 }

ibEponRemoteStableRecoverTrap NOTIFICATION-TYPE
    OBJECTS
        {
            ifIndex,
            ifDescr
        }
    STATUS      current
    DESCRIPTION
        "
        A ibEponRemoteStableRecoverTrap notification is sent when
        remote DTE has not seen or is unsatisfied with local
        state information and then is realized.
        "
    ::= { ibEponTrapPrefix 19 }

ibEponLocalStableRecoverTrap NOTIFICATION-TYPE
    OBJECTS
        {
            ifIndex,
            ifDescr
        }
    STATUS      current
    DESCRIPTION
        "
        A ibEponLocalStableRecoverTrap notification is sent when
        DTE has not seen or is unsatisfied with remote state
        information and then is realized.
        "
    ::= { ibEponTrapPrefix 20 }

ibEponOamVendorSpecificRecoverTrap NOTIFICATION-TYPE
    OBJECTS
        {
            ifIndex,
            ifDescr,
            ibOamVendorSpecificAlarmCode
        }
    STATUS      current
    DESCRIPTION
        "
        A ibEponOamVendorSpecificRecoverTrap notification is sent when
        system vendor specific OAM alarm is detected and then recovered.
        "
    ::= { ibEponTrapPrefix 21 }

ibEponSoftwareErrRecoverTrap NOTIFICATION-TYPE
    OBJECTS
        {
            ibLswFrameIndex,
            ibLswSlotIndex,
            ibEponSoftwareErrorCode
        }
    STATUS      current
    DESCRIPTION
        "
        A ibEponSoftwareErrRecoverTrap notification is sent when
        a PAS-SOFT internal error is detected and then recovered.
        "
    ::= { ibEponTrapPrefix 22 }

ibDot3OamThresholdRecoverEvent NOTIFICATION-TYPE
    OBJECTS
        {
            ifIndex,
            ibOamEventLogType,
            ibOamEventLogLocation
        }
    STATUS      current
    DESCRIPTION
        "
        A ibDot3OamThresholdRecoverEvent notification is sent when
        ibDot3OamThresholdEvent is detected and then recovered.
        "
    ::= { ibEponTrapPrefix 23 }


ibDot3OamNonThresholdRecoverEvent NOTIFICATION-TYPE
    OBJECTS
        {
            ifIndex,
            ibOamEventLogType,
            ibOamEventLogLocation
        }
    STATUS      current
    DESCRIPTION
        "
        A ibDot3OamNonThresholdRecoverEvent notification is sent when
        ibDot3OamNonThresholdEvent is detected and then recovered.
        "
    ::= { ibEponTrapPrefix 24 }

ibEponOnuRegExcessTrap NOTIFICATION-TYPE
    OBJECTS
        {
            ifIndex,
            ifDescr
        }
    STATUS      current
    DESCRIPTION
        "
        A ibEponOnuRegExcessTrap notification is sent when the
        number of registered ONUs exceeds the limit.
        "
    ::= { ibEponTrapPrefix 25 }

ibEponOnuRegExcessRecoverTrap NOTIFICATION-TYPE
    OBJECTS
        {
            ifIndex,
            ifDescr
        }
    STATUS      current
    DESCRIPTION
        "
        A ibEponOnuRegExcessRecoverTrap notification is sent when
        ibEponOnuRegExcessTrap is detected and then recovered.
        "
    ::= { ibEponTrapPrefix 26 }

ibEponOnuPowerOffTrap NOTIFICATION-TYPE
    OBJECTS
        {
            ifIndex,
            ifDescr
        }
    STATUS      current
    DESCRIPTION
        "
        A ibEponOnuPowerOffTrap notification is sent when ONU is power off.
        "
    ::= { ibEponTrapPrefix 27 }

ibEponOltSwitchoverTrap NOTIFICATION-TYPE
    OBJECTS
        {
            ifIndex,
            ifDescr
        }
    STATUS      current
    DESCRIPTION
        "
        A ibEponOltSwithoverTrap notification is sent when OLT switchover
        is detected.
        "
    ::= { ibEponTrapPrefix 28 }

ibEponOltDFETrap NOTIFICATION-TYPE
    OBJECTS
        {
            ifIndex,
            ifDescr
        }
    STATUS      current
    DESCRIPTION
        "
        A ibEponOltDFETrap notification is sent when there was
        a serious problem(device fatal error) on OLT.
        "
    ::= { ibEponTrapPrefix 29 }

ibEponOltDFERecoverTrap NOTIFICATION-TYPE
    OBJECTS
        {
            ifIndex,
            ifDescr
        }
    STATUS      current
    DESCRIPTION
        "
        A ibEponOltDFERecoverTrap notification is sent when
        device fatal error is detected and then recovered.
        "
    ::= { ibEponTrapPrefix 30 }

ibEponOnuSilenceTrap NOTIFICATION-TYPE
    OBJECTS
        {
            ifIndex,
            ifDescr,
            ibEponOnuRegSilentMac
        }
    STATUS      current
    DESCRIPTION
        "
        The ibEponOnuSilenceTrap notification is sent when an
        unbound ONU try to register to an OLT.
        "
    ::= { ibEponTrapPrefix 31 }

ibEponOnuSilenceRecoverTrap NOTIFICATION-TYPE
    OBJECTS
        {
            ifIndex,
            ifDescr,
            ibEponOnuRegSilentMac
        }
    STATUS      current
    DESCRIPTION
        "
        The ibEponOnuSilenceRecoverTrap notification is sent when
        a silent ONU is bound in the OLT or the aging onu mac
        address is timeout.
        "
    ::= { ibEponTrapPrefix 32 }

ibEponOnuUpdateResultTrap NOTIFICATION-TYPE
    OBJECTS
        {
            ifIndex,
            ifDescr,
            ibOnuBindMacAddress,
            ibOnuUpdateResult,
            ibOnuRegType,
            ibOnuUpdateFileName
        }
    STATUS      current
    DESCRIPTION
        "
        A ibEponUpdateResultTrap notification is sent when
        an ONU reported its firmware update result.
        "
    ::= { ibEponTrapPrefix 33 }

ibEponOnuAutoBindTrap NOTIFICATION-TYPE
    OBJECTS
        {
            ifIndex,
            ifDescr,
            ibOnuBindMacAddress,
            ibEponOperationResult
        }
    STATUS      current
    DESCRIPTION
        "
        A ibEponOnuAutoBindTrap notification is sent
        when a silent ONU is bound automatically.
        "
    ::= { ibEponTrapPrefix 34 }

ibEponOnuPortStpStateTrap NOTIFICATION-TYPE
    OBJECTS
        {
            ifIndex,
            ifDescr,
            ibEponStpPortIndex,
            ibEponStpPortDescr,
            ibEponStpPortState
        }
    STATUS      current
    DESCRIPTION
        "
        A ibEponOnuPortStpStateTrap notification is sent when
        a port turns into another state in STP environment.
        "
    ::= { ibEponTrapPrefix 35 }

ibEponOnuLaserFailedTrap NOTIFICATION-TYPE
    OBJECTS
        {
            ifIndex,
            ifDescr,
            ibEponOnuLaserState
        }
    STATUS      current
    DESCRIPTION
        "
        A ibEponOnuLaserFailedTrap notification is sent when
        an ONU has trouble with laser, such as laser constantly turned on,
        signal degradation or optics EOL (End of Life).
        "
    ::= { ibEponTrapPrefix 36 }

ibOnuSmlkSwitchoverTrap NOTIFICATION-TYPE
    OBJECTS
        {
            ifIndex,
            ifDescr,
            ibOnuSmlkGroupID,
            ibOnuSmlkFirstPonStatus,
            ibOnuSmlkSecondPonStatus
        }
    STATUS      current
    DESCRIPTION
        "
        A ibOnuSmlkSwitchoverTrap notification is sent when
        an ONU SMLK switchover is detected.
        "
    ::= { ibEponTrapPrefix 37 }

ibEponOnuRegLoidErrTrap NOTIFICATION-TYPE
    OBJECTS
        {
            ifIndex,
            ifDescr,
            ibEponOnuRegErrorLoid,
            ibEponOnuRegErrorLoidCode
        }
    STATUS      current
    DESCRIPTION
        "
        A ibEponOnuRegLoidErrTrap notification is sent when an
        ONU failed to register identified by LOID.
        "
    ::= { ibEponTrapPrefix 38 }

ibEponOnuRegLoidErrRecTrap NOTIFICATION-TYPE
    OBJECTS
        {
            ifIndex,
            ifDescr,
            ibEponOnuRegErrorLoid,
            ibEponOnuRegErrorLoidCode
        }
    STATUS      current
    DESCRIPTION
        "
        A ibEponOnuRegLoidErrRecTrap notification is sent when an
        ONU failed to register and then registered successful again identified by LOID.
        "
    ::= { ibEponTrapPrefix 39 }

ibEponOnuSilenceLoidTrap NOTIFICATION-TYPE
    OBJECTS
        {
            ifIndex,
            ifDescr,
            ibEponOnuRegSilentBindType,
            ibEponOnuRegSilentMac,
            ibEponOnuRegSilentLoid,
            ibEponOnuRegSilentLoidPwd
        }
    STATUS      current
    DESCRIPTION
        "
        The ibEponOnuSilenceLoidTrap notification is sent when an
        unbound ONU try to register to an OLT identified by LOID.
        "
    ::= { ibEponTrapPrefix 40 }

ibEponOnuSilenceLoidRecTrap NOTIFICATION-TYPE
    OBJECTS
        {
            ifIndex,
            ifDescr,
            ibEponOnuRegSilentBindType,
            ibEponOnuRegSilentMac,
            ibEponOnuRegSilentLoid,
            ibEponOnuRegSilentLoidPwd
        }
    STATUS      current
    DESCRIPTION
        "
        The ibEponOnuSilenceLoidRecTrap notification is sent when
        a silent ONU is bound in the OLT or the aging ONU MAC
        address times out identified by LOID.
        "
    ::= { ibEponTrapPrefix 41 }

ibEponOnuUpdateLoidRetTrap NOTIFICATION-TYPE
    OBJECTS
        {
            ifIndex,
            ifDescr,
            ibOnuBindLoid,
            ibOnuUpdateResult,
            ibOnuRegType,
            ibOnuUpdateFileName
        }
    STATUS      current
    DESCRIPTION
        "
        A ibEponOnuUpdateLoidRetTrap notification is sent when
        an ONU reported its firmware update result identified by LOID.
        "
    ::= { ibEponTrapPrefix 42 }

ibEponOnuAutoBindLoidTrap NOTIFICATION-TYPE
    OBJECTS
        {
            ifIndex,
            ifDescr,
            ibOnuBindLoid,
            ibEponOperationResult
        }
    STATUS      current
    DESCRIPTION
        "
        A ibEponOnuAutoBindLoidTrap notification is sent
        when a silent ONU is bound automatically identified by LOID.
        "
    ::= { ibEponTrapPrefix 43 }

ibEponOnuPowerOnTrap NOTIFICATION-TYPE
    OBJECTS
        {
            ifIndex,
            ifDescr
        }
    STATUS      current
    DESCRIPTION
        "
        A ibEponOnuPowerOffTrap notification is sent when ONU is powered on.
        "
    ::= { ibEponTrapPrefix 44 }

ibEponOpticalSignalLosTrap NOTIFICATION-TYPE
    OBJECTS
        {
            ifIndex,
            ifDescr
        }
    STATUS      current
    DESCRIPTION
        "
        A ibEponOpticalSignalLosTrap notification is sent when optical signals are lost.
        "
    ::= { ibEponTrapPrefix 45 }

ibEponOpticalSignalLosRecoverTrap NOTIFICATION-TYPE
    OBJECTS
        {
            ifIndex,
            ifDescr
        }
    STATUS      current
    DESCRIPTION
        "
        A ibEponOpticalSignalLosTrap notification is sent when optical signal loss recovers.
        "
    ::= { ibEponTrapPrefix 46 }

ibEponOnuFiberFailTrap NOTIFICATION-TYPE
    OBJECTS
        {
            ifIndex,
            ifDescr
        }
    STATUS      current
    DESCRIPTION
        "
        A ibEponOnuPowerOffTrap notification is sent when the ONU fiber fails.
        "
    ::= { ibEponTrapPrefix 47 }

ibEponOnuFiberFailRecoverTrap NOTIFICATION-TYPE
    OBJECTS
        {
            ifIndex,
            ifDescr
        }
    STATUS      current
    DESCRIPTION
        "
        A ibEponOnuPowerOffTrap notification is sent when the ONU fiber failure recovers.
        "
    ::= { ibEponTrapPrefix 48 }

ibEponStat OBJECT IDENTIFIER ::= { ibEponMibObjects 9 }

--
-- ibEponStatTable
--

ibEponStatTable OBJECT-TYPE
    SYNTAX      SEQUENCE OF IbEponStatEntry
    MAX-ACCESS  not-accessible
    STATUS      current
    DESCRIPTION
        "
        This table contains line code error statistics of epon port.
        "
    ::= { ibEponStat 1 }

ibEponStatEntry OBJECT-TYPE
    SYNTAX      IbEponStatEntry
    MAX-ACCESS  not-accessible
    STATUS      current
    DESCRIPTION
        "
        The entry of ibEponStatTable.
        "
    INDEX
        {
            ifIndex
        }
    ::= { ibEponStatTable 1 }

IbEponStatEntry ::= SEQUENCE
    {
        ibEponStatFER    Counter64,
        ibEponStatBER    Counter64
    }

ibEponStatFER OBJECT-TYPE
    SYNTAX      Counter64
    MAX-ACCESS  read-only
    STATUS      current
    DESCRIPTION
        "
        The frame error rate of epon port, measured in 1e-9 unit.
        "
    ::= { ibEponStatEntry 1 }

ibEponStatBER OBJECT-TYPE
    SYNTAX      Counter64
    MAX-ACCESS  read-only
    STATUS      current
    DESCRIPTION
        "
        The bit error rate of epon port, measured in 1e-9 unit.
        "
    ::= { ibEponStatEntry 2  }

ibEponRoltMan OBJECT IDENTIFIER ::= { ibEponMibObjects 10 }

--
-- ibRoltInterfaceTable
--

ibRoltInterfaceTable OBJECT-TYPE
    SYNTAX      SEQUENCE OF IbRoltInterfaceEntry
    MAX-ACCESS  not-accessible
    STATUS      current
    DESCRIPTION
        "
        The table of redundant OLT interfaces.
        "
    ::= { ibEponRoltMan 1 }

ibRoltInterfaceEntry  OBJECT-TYPE
    SYNTAX      IbRoltInterfaceEntry
    MAX-ACCESS  not-accessible
    STATUS      current
    DESCRIPTION
        "
        The entry of the table ibRoltInterfaceTable.
        "
    INDEX
        {
            ibRoltInterfaceNumber
        }
    ::= { ibRoltInterfaceTable 1 }

IbRoltInterfaceEntry ::= SEQUENCE
    {
        ibRoltInterfaceNumber       Integer32,
        ibRoltInterfaceIfIndex      Integer32,
        ibRoltInterfaceRowStatus    RowStatus
    }

ibRoltInterfaceNumber OBJECT-TYPE
    SYNTAX      Integer32
    MAX-ACCESS  not-accessible
    STATUS      current
    DESCRIPTION
        "
        The number of an ROLT interface.
        "
    ::= { ibRoltInterfaceEntry 1 }

ibRoltInterfaceIfIndex OBJECT-TYPE
    SYNTAX      Integer32
    MAX-ACCESS  read-only
    STATUS      current
    DESCRIPTION
        "
        The ifIndex of an ROLT interface.
        "
    ::= { ibRoltInterfaceEntry 2 }

ibRoltInterfaceRowStatus OBJECT-TYPE
    SYNTAX      RowStatus
    MAX-ACCESS  read-create
    STATUS      current
    DESCRIPTION
        "
        Create or delete a redundant OLT interface.
        Now only two operations are supported:
        createAndGo and destroy.
        "
    ::= { ibRoltInterfaceEntry 3 }

--
-- ibRoltMemberTable
--
ibRoltMemberTable OBJECT-TYPE
    SYNTAX      SEQUENCE OF IbRoltMemberEntry
    MAX-ACCESS  not-accessible
    STATUS      current
    DESCRIPTION
        "
        This table is used for adding or deleting the OLT member
        interfaces of an redundant OLT interface.
        "
    ::= { ibEponRoltMan 2 }

ibRoltMemberEntry  OBJECT-TYPE
    SYNTAX      IbRoltMemberEntry
    MAX-ACCESS  not-accessible
    STATUS      current
    DESCRIPTION
        "
        The entry of the table ibRoltMemberTable.
        "
    INDEX
        {
            ibRoltInterfaceNumber,
            ibRoltMemberOltIfindex
        }
    ::= { ibRoltMemberTable 1 }

IbRoltMemberEntry ::= SEQUENCE
    {
        ibRoltMemberOltIfindex      Integer32,
        ibRoltMemberOltPriority     Integer32,
        ibRoltMemberRowStatus       RowStatus,
        ibRoltMemberForwardStatus   TruthValue
    }

ibRoltMemberOltIfindex OBJECT-TYPE
    SYNTAX      Integer32
    MAX-ACCESS  not-accessible
    STATUS      current
    DESCRIPTION
        "
        The ifindex of an OLT interface.
        "
    ::= { ibRoltMemberEntry 1 }

ibRoltMemberOltPriority OBJECT-TYPE
    SYNTAX      Integer32 (1..255)
    MAX-ACCESS  read-create
    STATUS      current
    DESCRIPTION
        "
        The priority of an OLT interface that will be assigned to an ROLT interface.
        "
    ::= { ibRoltMemberEntry 2 }

ibRoltMemberRowStatus OBJECT-TYPE
    SYNTAX      RowStatus
    MAX-ACCESS  read-create
    STATUS      current
    DESCRIPTION
        "
        Operation status.  Now only two states are supported:
        createAndGo and destroy.
        "
    ::= { ibRoltMemberEntry 3 }

ibRoltMemberForwardStatus OBJECT-TYPE
    SYNTAX      TruthValue
    MAX-ACCESS  read-only
    STATUS      current
    DESCRIPTION
        "
        The forwarding status of an OLT member interface.
        true(1)  - Active.
        false(2) - Inactive.
        "
    ::= { ibRoltMemberEntry 4 }
END
