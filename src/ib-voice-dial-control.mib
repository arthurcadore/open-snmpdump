-- ==========================================================================
-- Copyright (C) 2023 Intelbras S.A. All rights reserved.
--
-- Description: The purpose of this MIB file is to provide the definition of
--              voice dial control configuration, it includes the common
--              cofiguration of entities, and special configuration for
--              pots entities and VoIP entities.
-- Reference:
-- Version: V1.2
-- History:
-- V1.0 2008-02-17 Initial version, created by Tian Xiaoqiang, Qu Jin
-- V1.1 2009-04-16 Add number management table 'ibVoEntityNumberTable', by
--                 Qu Pingping.
-- V1.2 2009-12-09 Add g729br8 to "IbCodecType", Wang Tong.
--                 Modify scope of ibVoEntityNumberAuthUser, 
--                 from 31 to 63 by yangzhanhua.
-- ==========================================================================
IB-VOICE-DIAL-CONTROL-MIB DEFINITIONS ::= BEGIN
IMPORTS
        OBJECT-TYPE, MODULE-IDENTITY, Integer32
    FROM SNMPv2-SMI
        TEXTUAL-CONVENTION, RowStatus, TruthValue
    FROM SNMPv2-TC
        InetAddressType, InetAddress
    FROM INET-ADDRESS-MIB
        AbsoluteCounter32
    FROM DIAL-CONTROL-MIB
        ibVoice
    FROM IB-OID-MIB;


ibVoiceEntityControl MODULE-IDENTITY
    LAST-UPDATED "200904160000Z"
    ORGANIZATION
        "Intelbras S.A. Industria de Telecomunicacao Eletronica Brasileria."
    CONTACT-INFO
        ""
    DESCRIPTION
        "This MIB file is to provide the definition of
        voice dial control configuration."
    REVISION "200904160000Z"
    DESCRIPTION
        "The initial version of this MIB file."
    ::= { ibVoice 14 }

-- ======================================
--          Type declaration
-- ======================================
IbCodecType      ::= TEXTUAL-CONVENTION
STATUS       current
DESCRIPTION
        "Type of Codec."
SYNTAX  INTEGER
        {
        g711a(1),
        g711u(2),
        g723r53(3),
        g723r63(4),
        g729r8(5),
        g729a(6),
        g726r16(7),
        g726r24(8),
        g726r32(9),
        g726r40(10),
        unknown(11),
        g729br8(12)
        }

IbOutBandMode    ::= TEXTUAL-CONVENTION
STATUS       current
DESCRIPTION
        "Type of OutBandMode."
SYNTAX  INTEGER
        {
        voice(1),
        h245AlphaNumeric(2),
        h225(3),
        sip(4),
        nte(5),
        vofr(6)
        }

IbFaxProtocolType    ::= TEXTUAL-CONVENTION
STATUS       current
DESCRIPTION
        "Type of FaxProtocol."
SYNTAX INTEGER
        {
        t38(1),
        standardt38(2),
        pcmG711alaw(3),
        pcmG711ulaw(4)
        }

IbFaxBaudrateType    ::= TEXTUAL-CONVENTION
STATUS       current
DESCRIPTION
        "Type of FaxBaudrate."
SYNTAX INTEGER
        {
        disable(1),
        voice(2),
        b2400(3),
        b4800(4),
        b9600(5),
        b14400(6)
        }
IbFaxTrainMode   ::= TEXTUAL-CONVENTION
STATUS       current
DESCRIPTION
        "Type of FaxTrainMode."
SYNTAX INTEGER
        {
        local(1),
        ppp(2)
        }

IbRegisterdStatus    ::= TEXTUAL-CONVENTION
STATUS       current
DESCRIPTION
        "Type of Registerd Status."
SYNTAX INTEGER
        {
        other(1),           -- pots entity has not matched number or has not
                            -- line with valid voice subscriber-line, or has not
                            -- turned on registered switch
        offline(2),         -- register failed or out of management with server
        online(3),          -- register successfully
        login(4),           -- registering to the server
        logout(5)           -- registering out from the server
        }

ibVoEntityObjects OBJECT IDENTIFIER ::= { ibVoiceEntityControl 1 }

-- ========================================================================
--                      ibVoEntityCreateTable
--
-- ========================================================================

ibVoEntityCreateTable OBJECT-TYPE
    SYNTAX      SEQUENCE OF IBVoEntityCreateEntry
    MAX-ACCESS  not-accessible
    STATUS      current
    DESCRIPTION
        "The table contains the voice entity information that
        is used to create an ifIndexed row."
    ::= { ibVoEntityObjects 1 }

ibVoEntityCreateEntry OBJECT-TYPE
    SYNTAX      IBVoEntityCreateEntry
    MAX-ACCESS  not-accessible
    STATUS      current
    DESCRIPTION
        "The entry of ibVoEntityCreateTable."
    INDEX
        {
            ibVoEntityIndex
        }
    ::= { ibVoEntityCreateTable 1 }

IBVoEntityCreateEntry ::= SEQUENCE
    {
        ibVoEntityIndex        Integer32,
        ibVoEntityType         INTEGER,
        ibVoEntityRowStatus    RowStatus
    }

ibVoEntityIndex OBJECT-TYPE
    SYNTAX      Integer32(1..2147483647)
    MAX-ACCESS  not-accessible
    STATUS      current
    DESCRIPTION
        "An arbitrary index that uniquely identifies a voice entity."
    ::= { ibVoEntityCreateEntry 1 }

ibVoEntityType OBJECT-TYPE
    SYNTAX      INTEGER
        {
            pots(1),
            voip(2),
            vofr(3)
        }
    MAX-ACCESS  read-create
    STATUS      current
    DESCRIPTION
        "Specify the type of voice related encapsulation."
    ::= { ibVoEntityCreateEntry 2 }

ibVoEntityRowStatus OBJECT-TYPE
    SYNTAX      RowStatus
    MAX-ACCESS  read-create
    STATUS      current
    DESCRIPTION
        " This object is used to create, delete or modify a row in
        this table. The ibVoEntityType object should not be
        modified once the new row has been created."
    ::= { ibVoEntityCreateEntry 3 }

-- ========================================================================
--                      ibVoEntityCommonConfigTable
--
-- ========================================================================
ibVoEntityCommonConfigTable OBJECT-TYPE
    SYNTAX      SEQUENCE OF IBVoEntityCommonConfigEntry
    MAX-ACCESS  not-accessible
    STATUS      current
    DESCRIPTION
        "This table contains the general voice entity information."
    ::= { ibVoEntityObjects 2 }


ibVoEntityCommonConfigEntry OBJECT-TYPE
    SYNTAX      IBVoEntityCommonConfigEntry
    MAX-ACCESS  not-accessible
    STATUS      current
    DESCRIPTION
        "The entry of ibVoEntityCommonConfigTable."
    INDEX
        {
            ibVoEntityCfgIndex
        }
    ::= { ibVoEntityCommonConfigTable 1 }


IBVoEntityCommonConfigEntry ::= SEQUENCE
    {
        ibVoEntityCfgIndex                Integer32,
        ibVoEntityCfgCodec1st             IbCodecType,
        ibVoEntityCfgCodec2nd             IbCodecType,
        ibVoEntityCfgCodec3rd             IbCodecType,
        ibVoEntityCfgCodec4th             IbCodecType,
        ibVoEntityCfgDSCP                 Integer32,
        ibVoEntityCfgVADEnable            TruthValue,
        ibVoEntityCfgOutbandMode          IbOutBandMode,
        ibVoEntityCfgFaxLevel             Integer32,
        ibVoEntityCfgFaxBaudrate          IbFaxBaudrateType,
        ibVoEntityCfgFaxLocalTrainPara    Integer32,
        ibVoEntityCfgFaxProtocol          IbFaxProtocolType,
        ibVoEntityCfgFaxHRPackNum         Integer32,
        ibVoEntityCfgFaxLRPackNum         Integer32,
        ibVoEntityCfgFaxSendNSFEnable     TruthValue,
        ibVoEntityCfgFaxTrainMode         IbFaxTrainMode,
        ibVoEntityCfgFaxEcm               TruthValue,
        ibVoEntityCfgPriority             Integer32,
        ibVoEntityCfgDescription          OCTET STRING
    }

ibVoEntityCfgIndex OBJECT-TYPE
    SYNTAX      Integer32(1..2147483647)
    MAX-ACCESS  not-accessible
    STATUS      current
    DESCRIPTION
        "An arbitrary index that uniquely identifies a voice entity."
    ::= { ibVoEntityCommonConfigEntry 1 }

ibVoEntityCfgCodec1st OBJECT-TYPE
    SYNTAX      IbCodecType
    MAX-ACCESS  read-write
    STATUS      current
    DESCRIPTION
        "This object indicates the first desirable CODEC of speech
        of this dial entity."
    ::= { ibVoEntityCommonConfigEntry 2 }


ibVoEntityCfgCodec2nd OBJECT-TYPE
    SYNTAX      IbCodecType
    MAX-ACCESS  read-write
    STATUS      current
    DESCRIPTION
        "This object indicates the second desirable CODEC of speech
        of this dial entity."
    ::= { ibVoEntityCommonConfigEntry 3 }


ibVoEntityCfgCodec3rd OBJECT-TYPE
    SYNTAX      IbCodecType
    MAX-ACCESS  read-write
    STATUS      current
    DESCRIPTION
        "This object indicates the third desirable CODEC of speech
        of this dial entity."
    ::= { ibVoEntityCommonConfigEntry 4 }


ibVoEntityCfgCodec4th OBJECT-TYPE
    SYNTAX      IbCodecType
    MAX-ACCESS  read-write
    STATUS      current
    DESCRIPTION
        "This object indicates the forth desirable CODEC of speech
        of this dial entity."
    ::= { ibVoEntityCommonConfigEntry 5 }


ibVoEntityCfgDSCP OBJECT-TYPE
    SYNTAX      Integer32(0..63)
    MAX-ACCESS  read-write
    STATUS      current
    DESCRIPTION
        "This object indicates the DSCP(Different Service Code Point)
        value of voice packets."
    ::= { ibVoEntityCommonConfigEntry 6 }


ibVoEntityCfgVADEnable OBJECT-TYPE
    SYNTAX      TruthValue
    MAX-ACCESS  read-write
    STATUS      current
    DESCRIPTION
        "This object indicates whether the VAD(Voice Activity Detection)
        is enabled."
    ::= { ibVoEntityCommonConfigEntry 7 }


ibVoEntityCfgOutbandMode OBJECT-TYPE
    SYNTAX      IbOutBandMode
    MAX-ACCESS  read-write
    STATUS      current
    DESCRIPTION
        "This object indicates the DTMF(Dual Tone Multi-Frequency)
        outband type of this dial entity."
    ::= { ibVoEntityCommonConfigEntry 8 }


ibVoEntityCfgFaxLevel OBJECT-TYPE
    SYNTAX      Integer32(-60..-3)
    MAX-ACCESS  read-write
    STATUS      current
    DESCRIPTION
        "This object indicates the fax level of this dial entity."
    ::= { ibVoEntityCommonConfigEntry 9 }


ibVoEntityCfgFaxBaudrate OBJECT-TYPE
    SYNTAX      IbFaxBaudrateType
    MAX-ACCESS  read-write
    STATUS      current
    DESCRIPTION
        "This object indicates the fax baudrate of this dial entity."
    ::= { ibVoEntityCommonConfigEntry 10 }


ibVoEntityCfgFaxLocalTrainPara OBJECT-TYPE
    SYNTAX      Integer32(0..100)
    MAX-ACCESS  read-write
    STATUS      current
    DESCRIPTION
        "This object indicates the fax local train threshold of this
        dial entity."
    ::= { ibVoEntityCommonConfigEntry 11 }


ibVoEntityCfgFaxProtocol OBJECT-TYPE
    SYNTAX      IbFaxProtocolType
    MAX-ACCESS  read-write
    STATUS      current
    DESCRIPTION
        "This object indicates the fax protocol of this dial entity."
    ::= { ibVoEntityCommonConfigEntry 12 }


ibVoEntityCfgFaxHRPackNum OBJECT-TYPE
    SYNTAX      Integer32(0..2)
    MAX-ACCESS  read-write
    STATUS      current
    DESCRIPTION
        "This object indicates the high speed redundancy packet
        numbers of t38 and standard-t38."
    ::= { ibVoEntityCommonConfigEntry 13 }


ibVoEntityCfgFaxLRPackNum OBJECT-TYPE
    SYNTAX      Integer32(0..5)
    MAX-ACCESS  read-write
    STATUS      current
    DESCRIPTION
        "This object indicates the low speed redundancy packet
        numbers of t38 and standard-t38."
    ::= { ibVoEntityCommonConfigEntry 14 }


ibVoEntityCfgFaxSendNSFEnable OBJECT-TYPE
    SYNTAX      TruthValue
    MAX-ACCESS  read-write
    STATUS      current
    DESCRIPTION
        "This object indicates whether sends NSF(Non-Standard Faculty)
        to fax of this dial entity."
    ::= { ibVoEntityCommonConfigEntry 15 }


ibVoEntityCfgFaxTrainMode OBJECT-TYPE
    SYNTAX      IbFaxTrainMode
    MAX-ACCESS  read-write
    STATUS      current
    DESCRIPTION
        "This object indicates the fax train mode of this dial entity."
    ::= { ibVoEntityCommonConfigEntry 16 }


ibVoEntityCfgFaxEcm OBJECT-TYPE
    SYNTAX      TruthValue
    MAX-ACCESS  read-write
    STATUS      current
    DESCRIPTION
        "This object indicates whether the ECM(Error Correct Mode)
        is enabled."
    ::= { ibVoEntityCommonConfigEntry 17 }


ibVoEntityCfgPriority OBJECT-TYPE
    SYNTAX      Integer32(0..10)
    MAX-ACCESS  read-write
    STATUS      current
    DESCRIPTION
        "This object indicates the priority of this dial entity."
    ::= { ibVoEntityCommonConfigEntry 18 }


ibVoEntityCfgDescription OBJECT-TYPE
    SYNTAX      OCTET STRING(SIZE(0..80))
    MAX-ACCESS  read-write
    STATUS      current
    DESCRIPTION
        "This object indicates the textual description of this
        dial entity."
    ::= { ibVoEntityCommonConfigEntry 19 }




-- ========================================================================
--                      ibVoPOTSEntityConfigTable
--
-- ========================================================================
ibVoPOTSEntityConfigTable OBJECT-TYPE
    SYNTAX      SEQUENCE OF IBVoPOTSEntityConfigEntry
    MAX-ACCESS  not-accessible
    STATUS      current
    DESCRIPTION
        "This table contains the POTS(Public Switched Telephone Network)
        entity information."
    ::= { ibVoEntityObjects 3 }


ibVoPOTSEntityConfigEntry OBJECT-TYPE
    SYNTAX      IBVoPOTSEntityConfigEntry
    MAX-ACCESS  not-accessible
    STATUS      current
    DESCRIPTION
        "The entry of ibVoPOTSEntityConfigTable."
    INDEX
        {
            ibVoPOTSEntityConfigIndex
        }
    ::= { ibVoPOTSEntityConfigTable 1 }


IBVoPOTSEntityConfigEntry ::= SEQUENCE
    {
        ibVoPOTSEntityConfigIndex      Integer32,
        ibVoPOTSEntityConfigPrefix     OCTET STRING,
        ibVoPOTSEntityConfigSubLine    OCTET STRING,
        ibVoPOTSEntityConfigSendNum    Integer32
    }

ibVoPOTSEntityConfigIndex OBJECT-TYPE
    SYNTAX      Integer32(1..2147483647)
    MAX-ACCESS  not-accessible
    STATUS      current
    DESCRIPTION
        "An arbitrary index that uniquely identifies a voice entity."
    ::= { ibVoPOTSEntityConfigEntry 1 }


ibVoPOTSEntityConfigPrefix OBJECT-TYPE
    SYNTAX      OCTET STRING(SIZE(0..31))
    MAX-ACCESS  read-write
    STATUS      current
    DESCRIPTION
        "This object indicates the prefix which is added to the
        called number."
    ::= { ibVoPOTSEntityConfigEntry 2 }


ibVoPOTSEntityConfigSubLine OBJECT-TYPE
    SYNTAX      OCTET STRING
    MAX-ACCESS  read-write
    STATUS      current
    DESCRIPTION
        "This object indicates the voice subscriber line of
        this dial entity."
    ::= { ibVoPOTSEntityConfigEntry 3 }


ibVoPOTSEntityConfigSendNum OBJECT-TYPE
    SYNTAX      Integer32(0..31|65534|65535)
    MAX-ACCESS  read-write
    STATUS      current
    DESCRIPTION
        "This object indicates the digit of phone number to be
        sent to the destination.
        0..31: Number of digits (that are extracted from the end of a number)
        to be sent, in the range of 0 to 31. It is not greater than the total
        number of digits of the called number.
        65534: Sends all digits of a called number.
        65535: Sends a truncated called number."
    ::= { ibVoPOTSEntityConfigEntry 4 }



-- ========================================================================
--                      ibVoVoIPEntityConfigTable
--
-- ========================================================================
ibVoVoIPEntityConfigTable OBJECT-TYPE
    SYNTAX      SEQUENCE OF IBVoVoIPEntityConfigEntry
    MAX-ACCESS  not-accessible
    STATUS      current
    DESCRIPTION
        "This table contains the VoIP entity information."
    ::= { ibVoEntityObjects 4 }


ibVoVoIPEntityConfigEntry OBJECT-TYPE
    SYNTAX      IBVoVoIPEntityConfigEntry
    MAX-ACCESS  not-accessible
    STATUS      current
    DESCRIPTION
        "The entry of ibVoVoIPEntityConfigTable."
    INDEX
        {
            ibVoVoIPEntityCfgIndex
        }
    ::= { ibVoVoIPEntityConfigTable 1 }


IBVoVoIPEntityConfigEntry ::= SEQUENCE
    {
        ibVoVoIPEntityCfgIndex             Integer32,
        ibVoVoIPEntityCfgTargetType        INTEGER,
        ibVoVoIPEntityCfgTargetAddrType    InetAddressType,
        ibVoVoIPEntityCfgTargetAddr        InetAddress
    }

ibVoVoIPEntityCfgIndex OBJECT-TYPE
    SYNTAX      Integer32(1..2147483647)
    MAX-ACCESS  not-accessible
    STATUS      current
    DESCRIPTION
        "An arbitrary index that uniquely identifies a voice entity."
    ::= { ibVoVoIPEntityConfigEntry 1 }


ibVoVoIPEntityCfgTargetType OBJECT-TYPE
    SYNTAX      INTEGER
        {
            unknown(1),
            ras(2),
            h323IpAddress(3),
            sipIpAddress(4),
            sipProxy(5)
        }
    MAX-ACCESS  read-write
    STATUS      current
    DESCRIPTION
        "This object indicates the type of the session target of this entity."
    ::= { ibVoVoIPEntityConfigEntry 2 }


ibVoVoIPEntityCfgTargetAddrType OBJECT-TYPE
    SYNTAX      InetAddressType
    MAX-ACCESS  read-write
    STATUS      current
    DESCRIPTION
        "The IP address type of object ibVoVoIPEntityCfgTargetAddr."
    ::= { ibVoVoIPEntityConfigEntry 3 }


ibVoVoIPEntityCfgTargetAddr OBJECT-TYPE
    SYNTAX      InetAddress
    MAX-ACCESS  read-write
    STATUS      current
    DESCRIPTION
        "This object indicates the target IP address."
    ::= { ibVoVoIPEntityConfigEntry 4 }

-- ========================================================================
--                      ibVoEntityNumberTable
--
-- ========================================================================
ibVoEntityNumberTable OBJECT-TYPE
    SYNTAX      SEQUENCE OF IbVoEntityNumberEntry
    MAX-ACCESS  not-accessible
    STATUS      current
    DESCRIPTION
        "The table contains the number management information."
    ::= { ibVoEntityObjects 5 }


ibVoEntityNumberEntry OBJECT-TYPE
    SYNTAX      IbVoEntityNumberEntry
    MAX-ACCESS  not-accessible
    STATUS      current
    DESCRIPTION
        "The entry of ibVoEntityNumberTable.  IbVoEntityIndex
        is used to uniquely identify these numbers registered on
        the server.  The same value of ibVoEntityIndex used in
        the corresponding IBVoEntityCommonConfigTable is used here."
    INDEX
        {
            ibVoEntityIndex
        }
    ::= { ibVoEntityNumberTable 1 }

IbVoEntityNumberEntry ::= SEQUENCE
{
    ibVoEntityNumberAuthUser                   OCTET STRING,
    ibVoEntityNumberPasswordType               Integer32,
    ibVoEntityNumberPassword                   OCTET STRING,
    ibVoEntityNumberStatus                     IbRegisterdStatus,
    ibVoEntityNumberExpires                    Integer32
}

ibVoEntityNumberAuthUser OBJECT-TYPE
    SYNTAX      OCTET STRING(SIZE(0..63))
    MAX-ACCESS  read-write
    STATUS      current
    DESCRIPTION
        "This object indicates the username of the entity number to authorize."
    ::= { ibVoEntityNumberEntry 1 }

ibVoEntityNumberPasswordType OBJECT-TYPE
    SYNTAX      Integer32
    MAX-ACCESS  read-write
    STATUS      current
    DESCRIPTION
        "This object indicates the password type of the entity number to authorize.
         The encrypting type of password:
         0 : password simple, means password is clean text.
         1 : password cipher, means password is encrypted text.
         default is 65535."
    ::= { ibVoEntityNumberEntry 2 }

ibVoEntityNumberPassword OBJECT-TYPE
    SYNTAX      OCTET STRING(SIZE(0..16 | 24))
    MAX-ACCESS  read-write
    STATUS      current
    DESCRIPTION
        "This object indicates the password of the entity number to authorize."
    ::= { ibVoEntityNumberEntry 3 }

ibVoEntityNumberStatus OBJECT-TYPE
    SYNTAX      IbRegisterdStatus
    MAX-ACCESS  read-only
    STATUS      current
    DESCRIPTION
        "This object indicates the current state of the entity number."
    ::= { ibVoEntityNumberEntry 4 }

ibVoEntityNumberExpires OBJECT-TYPE
    SYNTAX      Integer32
    UNITS       "seconds"
    MAX-ACCESS  read-only
    STATUS      current
    DESCRIPTION
        "This is the interval time for entity number updating registered message."
    ::= { ibVoEntityNumberEntry 5 }

END
