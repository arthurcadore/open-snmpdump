-- =========================================================================
-- Copyright (C) 2023 Intelbras S.A. All rights reserved.
--
-- Description: This MIB file is used for management of ib Class Based
--             QoS information.
-- Reference:
-- Version: V2.7
-- History:
-- V1.0 created by tangshun.
-- V1.1 2006/01/17 modified by wangjinwang
--   add enum value 22 and 23 in MatchRuleType
--   add comment for ibCBQoSMatchRuleIntValue1
-- V1.2 2006/02/24 modified by changhuifeng
--   Add an enumeration Bittorrent(24) to object ibCBQoSMatchRuleType.
--   Add ibCBQoSMirrorCfgInfoTable for flow mirror.
--   Add ibCBQoSRedirectIpv6Interface1 and ibCBQoSRedirectIpv6Interface2
--   object for ibCBQoSRedirectCfgInfoTable.
--   Modify the value range of ibCBQoSRemarkValue from "1~4094" to "1~4095"
--   in ibIfQoSPQClassRuleTable.
-- V1.3 2006/03/29 modified by xialei
--   Modify the MAX-ACCESS clause of ibCBQoSQueueDropType.
--   Modify the description for object ibCBQoSQueueCbs.
--   Modify the enumeration name of object ibCBQoSRedirectType.
-- V1.4 2007/10/15 modified by wangjinwang
--   Add ibCBQoSGlobalApplyTable to global policy apply.
--   Add ibCBQoSPolicyClassMode and ibCBQoSPolicyClassCfgOrder to
--   ibCBQoSPolicyClassCfgInfoTable.
--   Add ibCBQoSNestCfgInfoTable to traffic behavior.
--   Add enumeration matchRuleServiceDot1p
--   to object ibCBQoSMatchRuleType.
--   Add enumeration typeTopMostVlanID to object ibCBQoSRemarkType.
-- V1.5 2007/12/12 modified by Xu Hang/ChenWei
--   Delete the default value of ibCBQoSGlobalApplyDirection
--   in ibCBQoSGlobalApplyTable
--   Add ibCBQoSApplyPolicyIndexObjects to ibCBQoSApplyPolicyStaticsObjects
--   Add ibCBQoSStaticsObjects to ibCBQoSApplyPolicyStaticsObjects
--   Modify the MAX-ACCESS clause of ibCBQoSQueueDropType.
--   Modify the MAX-ACCESS clause of ibCBQoSIfApplyPolicyIfIndex,
--   ibCBQoSIfApplyPolicyDirection, ibCBQoSVlanApplyPolicyVlanid
--   and ibCBQoSVlanApplyPolicyDirection.
--   Add ibCBQoSApplyingStatusObjects to ibCBQoSObjects.
--   Add ibCBQoSApplyingStatus to ibCBQoSApplyPolicyObjects.
--   Add ibCBQoSNotifications to ibCBQoSObjects.
--   Add ibCBQoSNotificationsPrefix to ibCBQoSNotifications.
--   Add ibCBQoSIfPolicyChanged and ibCBQoSVlanPolicyChanged
--   to ibCBQoSNotificationsPrefix.
--   Add remark-local-pre-pass and remark-drop-pre-pass to CarAction.
--   Delete the default value of ibCBQoSVlanApplyPolicyDirection and
--   ibCBQoSGlobalApplyDirection.
-- V1.6 2008/05/28 modified by ChenWei
--   Add ibCBQoSNestPolicyCfgInfoTable to ibCBQoSBehaviorObjects.
--   Add ibCBQoSNestPolicyApplyObjectTable to ibCBQoSApplyPolicyIndexObjects.
-- V1.7 2011/01/25 modified by XuGuoFang/zhaixiaoxiang
--   Modify the range of ibCBQoSQueueBandwidthValue.
--   Modify the range of ibCBQoSQueueCbs.
--   Modify the description of ibCBQoSQueueCbsRatio.
--   Modify the description of ibCBQoSBehaviorIndexNext.
-- V1.8 2012/07/02 modified by XuJunjie/XunZhi
--   Modify MatchRuleType add matchRuleMplsLabel to matchRuleForwardingLayer.
--   Modify the description for ibCBQoSClassifierIndexNext.
--   Modify the description for ibCBQosClassifierMatchRuleNextIndex.
--   Modify the description for ibCBQoSMatchRuleStringValue.
--   Modify the description for ibCBQoSMatchRuleIntValue1.
--   Modify the description for ibCBQoSMatchRuleIntValue2.
--   Add table ibCBQoSMatchCpProtoCfgTable.
--   Add table ibCBQoSMatchCpGroupCfgTable.
--   Add ibCBQoSAccountingMode in ibCBQoSAccountCfgInfoTable.
--   Add ibCBQoSRedirectIfVlanID in ibCBQoSRedirectCfgInfoTable.
--   Add table ibCBQoSMirrorIfCfgInfoTable.
--   Add table ibCBQoSColoredRemarkCfgTable.
--   Add table ibCBQoSPrimapCfgInfoTable.
--   Add table ibCBQoSColorMapDpCfgInfoTable.
--   Modify the description for ibCBQoSPolicyIndexNext
--   Modify the description for ibCBQoSPolicyClassNextIndex
--   Add table ibCBQoSCpApplyPolicyTable
--   Modify ApplyObjectType add controlPlane
--   Modify the description for ibCBQoSApplyObjectMainSite
--   Modify the description for ibCBQoSApplyObjectSubChannel
--   Add table ibCBQoSCpApplyObjectTable
--   Modify SYNTAX add partialSuccess(3) for ibCBQoSClassBehaviorStatus
--   Modify ibCBQoSQueueBandwidthUnit add a value RemainPercent.
--   Modify ibCBQoSPolicyClassMode, add modeQppb, modeIpSourceGuard, modeVoiceVlan,
--   modeDCBX to value list.
--   Add node ApplyPolicyStatus for table ibCBQoSIfApplyPolicyTable,
--   ibCBQoSVlanApplyPolicyTable, and ibCBQoSGlobalApplyTable.
-- V1.9 2013/03/13 modified by MouXuanli
--   Add typeSecondMplsExp to RemarkType.
--   Modify the description of ibCBQoSRemarkValue and ibCBQoSColoredRemarkValue.
-- V2.0 2014/02/24 modified by MouXuanli
--   Modify the range of ibCBQoSQueueLength.
-- V2.1 2014/04/17 modified by GaoYu/XunZhi
--   Add enumeration matchRuleMacAcl and matchRuleUserAcl to MatchRuleType.
--   Modify the description of ibCBQoSMatchRuleStringValue.
--   Modify the description of ibCBQoSMatchRuleIntValue1.
-- V2.2 2016/2/24 modified by WanQing
--   Add enumeration matchRuleVxlan to MatchRuleType.
--   Modify the description of ibCBQoSMatchRuleStringValue.
--   2017/03/02 modified by gaomengfei
--   Add ibCBQoSCarClassName to ibCBQoSCarRunInfoEntry.
--   2017/10/10 modified by gaomengfei
--   Add ibCBQoSAccountingPktpps to IbCBQoSAccountingRunInfoEntry.
--   Add ibCBQoSAccountingPktbps to IbCBQoSAccountingRunInfoEntry.
--   2018/01/4 modified by gaomengfei
--   Add ibCBQoSPolicyAccRunInfoTable.
-- V2.3 2018/10/31 modified by gaomengfei
--   Add ibCBQoSCarGreenpps to ibCBQoSCarRunInfoEntry.
--   Add ibCBQoSCarGreenbps to ibCBQoSCarRunInfoEntry.
--   Add ibCBQoSCarRedpps to ibCBQoSCarRunInfoEntry.
--   Add ibCBQoSCarRedbps to ibCBQoSCarRunInfoEntry.
--   Add ibCBQoSCarYellowpps to ibCBQoSCarRunInfoEntry.
--   Add ibCBQoSCarYellowbps to ibCBQoSCarRunInfoEntry.
-- V2.4 2019/05/29 modified by gaomengfei
--   Modify the value range of ibCBQoSQueueBandwidthValue from "1~10000000" to "1~100000000".
-- V2.5 2021/09/16 modified by gaomengfei
--   Add ibCBQoSGlobalAclNotSupport.
--   Add ibCBQoSGlobalQPPBNotSupport.
--   Add ibCBQoSNotificationsBindings.
-- V2.6 2022/06/09 modified by lizhaocheng
--   Add ibCBQoSRedirectInvalidAlarm
--   Add ibCBQoSRedirectInvalidAlarmRecover
-- V2.7 2022/11/21 modified by zhangxiaowei
--   Add ibCBQoSRdtNHLackResAlarm
--   Add ibCBQoSRdtNHLackResRecover
-- ==========================================================================
IB-CBQOS2-MIB DEFINITIONS ::= BEGIN

IMPORTS
    ibCommon
        FROM IB-OID-MIB
    Integer32, Counter64, Unsigned32, OBJECT-TYPE, MODULE-IDENTITY, NOTIFICATION-TYPE
        FROM SNMPv2-SMI
    InetAddressType, InetAddress
        FROM INET-ADDRESS-MIB           -- [RFC3291]
    TEXTUAL-CONVENTION, RowStatus, TruthValue
        FROM SNMPv2-TC;

ibCBQos2 MODULE-IDENTITY
    LAST-UPDATED "202211210000Z"        --November 21, 2022 at 00:00 GMT
    ORGANIZATION
        "Intelbras S.A. Industria de Telecomunicacao Eletronica Brasileria."
    CONTACT-INFO
        ""
    DESCRIPTION
        "This MIB contains objects to manage configuration and
         monitor running state for Class Based QoS feature.

            *********************************
                    MIB Tables
            **********************************
         This MIB consists of the following tables:
            1 :  ibCBQoSClassifierCfgInfoTable
            2 :  ibCBQoSMatchRuleCfgInfoTable
            3 :  ibCBQoSMatchCpProtoCfgTable
            4 :  ibCBQoSMatchCpGroupCfgTable
            5 :  ibCBQoSBehaviorCfgInfoTable
            6 :  ibCBQoSCarCfgInfoTable
            7 :  ibCBQoSAggregativeCarCfgInfoTable
            8 :  ibCBQoSGtsCfgInfoTable
            9 :  ibCBQoSRemarkCfgInfoTable
            10:  ibCBQoSQueueCfgInfoTable
            11:  ibCBQoSWredCfgInfoTable
            12:  ibCBQoSWredClassCfgInfoTable
            13:  ibCBQoSPolicyRouteCfgInfoTable
            14:  ibCBQoSNatCfgInfoTable
            15:  ibCBQoSFirewallCfgInfoTable
            16:  ibCBQoSSamplingCfgInfoTable
            17:  ibCBQoSAccountCfgInfoTable
            18:  ibCBQoSRedirectCfgInfoTable
            19:  ibCBQoSPriorityMapCfgInfoTable
            20:  ibCBQoSPolicyCfgInfoTable
            21:  ibCBQoSPolicyClassCfgInfoTable
            22:  ibCBQoSIfApplyPolicyTable
            23:  ibCBQoSAtmPvcApplyPolicyTable
            24:  ibCBQoSVlanApplyPolicyTable
            25:  ibCBQoSFrClassApplyPolicyTable
            26:  ibCBQoSFrPvcApplyPolicyTable
            27:  ibCBQoSIfCbqRunInfoTable
            28:  ibCBQoSIfClassMatchRunInfoTable
            29:  ibCBQoSIfCarRunInfoTable
            30:  ibCBQoSIfGtsRunInfoTable
            31:  ibCBQoSIfRemarkRunInfoTable
            32:  ibCBQoSIfQueueRunInfoTable
            33:  ibCBQoSIfWredRunInfoTable
            34:  ibCBQoSIfAccountingRunInfoTable
            35:  ibCBQoSAtmPvcCbqRunInfoTable
            36:  ibCBQoSAtmPvcClassMatchRunInfoTable
            37:  ibCBQoSAtmPvcCarRunInfoTable
            38:  ibCBQoSAtmPvcGtsRunInfoTable
            39:  ibCBQoSAtmPvcRemarkRunInfoTable
            40:  ibCBQoSAtmPvcQueueRunInfoTable
            41:  ibCBQoSAtmPvcWredRunInfoTable
            42:  ibCBQoSAtmPvcAccountingRunInfoTable
            43:  ibCBQoSFrPvcCbqRunInfoTable
            44:  ibCBQoSFrPvcClassMatchRunInfoTable
            45:  ibCBQoSFrPvcCarRunInfoTable
            46:  ibCBQoSFrPvcGtsRunInfoTable
            47:  ibCBQoSFrPvcRemarkRunInfoTable
            48:  ibCBQoSFrPvcQueueRunInfoTable
            49:  ibCBQoSFrPvcWredRunInfoTable
            50:  ibCBQoSFrPvcAccountingRunInfoTable
            51:  ibCBQoSIfVlanClassMatchRunInfoTable
            52:  ibCBQoSIfVlanAccountingRunInfoTable
            53:  ibCBQoSMirrorCfgInfoTable
            54:  ibCBQoSGlobalApplyTable
            55:  ibCBQoSCpApplyPolicyTable
            56:  ibCBQoSNestCfgInfoTable
            57:  ibCBQoSNestPolicyCfgInfoTable
            58:  ibCBQoSMirrorIfCfgInfoTable
            59:  ibCBQoSColoredRemarkCfgTable
            60:  ibCBQoSPrimapCfgInfoTable
            61:  ibCBQoSColorMapDpCfgInfoTable
            62:  ibCBQoSApplyObjectTable
            63:  ibCBQoSIntApplyObjectTable
            64:  ibCBQoSVlanApplyObjectTable
            65:  ibCBQoSPvcApplyObjectTable
            66:  ibCBQoSNestPolicyApplyObjectTable
            67:  ibCBQoSCpApplyObjectTable
            68:  ibCBQoSCbqRunInfoTable
            69:  ibCBQoSClassMatchRunInfoTable
            70:  ibCBQoSCarRunInfoTable
            71:  ibCBQoSGtsRunInfoTable
            72:  ibCBQoSRemarkRunInfoTable
            73:  ibCBQoSQueueRunInfoTable
            74:  ibCBQoSWredRunInfoTable
            75:  ibCBQoSAccountingRunInfoTable
            76:  ibCBQoSPolicyAccRunInfoTable
            77:  ibCBQoSApplyingStatusObjects
            78:  ibCBQoSNotifications
            79:  ibCBQoSNotificationsBindings
        "
    REVISION "202211210000Z"        --November 21, 2022 at 00:00 GMT
    DESCRIPTION
        "Add ibCBQoSRdtNHLackResAlarm.
         Add ibCBQoSRdtNHLackResRecover."
    REVISION "202206090000Z"        --June 9, 2022 at 00:00 GMT
    DESCRIPTION
        "Add ibCBQoSRedirectInvalidAlarm.
         Add ibCBQoSRedirectInvalidAlarmRecover."
    REVISION "202109160000Z"        --Sep 16, 2021 at 00:00 GMT
    DESCRIPTION
        "Add ibCBQoSGlobalAclNotSupport.
         Add ibCBQoSGlobalQPPBNotSupport.
         Add ibCBQoSNotificationsBindings."
    REVISION "201905290000Z"        --May 29, 2019 at 00:00 GMT
    DESCRIPTION
        "Modify the value range of ibCBQoSQueueBandwidthValue from 1~10000000 to 1~100000000."
    REVISION "201810310000Z"        --October 31, 2018 at 00:00 GMT
    DESCRIPTION
        "Add ibCBQoSCarGreenpps to ibCBQoSCarRunInfoEntry.
         Add ibCBQoSCarGreenbps to ibCBQoSCarRunInfoEntry.
         Add ibCBQoSCarRedpps to ibCBQoSCarRunInfoEntry.
         Add ibCBQoSCarRedbps to ibCBQoSCarRunInfoEntry.
         Add ibCBQoSCarYellowpps to ibCBQoSCarRunInfoEntry.
         Add ibCBQoSCarYellowbps to ibCBQoSCarRunInfoEntry."
    REVISION "201801040000Z"        --January 4, 2018 at 00:00 GMT
    DESCRIPTION
        "Add ibCBQoSPolicyAccRunInfoTable."
    REVISION "201710100000Z"        --October 10, 2017 at 00:00 GMT
    DESCRIPTION
        "Add ibCBQoSAccountingPktpps to IbCBQoSAccountingRunInfoEntry.
         Add ibCBQoSAccountingPktbps to IbCBQoSAccountingRunInfoEntry."
    REVISION "201703020000Z"        --March 02, 2017 at 00:00 GMT
    DESCRIPTION
        "Add ibCBQoSCarClassName to ibCBQoSCarRunInfoEntry."
    REVISION "201602240000Z"        -- Feb 24, 2016 at 00:00 GMT
    DESCRIPTION
        "Add enumeration matchRuleVxlan to MatchRuleType.
         Modify the description of ibCBQoSMatchRuleStringValue."
    REVISION "201207020000Z"        -- July 02, 2012 at 00:00 GMT
    DESCRIPTION
        "Modified to add new tables and new nodes."
    REVISION "200507300000Z"        -- July 30, 2005 at 00:00 GMT
    DESCRIPTION
        "The initial revision of this MIB module."
    ::= { ibQos2 2 }

ibQos2 OBJECT IDENTIFIER ::= { ibCommon 65 }

--
-- type definitions in the traffic classifier
--

-- MatchRuleType
MatchRuleType ::= TEXTUAL-CONVENTION
    STATUS current
    DESCRIPTION
        "Type of Match Rule."
    SYNTAX INTEGER
    {
        matchRuleAny(1),
        matchRuleIpv4Acl(2),
        matchRuleIPv6Acl(3) ,
        matchRuleIPv4Protocol(4),
        matchRuleIPv6Protocol(5),
        matchRuleIPXProtocol(6),
        matchRuleDscp(7),
        matchRuleIpPre(8),
        matchRuleVlan8021p(9),
        matchRuleMplsExp(10),
        matchRuleAtmClp(11),
        matchRuleFrDe(12),
        matchRuleSourceMac(13),
        matchRuleDestinationMac(14),
        matchRuleQosLocalID(15),
        matchRuleClassifier(16),
        matchRuleInboundInterface(17),
        matchRuleRtpPort(18),
        matchRuleSourceIp(19),
        matchRuleVlanID(20),
        matchRuleTopMostVlanID(21),
        matchRuleLocalPrecedence(22),
        matchRuleDropPriority(23),
        matchRuleBittorrent(24),
        matchRuleServiceDot1p(25),
        matchRuleMplsLabel(26),
        matchRuleSecondMplsLabel(27),
        matchRuleSecondMplsExp(28),
        matchRulePacketLength(29),
        matchRuleArpProtocol(30),
        matchRuleForwardingLayer(31),
        matchRuleMacAcl(32),
        matchRuleUserAcl(33),
        matchRuleVxlan(34)
    }
--
-- end of type definitions in the traffic classifier
--

--
-- type definitions in the traffic behavior
--

-- CarAction
CarAction ::= TEXTUAL-CONVENTION
    STATUS current
    DESCRIPTION
        "The actions taken when packets conforming or exceeding
         the configured committed information rate(CIR)."
    SYNTAX INTEGER
    {
        invalid(0),
        pass(1),
        continue(2),
        discard(3),
        remark(4),
        remark-ip-continue(5),
        remark-ip-pass(6),
        remark-mplsexp-continue(7),
        remark-mplsexp-pass(8),
        remark-dscp-continue(9),
        remark-dscp-pass(10),
        remark-dot1p-continue(11),
        remark-dot1p-pass(12),
        remark-atm-clp-continue(13),
        remark-atm-clp-pass(14),
        remark-fr-de-continue(15),
        remark-fr-de-pass(16),
        remark-local-pre-pass(17),
        remark-drop-pre-pass(18)
    }

-- RemarkType
RemarkType ::= TEXTUAL-CONVENTION
    STATUS  current
    DESCRIPTION
        "Type of remark."
    SYNTAX INTEGER
    {
        typeIpPrecedence(1),
        typeDscp(2),
        typeMplsExp(3),
        typeVlan8021p(4),
        typeAtmClp(5),
        typeFrDe(6),
        typeVlanID(7),
        typeQosLocalID(8),
        typeDropPrecedence(9),
        typeLocalPrecedence(10),
        typeTopMostVlanID(11),
        typeSecondMplsExp(12)
    }

-- WredType
WredType ::= TEXTUAL-CONVENTION
    STATUS current
    DESCRIPTION
        "WRED type."
    SYNTAX INTEGER
    {
        typeIpPrecBased(1),
        typeDscpBased(2),
        typeDropLevelBased(3),
        typeAtmClpBased(4),
        typeVlan8021pBased(5),
        typeMplsExpBased(6)
    }

-- QueueType
QueueType ::= TEXTUAL-CONVENTION
    STATUS  current
    DESCRIPTION
        "Queueing Type:
         EF:(1)
         AF:(2)
         WFQ:(3)
        "
    SYNTAX INTEGER
    {
        ef(1),
        af(2),
        wfq(3)
    }

-- QueueBandwidthUnit
QueueBandwidthUnit ::= TEXTUAL-CONVENTION
    STATUS current
    DESCRIPTION
        "Bandwidth Unit:
         Absolute, Unit : Kbps(1)
         Percent, Unit : %(2)
         RemainPercent, Unit : %(3)
        "
    SYNTAX INTEGER
    {
        unitUnavailable(0),
        unitAbsolute(1),
        unitPercent(2),
        unitRemainPercent(3)
    }

--
-- end of type definitions in the traffic behavior
--

--
-- type definitions in the policy
--

-- Direction
DirectionType ::= TEXTUAL-CONVENTION
    STATUS  current
    DESCRIPTION
        "The direction of policy apply on at interface."
    SYNTAX  INTEGER
    {
        inbound(1),
        outbound(2)
    }

-- ApplyObjectType
ApplyObjectType ::= TEXTUAL-CONVENTION
    STATUS  current
    DESCRIPTION
        "Type of QoS apply object."
    SYNTAX  INTEGER
    {
        interface(1),
        vlan(2),
        atmPvc(3),
        frDlci(4),
        controlPlane(5)
    }

--
-- end of type definitions in policy
--

--
-- Node definitions
--
ibCBQoSObjects OBJECT IDENTIFIER ::= { ibCBQos2 1 }

-- ibCBQoSClassifierObjects

ibCBQoSClassifierObjects OBJECT IDENTIFIER ::= { ibCBQoSObjects 1 }

-- Traffic Classifier Next Index
ibCBQoSClassifierIndexNext OBJECT-TYPE
    SYNTAX Integer32
    MAX-ACCESS read-only
    STATUS current
    DESCRIPTION
        "This object contains an appropriate value to be used for
         ibCBQoSClassifierIndex when creating rows in the
         ibCBQoSClassifierCfgInfoTable.
        "
    ::= { ibCBQoSClassifierObjects 1 }

-- Traffic Classifier

ibCBQoSClassifierCfgInfoTable OBJECT-TYPE
    SYNTAX SEQUENCE OF IbCBQoSClassifierCfgInfoEntry
    MAX-ACCESS not-accessible
    STATUS current
    DESCRIPTION
        "A table of Traffic Classifier configuration information."
    ::= { ibCBQoSClassifierObjects 2 }

ibCBQoSClassifierCfgInfoEntry OBJECT-TYPE
    SYNTAX IbCBQoSClassifierCfgInfoEntry
    MAX-ACCESS not-accessible
    STATUS current
    DESCRIPTION
        "Traffic Classifier Configuration Information Entry."
    INDEX { ibCBQoSClassifierIndex }
    ::= { ibCBQoSClassifierCfgInfoTable 1 }

IbCBQoSClassifierCfgInfoEntry ::=
    SEQUENCE
    {
        ibCBQoSClassifierIndex
            Integer32,
        ibCBQoSClassifierName
            OCTET STRING,
        ibCBQoSClassifierRuleCount
            Integer32,
        ibCBQoSClassifierOperator
            INTEGER,
        ibCBQoSClassifierLayer
            INTEGER,
        ibCBQoSClassifierType
            INTEGER,
        ibCBQosClassifierMatchRuleNextIndex
            Integer32,
        ibCBQoSClassifierRowStatus
            RowStatus
    }

ibCBQoSClassifierIndex OBJECT-TYPE
    SYNTAX Integer32
    MAX-ACCESS not-accessible
    STATUS current
    DESCRIPTION
        "Index of Traffic Classifier.  Begin with 0."
    ::= { ibCBQoSClassifierCfgInfoEntry 1 }

ibCBQoSClassifierName OBJECT-TYPE
    SYNTAX OCTET STRING (SIZE (1..31))
    MAX-ACCESS read-create
    STATUS current
    DESCRIPTION
        "Name of Traffic Classifier."
    ::= { ibCBQoSClassifierCfgInfoEntry 2 }

ibCBQoSClassifierRuleCount OBJECT-TYPE
    SYNTAX Integer32
    MAX-ACCESS read-only
    STATUS current
    DESCRIPTION
        "The counter of match rules of Traffic classifier."
    ::= { ibCBQoSClassifierCfgInfoEntry 3 }

ibCBQoSClassifierOperator OBJECT-TYPE
    SYNTAX INTEGER
    {
        and(1),
        or(2)
    }
    MAX-ACCESS read-create
    STATUS current
    DESCRIPTION
        "Operator of the match rules of traffic classifier.
         Software QoS supports and, or.
         Hardware QoS supports and.
        "
    DEFVAL { and }
    ::= { ibCBQoSClassifierCfgInfoEntry 4 }

ibCBQoSClassifierLayer OBJECT-TYPE
    SYNTAX INTEGER
    {
        unavailable(1),
        l2(2),
        l3(3),
        both(4)
    }
    MAX-ACCESS read-create
    STATUS current
    DESCRIPTION
        "Configuration layer of traffic classifier.
         Only hardware QoS support it.
         1(unavailable) is returned only when getting value from software QoS.
         1(unavailable) can't be set.
        "
    DEFVAL { l3 }
    ::= { ibCBQoSClassifierCfgInfoEntry 5 }

ibCBQoSClassifierType OBJECT-TYPE
    SYNTAX INTEGER
    {
        systemDefined(1),
        userDefined(2)
    }
    MAX-ACCESS read-only
    STATUS current
    DESCRIPTION
        "The type of classifier."
    ::= { ibCBQoSClassifierCfgInfoEntry 6 }

ibCBQosClassifierMatchRuleNextIndex OBJECT-TYPE
    SYNTAX Integer32
    MAX-ACCESS read-only
    STATUS current
    DESCRIPTION
        "This object contains an appropriate value to be used for
         ibCBQoSMatchRuleIndex when creating rows in the
         ibCBQoSMatchRuleCfgInfoTable.
        "
    ::= { ibCBQoSClassifierCfgInfoEntry 7 }

ibCBQoSClassifierRowStatus OBJECT-TYPE
    SYNTAX RowStatus
    MAX-ACCESS read-create
    STATUS current
    DESCRIPTION
        "RowStatus."
    ::= { ibCBQoSClassifierCfgInfoEntry 8 }

-- Match rule

ibCBQoSMatchRuleCfgInfoTable OBJECT-TYPE
    SYNTAX SEQUENCE OF IbCBQoSMatchRuleCfgInfoEntry
    MAX-ACCESS not-accessible
    STATUS current
    DESCRIPTION
        "A table of Match Rule configuration information."
    ::= { ibCBQoSClassifierObjects 3 }

ibCBQoSMatchRuleCfgInfoEntry OBJECT-TYPE
    SYNTAX IbCBQoSMatchRuleCfgInfoEntry
    MAX-ACCESS not-accessible
    STATUS current
    DESCRIPTION
        "Match Rule Configuration Information Entry."
    INDEX { ibCBQoSClassifierIndex, ibCBQoSMatchRuleIndex }
    ::= { ibCBQoSMatchRuleCfgInfoTable 1 }

IbCBQoSMatchRuleCfgInfoEntry ::=
    SEQUENCE
    {
        ibCBQoSMatchRuleIndex
            Integer32,
        ibCBQoSMatchRuleIfNot
            INTEGER,
        ibCBQoSMatchRuleType
            MatchRuleType,
        ibCBQoSMatchRuleStringValue
            OCTET STRING,
        ibCBQoSMatchRuleIntValue1
            Unsigned32,
        ibCBQoSMatchRuleIntValue2
            Unsigned32,
        ibCBQoSMatchIpAddressType
            InetAddressType,
        ibCBQoSMatchIpAddress
            InetAddress,
        ibCBQoSMatchRuleRowStatus
            RowStatus
    }

ibCBQoSMatchRuleIndex OBJECT-TYPE
    SYNTAX Integer32
    MAX-ACCESS not-accessible
    STATUS current
    DESCRIPTION
        "Index of Match Rule."
    ::= { ibCBQoSMatchRuleCfgInfoEntry 1 }

ibCBQoSMatchRuleIfNot OBJECT-TYPE
    SYNTAX INTEGER
    {
        match(1),
        matchNot(2)
    }
    MAX-ACCESS read-create
    STATUS current
    DESCRIPTION
        "Whether the if-match rule is a match or matchNot statement.
         Software QoS supports match, matchNot.
         Hardware QoS supports match.
        "
    DEFVAL { match }
    ::= { ibCBQoSMatchRuleCfgInfoEntry 2 }

ibCBQoSMatchRuleType OBJECT-TYPE
    SYNTAX MatchRuleType
    MAX-ACCESS read-create
    STATUS current
    DESCRIPTION
        "Type of Match Rule."
    ::= { ibCBQoSMatchRuleCfgInfoEntry 3 }

ibCBQoSMatchRuleStringValue OBJECT-TYPE
    SYNTAX OCTET STRING (SIZE (0..255))
    MAX-ACCESS read-create
    STATUS current
    DESCRIPTION
        "Value of Match Rule.
         IPv4 ACL: SIZE (1..63) ACL name
         MAC ACL: SIZE (1..63) MAC ACL name
         User ACL: SIZE (1..63) User ACL name
         IPv6 ACL: SIZE (1..63) IPv6 ACL name
         SourceMAC: SIZE (12) HHHHHHHHHHHH
           for example: 010102020303 means the match rule is
                        'if-match source-mac 0101-0202-0303'
         DestinationMAC: SIZE (12) HHHHHHHHHHHH
           for example: 010102020303 means the match rule is
                        'if-match destination-mac 0101-0202-0303'
         Classifier: SIZE (1..31) classifier name
         InboundInterface: SIZE (1..47) interface description
         TopMostVlanID, VlanID: SIZE(1..109), up to 10 values can be input;
           for example: 1##5#11#111##114#1111 means the match rule is
                        'if-match vlanid 1 to 5 11 111 to 114 1111'
         SourceIp: SIZE (12) HHHHHHHHHHHH
           for example: 010102020303 means the match rule is
                        'if-match source-ip mac-address 0101-0202-0303'
         MplsLabel: SIZE (1..63), up to 8 values can be input;
           for example: 1#11#111#1111 means the match rule is
                        'if-match mpls-label 1 11 111 1111';
                        1##1111 means the match rule is
                        'if-match mpls-label 1 to 1111';
         SecondMplsLabel: SIZE (1..63), up to 8 values can be input;
           for example: 1#11#111#1111 means the match rule is
                        'if-match mpls-label 1 11 111 1111';
                        1##1111 means the match rule is
                        'if-match mpls-label 1 to 1111';
         VxlanID: SIZE(1..8) Vxlan ID or any
           for example: 20 means the match rule is
                        'if-match vxlan 20';
                        any means the match rule is
                        'if-match vxlan any';
         other types: Set is not permitted.  Zero-length string will
                      be returned when getting.
        "
    ::= { ibCBQoSMatchRuleCfgInfoEntry 4 }

ibCBQoSMatchRuleIntValue1 OBJECT-TYPE
    SYNTAX Unsigned32
    MAX-ACCESS read-create
    STATUS current
    DESCRIPTION
        "Value of Match Rule.
         IPv4 ACL: 2000~3999
         MAC ACL: 4000~4999
         User ACL: 5000~5999
         IPv6 ACL: 2000~3999; 10000~42767
         Software QoS: 2000~3999
         Hardware Qos: 10000~42767
         RtpPort: start-port: 2000~65535
         IpPrec: value: 0~7, up to 8 values can be input.  The bit set to
                 1 of the last 8 bits of ibCBQoSMatchRuleIntValue1 is
                 used to indicate the value 0~7.
           for example: 0x53(Binary format is 01010011)
                        means the match rule is 'if-match ip-prec 0 1 4 6'
         Dscp: value:0~63, up to 8 values can be input.
               The bit set to 1 of ibCBQoSMatchRuleIntValue1 is used
               to indicate the value 32~63.
               The bit set to 1 of ibCBQoSMatchRuleIntValue2 is used to
               indicate the value 0~31.
           for example: 0x80000003 means the match rule is 'if-match
                        dscp 32 33 63'
         Vlan8021p: value:0~7, up to 8 values can be input.  The bit set
                    to 1 of the last 8 bits of ibCBQoSMatchRuleIntValue1
                    is used to indicate the value 0~7.
           for example: 0x53(Binary format is 01010011) means the
                        match rule is 'if-match customer-dot1p 0 1 4 6'
         MplsExp: value:0~7, up to 8 values can be input.  The bit set to 1
                  of the last 8 bits of ibCBQoSMatchRuleIntValue1 is used
                  to indicate the 8 value 0~7.
           for example: 0x53(Binary format is 01010011) means the
                        match rule is 'if-match mpls 0 1 4 6'
         SourceIp: 1~4095
         QosLocalID: 1~4095
         AtmClp: 0~1
         FrDe: 0~1
         LocalPrecedence: 0~7, up to 8 values can be input.  The bit set to
                          1 of the last 8 bits of ibCBQoSMatchRuleIntValue1
                          is used to indicate the value 0~7.
           for example: 0x53(Binary format is 01010011) means the match
                        rule is 'if-match localprecedence 0 1 4 6'
         DropPriority: 0~2, up to 3 values can be input.  The bit set to 1
                       of the last 3 bits of ibCBQoSMatchRuleIntValue1 is
                       used to indicate the value 0~2.
         ServiceDot1p: 0~7, up to 8 values can be input.
                       The bit set to 1 of the last 8 bits of
                       ibCBQoSMatchRuleIntValue1 is used to indicate
                       the value 0~7.
           for example: 0x53(Binary format is 01010011) means the match
                        rule is 'if-match service-dot1p 0 1 4 6'
         SecondMplsExp: value:0~7, up to 8 values can be input.  The bit
                        set to 1 of the last 8 bits of ibCBQoSMatchRuleIntValue1
                        is used to indicate the 8 value 0~7.
           for example: 0x53(Binary format is 01010011) means the
                        match rule is 'if-match mpls 0 1 4 6'
         PacketLength: 1~2000.  ibCBQoSMatchRuleIntValue1 is used to
                       indicate the minimum value, ibCBQoSMatchRuleIntValue2
                       is used to indicate the maximum value.
         ForwardingLayer: {bridge(1), route(2)}
         other types: Set is not permitted.  0xffffffff will be returned
                      when getting.
        "
    ::= { ibCBQoSMatchRuleCfgInfoEntry 5 }

ibCBQoSMatchRuleIntValue2 OBJECT-TYPE
    SYNTAX Unsigned32
    MAX-ACCESS read-create
    STATUS current
    DESCRIPTION
        "Value of Match Rule.
         RtpPort: end-port: 2000~65535
         Dscp: value:0~63, up to 8 values can be input.
               The bit set to 1 of ibCBQoSMatchRuleIntValue1 is used to indicate the value 32~63.
               The bit set to 1 of ibCBQoSMatchRuleIntValue2 is used to indicate the value 0~31.
               for example: 0x80000003 means the match rule is 'if-match dscp 0 1 31'
         PacketLength: 1~2000.  ibCBQoSMatchRuleIntValue1 is used to
                       indicate the minimum value, ibCBQoSMatchRuleIntValue2
                       is used to indicate the maximum value.
         other types: Set is not permitted.  0xffffffff will be returned when getting.
        "
    ::= { ibCBQoSMatchRuleCfgInfoEntry 6 }

ibCBQoSMatchIpAddressType OBJECT-TYPE
    SYNTAX InetAddressType
    MAX-ACCESS read-create
    STATUS current
    DESCRIPTION
        "A value that represents a type of Internet address.
          unknown(0)  An unknown address type.  This value MUST
            be used if the value of the corresponding
            InetAddress object is a zero-length string.
            It may also be used to indicate an IP address
            which is not in one of the formats defined below.

         ipv4(1)     An IPv4 address as defined by the
                InetAddressIPv4 textual convention.

         ipv6(2)     A global IPv6 address as defined by the
                InetAddressIPv6 textual convention.

         ipv4z(3)    A non-global IPv4 address including a zone
                index as defined by the InetAddressIPv4z textual convention.

         ipv6z(4)    A non-global IPv6 address including a zone
                index as defined by the InetAddressIPv6z textual convention.

         dns(16)     A DNS domain name as defined by the
                InetAddressDNS textual convention.

         Value of match rule.
         SourceIp support this node.
         other types: Set is not permitted.  Unknown will be returned when getting.
        "
    ::= { ibCBQoSMatchRuleCfgInfoEntry 7 }

ibCBQoSMatchIpAddress OBJECT-TYPE
    SYNTAX InetAddress
    MAX-ACCESS read-create
    STATUS current
    DESCRIPTION
        "Denotes a generic Internet address.
         SourceIP support this node.
         other types: Set is not permitted.  NULL will be returned when getting.
        "
    ::= { ibCBQoSMatchRuleCfgInfoEntry 8 }

ibCBQoSMatchRuleRowStatus OBJECT-TYPE
    SYNTAX RowStatus
    MAX-ACCESS read-create
    STATUS current
    DESCRIPTION
        "RowStatus."
    ::= { ibCBQoSMatchRuleCfgInfoEntry 9 }

-- ibCBQoSMatchCpProtoCfgTable

ibCBQoSMatchCpProtoCfgTable OBJECT-TYPE
    SYNTAX SEQUENCE OF IbCBQoSMatchCpProtoCfgEntry
    MAX-ACCESS not-accessible
    STATUS current
    DESCRIPTION
        "A table of Matching CpProtocol Rule configuration information."
    ::= { ibCBQoSClassifierObjects 4 }

ibCBQoSMatchCpProtoCfgEntry OBJECT-TYPE
    SYNTAX IbCBQoSMatchCpProtoCfgEntry
    MAX-ACCESS not-accessible
    STATUS current
    DESCRIPTION
        "Matching CpProtocol Rule Configuration Information Entry."
    INDEX { ibCBQoSClassifierIndex, ibCBQoSMatchRuleIndex }
    ::= { ibCBQoSMatchCpProtoCfgTable 1 }

IbCBQoSMatchCpProtoCfgEntry ::=
    SEQUENCE
    {
        ibCBQoSMatchCpProtoIfNot
            INTEGER,
        ibCBQoSMatchCpProtoValue
            OCTET STRING,
        ibCBQoSMatchCpProtoRowStatus
            RowStatus
    }

ibCBQoSMatchCpProtoIfNot OBJECT-TYPE
    SYNTAX INTEGER
    {
        match(1),
        matchNot(2)
    }
    MAX-ACCESS read-create
    STATUS current
    DESCRIPTION
        "Whether the if-match rule is a match or matchNot statement.
         Software QoS supports match, matchNot.
         Hardware QoS supports match.
        "
    DEFVAL { match }
    ::= { ibCBQoSMatchCpProtoCfgEntry 1 }

ibCBQoSMatchCpProtoValue OBJECT-TYPE
    SYNTAX OCTET STRING (SIZE (0..255))
    MAX-ACCESS read-create
    STATUS current
    DESCRIPTION
        "Value of Cp Protocol, SIZE (1..23).  Up to 8 values can be input.
           for example: 1#2#3#4#5 means the match rule is
                        'if-match control-plane protocol arp arp-snooping
                        bgp bgp4+ bpdu-tunnel';
        arp: 1
        arp-snooping: 2
        bgp: 3
        bgp4+: 4
        bpdu-tunnel: 5
        cdp: 6
        cfd: 7
        dhcp: 8
        dhcp-snooping: 9
        dhcp6: 10
        dldp: 11
        dot1x: 12
        gmrp: 13
        gvrp: 14
        http: 15
        https: 16
        icmp: 17
        icmp6: 18
        igmp: 19
        igmp-snooping: 20
        irdp: 21
        isis: 22
        lacp: 23
        ldp: 24
        ldp6: 25
        lldp: 26
        mld: 27
        msdp: 28
        ntp: 29
        oam: 30
        ospf-multicast: 31
        ospf-unicast: 32
        ospf3-multicast: 33
        ospf3-unicast: 34
        pagp: 35
        pim-multicast: 36
        pim-unicast: 37
        pim6-multicast: 38
        pim6-unicast: 39
        portal: 40
        pppoe-negotiation: 41
        pvst: 42
        radius: 43
        rip: 44
        ripng: 45
        rrpp: 46
        rsvp: 47
        smart-link: 48
        snmp: 49
        stp: 50
        tacas: 51
        udld: 52
        udp-helper: 53
        vrrp: 54
        vrrp6: 55
        vtp: 56
        ip-option: 57
        ipv6-option: 58
        ssh: 59
        telnet: 60"
    ::= { ibCBQoSMatchCpProtoCfgEntry 2 }

ibCBQoSMatchCpProtoRowStatus OBJECT-TYPE
    SYNTAX RowStatus
    MAX-ACCESS read-create
    STATUS current
    DESCRIPTION
        "RowStatus."
    ::= { ibCBQoSMatchCpProtoCfgEntry 3 }

-- ibCBQoSMatchCpGroupCfgTable

ibCBQoSMatchCpGroupCfgTable OBJECT-TYPE
    SYNTAX SEQUENCE OF IbCBQoSMatchCpGroupCfgEntry
    MAX-ACCESS not-accessible
    STATUS current
    DESCRIPTION
        "A table of matching Cp protocol group rule configuration information."
    ::= { ibCBQoSClassifierObjects 5 }

ibCBQoSMatchCpGroupCfgEntry OBJECT-TYPE
    SYNTAX IbCBQoSMatchCpGroupCfgEntry
    MAX-ACCESS not-accessible
    STATUS current
    DESCRIPTION
        "Matching Cp protocol group Rule Configuration Information Entry."
    INDEX { ibCBQoSClassifierIndex, ibCBQoSMatchRuleIndex }
    ::= { ibCBQoSMatchCpGroupCfgTable 1 }

IbCBQoSMatchCpGroupCfgEntry ::=
    SEQUENCE
    {
        ibCBQoSMatchCpGroupIfNot
            INTEGER,
        ibCBQoSMatchCpGroupValue
            INTEGER,
        ibCBQoSMatchCpGroupRowStatus
            RowStatus
    }

ibCBQoSMatchCpGroupIfNot OBJECT-TYPE
    SYNTAX INTEGER
    {
        match(1),
        matchNot(2)
    }
    MAX-ACCESS read-create
    STATUS current
    DESCRIPTION
        "Whether the if-match rule is a match or matchNot statement.
         Software QoS supports match, matchNot.
         Hardware QoS supports match.
        "
    DEFVAL { match }
    ::= { ibCBQoSMatchCpGroupCfgEntry 1 }

ibCBQoSMatchCpGroupValue OBJECT-TYPE
    SYNTAX INTEGER
    {
        critical(1),
        important(2),
        management(3),
        normal(4),
        redirect(5),
        monitor(6),
        exception(7)
    }
    MAX-ACCESS read-create
    STATUS current
    DESCRIPTION
        "Type of Cp protocol group.
        "
    ::= { ibCBQoSMatchCpGroupCfgEntry 2 }

ibCBQoSMatchCpGroupRowStatus OBJECT-TYPE
    SYNTAX RowStatus
    MAX-ACCESS read-create
    STATUS current
    DESCRIPTION
        "RowStatus."
    ::= { ibCBQoSMatchCpGroupCfgEntry 3 }

-- ibCBQoSBehaviorObjects

ibCBQoSBehaviorObjects OBJECT IDENTIFIER ::= { ibCBQoSObjects 2 }

-- Traffic Behavior Next Index

ibCBQoSBehaviorIndexNext OBJECT-TYPE
    SYNTAX Integer32
    MAX-ACCESS read-only
    STATUS current
    DESCRIPTION
        "This object contains an appropriate value to be used for
         ibCBQoSBehaviorIndex when creating rows in the
         ibCBQoSBehaviorCfgInfoTable."
    ::= { ibCBQoSBehaviorObjects 1 }

-- Traffic Behavior

ibCBQoSBehaviorCfgInfoTable OBJECT-TYPE
    SYNTAX SEQUENCE OF IbCBQoSBehaviorCfgInfoEntry
    MAX-ACCESS not-accessible
    STATUS current
    DESCRIPTION
        "A table of Traffic Behavior configuration information."
    ::= { ibCBQoSBehaviorObjects 2 }

ibCBQoSBehaviorCfgInfoEntry OBJECT-TYPE
    SYNTAX IbCBQoSBehaviorCfgInfoEntry
    MAX-ACCESS not-accessible
    STATUS current
    DESCRIPTION
        "Traffic Behavior Configuration Information Entry."
    INDEX { ibCBQoSBehaviorIndex }
    ::= { ibCBQoSBehaviorCfgInfoTable 1 }

IbCBQoSBehaviorCfgInfoEntry ::=
    SEQUENCE
    {
        ibCBQoSBehaviorIndex
            Integer32,
        ibCBQoSBehaviorName
            OCTET STRING,
        ibCBQoSBehaviorType
            INTEGER,
        ibCBQoSBehaviorRowStatus
            RowStatus
    }

ibCBQoSBehaviorIndex OBJECT-TYPE
    SYNTAX Integer32
    MAX-ACCESS not-accessible
    STATUS current
    DESCRIPTION
        "Index of Traffic Behavior."
    ::= { ibCBQoSBehaviorCfgInfoEntry 1 }

ibCBQoSBehaviorName OBJECT-TYPE
    SYNTAX OCTET STRING (SIZE (1..31))
    MAX-ACCESS read-create
    STATUS current
    DESCRIPTION
        "Name of Traffic Behavior."
    ::= { ibCBQoSBehaviorCfgInfoEntry 2 }

ibCBQoSBehaviorType OBJECT-TYPE
    SYNTAX INTEGER
    {
        systemDefined(1),
        userDefined(2)
    }
    MAX-ACCESS read-only
    STATUS current
    DESCRIPTION
        "Type of behavior."
    ::= { ibCBQoSBehaviorCfgInfoEntry 3 }

ibCBQoSBehaviorRowStatus OBJECT-TYPE
    SYNTAX RowStatus
    MAX-ACCESS read-create
    STATUS current
    DESCRIPTION
        "RowStatus."
    ::= { ibCBQoSBehaviorCfgInfoEntry 4 }

-- CAR

ibCBQoSCarCfgInfoTable OBJECT-TYPE
    SYNTAX SEQUENCE OF IbCBQoSCarCfgInfoEntry
    MAX-ACCESS not-accessible
    STATUS current
    DESCRIPTION
        "A table of CAR feature configuration information."
    ::= { ibCBQoSBehaviorObjects 3 }

ibCBQoSCarCfgInfoEntry OBJECT-TYPE
    SYNTAX IbCBQoSCarCfgInfoEntry
    MAX-ACCESS not-accessible
    STATUS current
    DESCRIPTION
        "CAR Configuration Information Entry."
    INDEX { ibCBQoSBehaviorIndex }
    ::= { ibCBQoSCarCfgInfoTable 1 }

IbCBQoSCarCfgInfoEntry ::=
    SEQUENCE
    {
        ibCBQoSCarCir
            Unsigned32,
        ibCBQoSCarCbs
            Unsigned32,
        ibCBQoSCarEbs
            Unsigned32,
        ibCBQoSCarPir
            Unsigned32,
        ibCBQoSCarPbs
            Unsigned32,
        ibCBQoSCarGreenAction
            CarAction,
        ibCBQoSCarGreenRemarkValue
            Integer32,
        ibCBQoSCarYellowAction
            CarAction,
        ibCBQoSCarYellowRemarkValue
            Integer32,
        ibCBQoSCarRedAction
            CarAction,
        ibCBQoSCarRedRemarkValue
            Integer32,
        ibCBQoSCarPolicedPriorityMapType
            INTEGER,
        ibCBQoSCarRowStatus
            RowStatus
    }

ibCBQoSCarCir OBJECT-TYPE
    SYNTAX Unsigned32
    MAX-ACCESS read-create
    STATUS current
    DESCRIPTION
        "Committed Information Rate.  Unit: kbps."
    ::= { ibCBQoSCarCfgInfoEntry 1 }

ibCBQoSCarCbs OBJECT-TYPE
    SYNTAX Unsigned32
    MAX-ACCESS read-create
    STATUS current
    DESCRIPTION
        "Committed Burst Size.  Unit: byte."
    ::= { ibCBQoSCarCfgInfoEntry 2 }

ibCBQoSCarEbs OBJECT-TYPE
    SYNTAX Unsigned32
    MAX-ACCESS read-create
    STATUS current
    DESCRIPTION
        "Excess Burst Size.  Unit: byte.
         Only software QoS support this node.
         4294967295 is returned only when getting value from hardware QoS.
         4294967295 can't be set."
    DEFVAL {0}
    ::= { ibCBQoSCarCfgInfoEntry 3 }

ibCBQoSCarPir OBJECT-TYPE
    SYNTAX Unsigned32
    MAX-ACCESS read-create
    STATUS current
    DESCRIPTION
        "Peak Information Rate.  Unit: kbps.
         Only hardware QoS support this node.
         4294967295 is returned only when getting value from software QoS.
         4294967295 can't be set."
    ::= { ibCBQoSCarCfgInfoEntry 4 }

ibCBQoSCarPbs OBJECT-TYPE
    SYNTAX Unsigned32
    MAX-ACCESS read-create
    STATUS current
    DESCRIPTION
        "Peak Burst Size.  Unit: byte.
         Only hardware QoS support this node.
         4294967295 is returned only when getting value from software QoS.
         4294967295 can't be set."
    ::= { ibCBQoSCarCfgInfoEntry 5 }

ibCBQoSCarGreenAction OBJECT-TYPE
    SYNTAX CarAction
    MAX-ACCESS read-create
    STATUS current
    DESCRIPTION
        "Green Action
         Hardware QoS : pass, discard, remark.
         Software QoS : pass, discard, remark IP Precedence, remark DSCP, remark MPLS EXP.
        "
    DEFVAL {pass}
    ::= { ibCBQoSCarCfgInfoEntry 6 }

ibCBQoSCarGreenRemarkValue OBJECT-TYPE
    SYNTAX Integer32 (0..63|255)
    MAX-ACCESS read-create
    STATUS current
    DESCRIPTION
        "The value is to remark When green action is remarking.
         For remarking DSCP, the range is 0~63;
         For remarking IP Precedence and MPLS EXP, the range is 0~7;
         Only software QoS support this node.
         255 is returned only when getting value from hardware QoS or
         when action being pass, discard of software QoS.
         255 can't be set.
        "
    ::= { ibCBQoSCarCfgInfoEntry 7 }

ibCBQoSCarYellowAction OBJECT-TYPE
    SYNTAX CarAction
    MAX-ACCESS read-create
    STATUS current
    DESCRIPTION
        "Yellow Action:
         Only hardware QoS support this node.  Hardware QoS support pass, discard, remark.
         invalid is returned only when getting value from software QoS.
         invalid can't be set.
        "
    DEFVAL {remark}
    ::= { ibCBQoSCarCfgInfoEntry 8 }

ibCBQoSCarYellowRemarkValue OBJECT-TYPE
    SYNTAX Integer32 (0..63|255)
    MAX-ACCESS read-create
    STATUS current
    DESCRIPTION
        "The value is to remark When red action is remarking.
         For remarking DSCP, the range is 0~63;
         For remarking IP Precedence and MPLS EXP, the range is 0~7;
         Only software QoS support this node.
         255 is returned only when getting value from hardware QoS or
         when action being pass, discard of software QoS.
         255 can't be set."
    ::= { ibCBQoSCarCfgInfoEntry 9 }

ibCBQoSCarRedAction OBJECT-TYPE
    SYNTAX CarAction
    MAX-ACCESS read-create
    STATUS current
    DESCRIPTION
        "Red Action:
         Hardware QoS : pass, discard, remark.
         Software QoS : pass, discard, remark IP Precedence, remark DSCP, remark MPLS EXP.
        "
    DEFVAL {discard}
    ::= { ibCBQoSCarCfgInfoEntry 10 }

ibCBQoSCarRedRemarkValue OBJECT-TYPE
    SYNTAX Integer32 (0..63|255)
    MAX-ACCESS read-create
    STATUS current
    DESCRIPTION
        "The value is to remark When red action is remarking.
         For remarking DSCP, the range is 0~63;
         For remarking IP Precedence and MPLS EXP, the range is 0~7;
         Only software QoS support this node.
         255 is returned only when getting value from hardware QoS or
         when action being pass, discard of software QoS.
         255 can't be set."
    ::= { ibCBQoSCarCfgInfoEntry 11 }

ibCBQoSCarPolicedPriorityMapType OBJECT-TYPE
    SYNTAX INTEGER
    {
        none(0),
        policed-service-map(1),
        local-precedence-dot1p-map(2),
        drop-precedence-map(3)
    }
    MAX-ACCESS read-create
    STATUS current
    DESCRIPTION
        "Type of priority map."
    DEFVAL { none }
    ::= { ibCBQoSCarCfgInfoEntry 12 }

ibCBQoSCarRowStatus OBJECT-TYPE
    SYNTAX RowStatus
    MAX-ACCESS read-create
    STATUS current
    DESCRIPTION
        "RowStatus."
    ::= { ibCBQoSCarCfgInfoEntry 13 }

--
-- nodes of aggregative CAR applyed behavior
--
ibCBQoSAggregativeCarCfgInfoTable OBJECT-TYPE
    SYNTAX SEQUENCE OF IbCBQoSAggregativeCarCfgInfoEntry
    MAX-ACCESS not-accessible
    STATUS current
    DESCRIPTION
        "A table of aggregative CAR applied CBQ feature configuration information.
         Aggregative CAR is managed by IB-IFQOS2-MIB.  So, you can use IB-IFQOS2-MIB
         to get some details information about aggregative CAR.
        "
    ::= { ibCBQoSBehaviorObjects 4 }

ibCBQoSAggregativeCarCfgInfoEntry OBJECT-TYPE
    SYNTAX IbCBQoSAggregativeCarCfgInfoEntry
    MAX-ACCESS not-accessible
    STATUS current
    DESCRIPTION
        "Aggregative CAR feature applied CBQ configuration information entry."
    INDEX { ibCBQoSBehaviorIndex,
            ibCBQoSCarAggregativeCarIndex }
    ::= { ibCBQoSAggregativeCarCfgInfoTable 1 }

IbCBQoSAggregativeCarCfgInfoEntry ::=
    SEQUENCE
    {
        ibCBQoSCarAggregativeCarIndex
            Integer32,
        ibCBQoSCarAggregativeCarName
            OCTET STRING,
        ibCBQoSAggregativeCarRowStatus
            RowStatus
    }

ibCBQoSCarAggregativeCarIndex OBJECT-TYPE
    SYNTAX Integer32
    MAX-ACCESS not-accessible
    STATUS current
    DESCRIPTION
        "Index of aggregative CAR.
         It is equal to ibIfQoSAggregativeCarIndex at IB-IFQOS2-MIB.
        "
    ::= { ibCBQoSAggregativeCarCfgInfoEntry 1 }

ibCBQoSCarAggregativeCarName OBJECT-TYPE
    SYNTAX OCTET STRING (SIZE(1..31))
    MAX-ACCESS read-only
    STATUS current
    DESCRIPTION
        "Name of aggregative CAR.
         It is equal to ibIfQoSAggregativeCarName at IB-IFQOS2-MIB.
        "
    ::= { ibCBQoSAggregativeCarCfgInfoEntry 2 }

ibCBQoSAggregativeCarRowStatus OBJECT-TYPE
    SYNTAX RowStatus
    MAX-ACCESS read-create
    STATUS current
    DESCRIPTION
        "RowStatus."
    ::= { ibCBQoSAggregativeCarCfgInfoEntry 3 }

-- GTS

ibCBQoSGtsCfgInfoTable OBJECT-TYPE
    SYNTAX SEQUENCE OF IbCBQoSGtsCfgInfoEntry
    MAX-ACCESS not-accessible
    STATUS current
    DESCRIPTION
        "A table of GTS feature configuration information."
    ::= { ibCBQoSBehaviorObjects 5 }

ibCBQoSGtsCfgInfoEntry OBJECT-TYPE
    SYNTAX IbCBQoSGtsCfgInfoEntry
    MAX-ACCESS not-accessible
    STATUS current
    DESCRIPTION
        "GTS Configuration Information Entry."
    INDEX { ibCBQoSBehaviorIndex }
    ::= { ibCBQoSGtsCfgInfoTable 1 }

IbCBQoSGtsCfgInfoEntry ::=
    SEQUENCE
    {
        ibCBQoSGtsCir
            Unsigned32,
        ibCBQoSGtsCbs
            Unsigned32,
        ibCBQoSGtsEbs
            Unsigned32,
        ibCBQoSGtsQueueLength
            Integer32,
        ibCBQoSGtsRowStatus
            RowStatus,
        ibCBQoSGtsPir
            Unsigned32
    }

ibCBQoSGtsCir OBJECT-TYPE
    SYNTAX Unsigned32
    MAX-ACCESS read-create
    STATUS current
    DESCRIPTION
        "Committed Information Rate.  Unit: kbps"
    ::= { ibCBQoSGtsCfgInfoEntry 1 }

ibCBQoSGtsCbs OBJECT-TYPE
    SYNTAX Unsigned32
    MAX-ACCESS read-create
    STATUS current
    DESCRIPTION
        "Committed Burst Size.  Unit: byte
         default: max(cir*1/2,15000)"
    ::= { ibCBQoSGtsCfgInfoEntry 2 }

ibCBQoSGtsEbs OBJECT-TYPE
    SYNTAX Unsigned32
    MAX-ACCESS read-create
    STATUS current
    DESCRIPTION
        "Excess Burst Size.  Unit: byte"
    ::= { ibCBQoSGtsCfgInfoEntry 3 }

ibCBQoSGtsQueueLength OBJECT-TYPE
    SYNTAX Integer32 (1..1024)
    MAX-ACCESS read-create
    STATUS current
    DESCRIPTION
        "The length of GTS buffer."
    DEFVAL { 50 }
    ::= { ibCBQoSGtsCfgInfoEntry 4 }

ibCBQoSGtsRowStatus OBJECT-TYPE
    SYNTAX RowStatus
    MAX-ACCESS read-create
    STATUS current
    DESCRIPTION
        "RowStatus."
    ::= { ibCBQoSGtsCfgInfoEntry 5 }

ibCBQoSGtsPir OBJECT-TYPE
    SYNTAX Unsigned32
    UNITS  "kbps"
    MAX-ACCESS read-create
    STATUS current
    DESCRIPTION
        "Peak Information Rate."
    ::= { ibCBQoSGtsCfgInfoEntry 6 }

-- REMARK

ibCBQoSRemarkCfgInfoTable OBJECT-TYPE
    SYNTAX SEQUENCE OF IbCBQoSRemarkCfgInfoEntry
    MAX-ACCESS not-accessible
    STATUS current
    DESCRIPTION
        "A table of Remarking feature configuration information."
    ::= { ibCBQoSBehaviorObjects 6 }

ibCBQoSRemarkCfgInfoEntry OBJECT-TYPE
    SYNTAX IbCBQoSRemarkCfgInfoEntry
    MAX-ACCESS not-accessible
    STATUS current
    DESCRIPTION
        "Remarking Configuration Information Entry."
    INDEX { ibCBQoSBehaviorIndex, ibCBQoSRemarkType }
    ::= { ibCBQoSRemarkCfgInfoTable 1 }

IbCBQoSRemarkCfgInfoEntry ::=
    SEQUENCE
    {
        ibCBQoSRemarkType
            RemarkType,
        ibCBQoSRemarkValue
            Integer32,
        ibCBQoSRemarkRowStatus
            RowStatus
    }

ibCBQoSRemarkType OBJECT-TYPE
    SYNTAX RemarkType
    MAX-ACCESS not-accessible
    STATUS current
    DESCRIPTION
        "Remark type."
    ::= { ibCBQoSRemarkCfgInfoEntry 1 }

ibCBQoSRemarkValue OBJECT-TYPE
    SYNTAX Integer32 (0..4095)
    MAX-ACCESS read-create
    STATUS current
    DESCRIPTION
        "Value to remark:
         for IpPrecedence: 0~7
         for Dscp: 0~63
         for MplsExp: 0~7
         for Vlan8021p: 0~7
         for AtmClp: 0~1
         for FrDe: 0~1
         for VlanID: 1~4094
         for QosLocalID: 1~4095
         for DropPrecedence: 0~2
         for LocalPrecedence: 0~7
         for TopMostVlanID: 1~4094
         for SecondMplsExp: 0~7
        "
    ::= { ibCBQoSRemarkCfgInfoEntry 2 }

ibCBQoSRemarkRowStatus OBJECT-TYPE
    SYNTAX RowStatus
    MAX-ACCESS read-create
    STATUS current
    DESCRIPTION
        "RowStatus"
    ::= { ibCBQoSRemarkCfgInfoEntry 3 }

-- Queue

ibCBQoSQueueCfgInfoTable OBJECT-TYPE
    SYNTAX SEQUENCE OF IbCBQoSQueueCfgInfoEntry
    MAX-ACCESS not-accessible
    STATUS current
    DESCRIPTION
        "A table of queue feature configuration information."
    ::= { ibCBQoSBehaviorObjects 7 }

ibCBQoSQueueCfgInfoEntry OBJECT-TYPE
    SYNTAX IbCBQoSQueueCfgInfoEntry
    MAX-ACCESS not-accessible
    STATUS current
    DESCRIPTION
        "Queue Configuration Information Entry."
    INDEX { ibCBQoSBehaviorIndex }
    ::= { ibCBQoSQueueCfgInfoTable 1 }

IbCBQoSQueueCfgInfoEntry ::=
    SEQUENCE
    {
        ibCBQoSQueueType
            QueueType,
        ibCBQoSQueueDropType
            INTEGER,
        ibCBQoSQueueLength
            Integer32,
        ibCBQoSQueueBandwidthUnit
            QueueBandwidthUnit,
        ibCBQoSQueueBandwidthValue
            Integer32,
        ibCBQoSQueueCbs
            Integer32,
        ibCBQoSQueueQueueNumber
            INTEGER,
        ibCBQoSQueueCbsRatio
            Integer32,
        ibCBQoSQueueRowStatus
            RowStatus
    }

ibCBQoSQueueType OBJECT-TYPE
    SYNTAX QueueType
    MAX-ACCESS read-create
    STATUS current
    DESCRIPTION
        "Queueing Type:
         EF:(1)
         AF:(2)
         WFQ:(3)"
    ::= { ibCBQoSQueueCfgInfoEntry 1 }

ibCBQoSQueueDropType OBJECT-TYPE
    SYNTAX INTEGER
    {
        typeUnavailable(0),
        typeTailDrop(1),
        typeWred(2)
    }
    MAX-ACCESS read-create
    STATUS current
    DESCRIPTION
        "The drop type of queue.  Only valid for AF and WFQ queue.
         typeUnavailable is returned only when getting value about EF queue.
         typeUnavailable can't be set."
    DEFVAL {typeTailDrop}
    ::= { ibCBQoSQueueCfgInfoEntry 2 }

ibCBQoSQueueLength OBJECT-TYPE
    SYNTAX Integer32 (1..2147483647)
    MAX-ACCESS read-create
    STATUS current
    DESCRIPTION
        "The length of QueueLength.  Only valid for tail-drop type
         of AF and WFQ queue.
         2147483647 is returned only when getting value about EF queue
         or WRED type of AF and WFQ queue.
         2147483647 can't be set."
    DEFVAL { 64 }
    ::= { ibCBQoSQueueCfgInfoEntry 3 }

ibCBQoSQueueBandwidthUnit OBJECT-TYPE
    SYNTAX QueueBandwidthUnit
    MAX-ACCESS read-create
    STATUS current
    DESCRIPTION
        "Bandwidth Unit:
         Absolute, Unit Kbps (1)
         Percent, Unit % (2)
         RemainPercent, Unit % of remained bandwidth (3)
         Only valid for EF and AF queue.
         0 is returned only when getting value about WFQ queue.
         0 can't be set.
        "
    ::= { ibCBQoSQueueCfgInfoEntry 4 }

ibCBQoSQueueBandwidthValue OBJECT-TYPE
    SYNTAX Integer32 (1..100000000|2147483647)
    MAX-ACCESS read-create
    STATUS current
    DESCRIPTION
        "Bandwidth value:
         Absolute value: 8~100000000.  Unit: Kbps
         Percent value: 1~100.
         Only valid for EF and AF queue.
         2147483647 is returned only when getting value about WFQ queue.
         2147483647 can't be set."
    ::= { ibCBQoSQueueCfgInfoEntry 5 }

ibCBQoSQueueCbs OBJECT-TYPE
    SYNTAX Integer32 (32..1000000000|2147483647)
    MAX-ACCESS read-create
    STATUS current
    DESCRIPTION
        "Committed Burst Size.  Unit: byte.
         Only valid for EF queue.
         Default: If the value of 'ibCBQoSQueueBandwidthValue * 25' is
                  between 1500 and 2000000, the default value of this
                  object is 'ibCBQoSQueueBandwidthValue * 25';If the value of
                  'ibCBQoSQueueBandwidthValue * 25' is larger than or equal to
                  2000000, the default value of this object is 2000000;
                  If the value of 'ibCBQoSQueueBandwidthValue * 25' is
                  less than or equal to 1500, the default value of this object is 1500.
         2147483647 is returned only when getting value about AF or WFQ queue.
         2147483647 can't be set."
    ::= { ibCBQoSQueueCfgInfoEntry 6 }

ibCBQoSQueueQueueNumber OBJECT-TYPE
    SYNTAX INTEGER
    {
        unavailable(0),
        a16(16),
        a32(32),
        a64(64),
        a128(128),
        a256(256),
        a512(512),
        a1024(1024),
        a2048(2048),
        a4096(4096)
    }
    MAX-ACCESS read-create
    STATUS current
    DESCRIPTION
        "Max number of hashed queues (a power of 2).
         Only valid for WFQ.
         'unavailable' is returned only when getting value about AF or EF queue.
         'unavailable' can't be set."
    DEFVAL {a256}
    ::= { ibCBQoSQueueCfgInfoEntry 7 }

ibCBQoSQueueCbsRatio OBJECT-TYPE
    SYNTAX Integer32(25..500|2147483647)
    MAX-ACCESS read-create
    STATUS current
    DESCRIPTION
        "Committed Burst Size Ratio.
         CBS = CBS_Ratio * Bandwidth(k bps)
         Only valid for EF queue.
         2147483647 is returned only when getting value about AF or WFQ queue.
         2147483647 can't be set.
        "
    DEFVAL { 25 }
    ::= { ibCBQoSQueueCfgInfoEntry 8 }

ibCBQoSQueueRowStatus OBJECT-TYPE
    SYNTAX RowStatus
    MAX-ACCESS read-create
    STATUS current
    DESCRIPTION
        "RowStatus."
    ::= { ibCBQoSQueueCfgInfoEntry 9 }

-- WRED

ibCBQoSWredCfgInfoTable OBJECT-TYPE
    SYNTAX SEQUENCE OF IbCBQoSWredCfgInfoEntry
    MAX-ACCESS not-accessible
    STATUS current
    DESCRIPTION
        "A table of WRED configuration information."
    ::= { ibCBQoSBehaviorObjects 8 }

ibCBQoSWredCfgInfoEntry OBJECT-TYPE
    SYNTAX IbCBQoSWredCfgInfoEntry
    MAX-ACCESS not-accessible
    STATUS current
    DESCRIPTION
        "WRED Configuration Information Entry."
    INDEX { ibCBQoSBehaviorIndex }
    ::= { ibCBQoSWredCfgInfoTable 1 }

IbCBQoSWredCfgInfoEntry ::=
    SEQUENCE
    {
        ibCBQoSWredType
            WredType,
        ibCBQoSWredWeightConst
            Integer32
    }

ibCBQoSWredType OBJECT-TYPE
    SYNTAX WredType
    MAX-ACCESS read-write
    STATUS current
    DESCRIPTION
        "WRED type."
    DEFVAL { 1 }
    ::= { ibCBQoSWredCfgInfoEntry 1 }

ibCBQoSWredWeightConst OBJECT-TYPE
    SYNTAX Integer32 (1..16)
    MAX-ACCESS read-write
    STATUS current
    DESCRIPTION
        "Specify weight for calculating mean queue depth."
    DEFVAL { 9 }
    ::= { ibCBQoSWredCfgInfoEntry 2 }

-- WRED Class

ibCBQoSWredClassCfgInfoTable OBJECT-TYPE
    SYNTAX SEQUENCE OF IbCBQoSWredClassCfgInfoEntry
    MAX-ACCESS not-accessible
    STATUS current
    DESCRIPTION
        "A table of WRED configuration information."
    ::= { ibCBQoSBehaviorObjects 9 }

ibCBQoSWredClassCfgInfoEntry OBJECT-TYPE
    SYNTAX IbCBQoSWredClassCfgInfoEntry
    MAX-ACCESS not-accessible
    STATUS current
    DESCRIPTION
        "WRED Class Configuration Information Entry."
    INDEX { ibCBQoSBehaviorIndex, ibCBQoSWredClassValue }
    ::= { ibCBQoSWredClassCfgInfoTable 1 }

IbCBQoSWredClassCfgInfoEntry ::=
    SEQUENCE
    {
        ibCBQoSWredClassValue
            Integer32,
        ibCBQoSWredClassLowLimit
            Integer32,
        ibCBQoSWredClassHighLimit
            Integer32,
        ibCBQoSWredClassDiscardProb
            Integer32
    }

ibCBQoSWredClassValue OBJECT-TYPE
    SYNTAX Integer32 (0..63)
    MAX-ACCESS not-accessible
    STATUS current
    DESCRIPTION
        "The class value.
         For IP precedence based WRED, the class is IP precedence,
         and range is 0~7.
         For DSCP based WRED, the class is DSCP, and range is 0~63.
        "
    ::= { ibCBQoSWredClassCfgInfoEntry 1 }

ibCBQoSWredClassLowLimit OBJECT-TYPE
    SYNTAX Integer32 (1..1024)
    MAX-ACCESS read-write
    STATUS current
    DESCRIPTION
        "The low limit of queue depth."
    DEFVAL {10}
    ::= { ibCBQoSWredClassCfgInfoEntry 2 }

ibCBQoSWredClassHighLimit OBJECT-TYPE
    SYNTAX Integer32 (1..1024)
    MAX-ACCESS read-write
    STATUS current
    DESCRIPTION
        "The high limit of queue depth."
    DEFVAL { 30 }
    ::= { ibCBQoSWredClassCfgInfoEntry 3 }

ibCBQoSWredClassDiscardProb OBJECT-TYPE
    SYNTAX Integer32 (1..255)
    MAX-ACCESS read-write
    STATUS current
    DESCRIPTION
        "The discard probability denominator."
    DEFVAL { 10 }
    ::= { ibCBQoSWredClassCfgInfoEntry 4 }

-- Policy Route

ibCBQoSPolicyRouteCfgInfoTable OBJECT-TYPE
    SYNTAX SEQUENCE OF IbCBQoSPolicyRouteCfgInfoEntry
    MAX-ACCESS not-accessible
    STATUS current
    DESCRIPTION
        "A table of Policy Routing configuration information."
    ::= { ibCBQoSBehaviorObjects 10 }

ibCBQoSPolicyRouteCfgInfoEntry OBJECT-TYPE
    SYNTAX IbCBQoSPolicyRouteCfgInfoEntry
    MAX-ACCESS not-accessible
    STATUS current
    DESCRIPTION
        "Policy Routeing Configuration Information Entry."
    INDEX { ibCBQoSBehaviorIndex }
    ::= { ibCBQoSPolicyRouteCfgInfoTable 1 }

IbCBQoSPolicyRouteCfgInfoEntry ::=
    SEQUENCE
    {
        ibCBQoSPolicyRouteIpAddrType
            InetAddressType,
        ibCBQoSPolicyRouteNexthop
            InetAddress,
        ibCBQoSPolicyRouteBackup
            INTEGER,
        ibCBQoSPolicyRouteRowStatus
            RowStatus
    }

ibCBQoSPolicyRouteIpAddrType OBJECT-TYPE
    SYNTAX InetAddressType
    MAX-ACCESS read-create
    STATUS current
    DESCRIPTION
        "Type of InetAddress."
    ::= { ibCBQoSPolicyRouteCfgInfoEntry 1 }

ibCBQoSPolicyRouteNexthop OBJECT-TYPE
    SYNTAX InetAddress
    MAX-ACCESS read-create
    STATUS current
    DESCRIPTION
        "The next-hop ip address for redirection."
    ::= { ibCBQoSPolicyRouteCfgInfoEntry 2 }

ibCBQoSPolicyRouteBackup OBJECT-TYPE
    SYNTAX INTEGER
    {
        backup(1),
        notbackup(2)
    }
    MAX-ACCESS read-create
    STATUS current
    DESCRIPTION
        "Whether forward the packet according to the routing table
         When the next-hop IP address for redirection is not valid.
         Backup means forwarding.  NoBackup means not forwarding.
        "
    ::= { ibCBQoSPolicyRouteCfgInfoEntry 3 }

ibCBQoSPolicyRouteRowStatus OBJECT-TYPE
    SYNTAX RowStatus
    MAX-ACCESS read-create
    STATUS current
    DESCRIPTION
        "RowStatus."
    ::= { ibCBQoSPolicyRouteCfgInfoEntry 4 }

-- NAT

ibCBQoSNatCfgInfoTable OBJECT-TYPE
    SYNTAX SEQUENCE OF IbCBQoSNatCfgInfoEntry
    MAX-ACCESS not-accessible
    STATUS current
    DESCRIPTION
        "A table of Nat configuration information."
    ::= { ibCBQoSBehaviorObjects 11 }

ibCBQoSNatCfgInfoEntry OBJECT-TYPE
    SYNTAX IbCBQoSNatCfgInfoEntry
    MAX-ACCESS not-accessible
    STATUS current
    DESCRIPTION
        "Nat Configuration Information Entry."
    INDEX { ibCBQoSBehaviorIndex }
    ::= { ibCBQoSNatCfgInfoTable 1 }

IbCBQoSNatCfgInfoEntry ::=
    SEQUENCE
    {
        ibCBQoSNatMainNumber
            Integer32,
        ibCBQoSNatBackupNumber
            Integer32,
        ibCBQoSNatServiceClass
            Integer32,
        ibCBQoSNatRowStatus
            RowStatus
    }

ibCBQoSNatMainNumber OBJECT-TYPE
    SYNTAX Integer32 (1..255)
    MAX-ACCESS read-create
    STATUS current
    DESCRIPTION
        "The main ISP number."
    ::= { ibCBQoSNatCfgInfoEntry 1 }

ibCBQoSNatBackupNumber OBJECT-TYPE
    SYNTAX Integer32 (1..255)
    MAX-ACCESS read-create
    STATUS current
    DESCRIPTION
        "The backup ISP number"
    ::= { ibCBQoSNatCfgInfoEntry 2 }

ibCBQoSNatServiceClass OBJECT-TYPE
    SYNTAX Integer32 (1..4)
    MAX-ACCESS read-create
    STATUS current
    DESCRIPTION
        "The service class."
    DEFVAL { 2 }
    ::= { ibCBQoSNatCfgInfoEntry 3 }

ibCBQoSNatRowStatus OBJECT-TYPE
    SYNTAX RowStatus
    MAX-ACCESS read-create
    STATUS current
    DESCRIPTION
        "RowStatus."
    ::= { ibCBQoSNatCfgInfoEntry 4 }

-- Firewall

ibCBQoSFirewallCfgInfoTable OBJECT-TYPE
    SYNTAX SEQUENCE OF IbCBQoSFirewallCfgInfoEntry
    MAX-ACCESS not-accessible
    STATUS current
    DESCRIPTION
        "A table of firewall configuration information."
    ::= { ibCBQoSBehaviorObjects 12 }

ibCBQoSFirewallCfgInfoEntry OBJECT-TYPE
    SYNTAX IbCBQoSFirewallCfgInfoEntry
    MAX-ACCESS not-accessible
    STATUS current
    DESCRIPTION
        "Firewall configuration information entry."
    INDEX { ibCBQoSBehaviorIndex }
    ::= { ibCBQoSFirewallCfgInfoTable 1 }

IbCBQoSFirewallCfgInfoEntry ::=
    SEQUENCE
    {
        ibCBQoSFirewallAction
            INTEGER,
        ibCBQoSFirewallRowStatus
            RowStatus
    }

ibCBQoSFirewallAction OBJECT-TYPE
    SYNTAX INTEGER
    {
        permit(1),
        deny(2)
    }
    MAX-ACCESS read-create
    STATUS current
    DESCRIPTION
        "The firewall action "
    DEFVAL {permit}
    ::= { ibCBQoSFirewallCfgInfoEntry 1 }

ibCBQoSFirewallRowStatus OBJECT-TYPE
    SYNTAX RowStatus
    MAX-ACCESS read-create
    STATUS current
    DESCRIPTION
        "RowStatus."
    ::= { ibCBQoSFirewallCfgInfoEntry 2 }

-- Sampling behavior

ibCBQoSSamplingCfgInfoTable OBJECT-TYPE
    SYNTAX SEQUENCE OF IbCBQoSSamplingCfgInfoEntry
    MAX-ACCESS not-accessible
    STATUS current
    DESCRIPTION
        "A table of sampling configuration information."
    ::= { ibCBQoSBehaviorObjects 13 }

ibCBQoSSamplingCfgInfoEntry OBJECT-TYPE
    SYNTAX IbCBQoSSamplingCfgInfoEntry
    MAX-ACCESS not-accessible
    STATUS current
    DESCRIPTION
        "Sampling configuration information entry."
    INDEX { ibCBQoSBehaviorIndex }
    ::= { ibCBQoSSamplingCfgInfoTable 1 }

IbCBQoSSamplingCfgInfoEntry ::=
    SEQUENCE
    {
        ibCBQoSSamplingNum
            Integer32,
        ibCBQoSSamplingRowStatus
            RowStatus
    }

ibCBQoSSamplingNum OBJECT-TYPE
    SYNTAX Integer32 (1..16)
    MAX-ACCESS read-create
    STATUS current
    DESCRIPTION
        "The sampling number."
    ::= { ibCBQoSSamplingCfgInfoEntry 1 }

ibCBQoSSamplingRowStatus OBJECT-TYPE
    SYNTAX RowStatus
    MAX-ACCESS read-create
    STATUS current
    DESCRIPTION
        "RowStatus."
    ::= { ibCBQoSSamplingCfgInfoEntry 2 }

ibCBQoSAccountCfgInfoTable OBJECT-TYPE
    SYNTAX SEQUENCE OF IbCBQoSAccountCfgInfoEntry
    MAX-ACCESS not-accessible
    STATUS current
    DESCRIPTION
        "A table of account configuration information."
    ::= { ibCBQoSBehaviorObjects 14 }

ibCBQoSAccountCfgInfoEntry OBJECT-TYPE
    SYNTAX IbCBQoSAccountCfgInfoEntry
    MAX-ACCESS not-accessible
    STATUS current
    DESCRIPTION
        "Account configuration information entry."
    INDEX { ibCBQoSBehaviorIndex }
    ::= { ibCBQoSAccountCfgInfoTable 1 }

IbCBQoSAccountCfgInfoEntry ::=
    SEQUENCE
    {
        ibCBQoSAccounting
            TruthValue,
        ibCBQoSAccountRowStatus
            RowStatus,
        ibCBQoSAccountingMode
            INTEGER
    }

ibCBQoSAccounting OBJECT-TYPE
    SYNTAX TruthValue
    MAX-ACCESS read-create
    STATUS current
    DESCRIPTION
        "Account action."
    ::= { ibCBQoSAccountCfgInfoEntry 1 }

ibCBQoSAccountRowStatus OBJECT-TYPE
    SYNTAX RowStatus
    MAX-ACCESS read-create
    STATUS current
    DESCRIPTION
        "RowStatus."
    ::= { ibCBQoSAccountCfgInfoEntry 2 }

ibCBQoSAccountingMode OBJECT-TYPE
    SYNTAX INTEGER
    {
        auto(1),
        packet(2),
        byte(3),
        both(4)
    }
    MAX-ACCESS read-create
    STATUS current
    DESCRIPTION
        "Account mode."
    DEFVAL { auto }
    ::= { ibCBQoSAccountCfgInfoEntry 3 }

--
-- nodes of ibCBQoSRedirectCfgInfoTable
--
ibCBQoSRedirectCfgInfoTable OBJECT-TYPE
    SYNTAX SEQUENCE OF IbCBQoSRedirectCfgInfoEntry
    MAX-ACCESS not-accessible
    STATUS current
    DESCRIPTION
        "A table of redirect configuration information."
    ::= { ibCBQoSBehaviorObjects 15 }

ibCBQoSRedirectCfgInfoEntry OBJECT-TYPE
    SYNTAX IbCBQoSRedirectCfgInfoEntry
    MAX-ACCESS not-accessible
    STATUS current
    DESCRIPTION
        "Redirect configuration information entry."
    INDEX { ibCBQoSBehaviorIndex }
    ::= { ibCBQoSRedirectCfgInfoTable 1 }

IbCBQoSRedirectCfgInfoEntry ::=
    SEQUENCE
    {
        ibCBQoSRedirectType
            INTEGER,
        ibCBQoSRedirectIfIndex
            Integer32,
        ibCBQoSRedirectIpAddressType
            InetAddressType,
        ibCBQoSRedirectIpAddress1
            InetAddress,
        ibCBQoSRedirectIpAddress2
            InetAddress,
        ibCBQoSRedirectRowStatus
            RowStatus,
        ibCBQoSRedirectIpv6Interface1
            Integer32,
        ibCBQoSRedirectIpv6Interface2
            Integer32,
        ibCBQoSRedirectIfVlanID
            Integer32
    }

ibCBQoSRedirectType OBJECT-TYPE
    SYNTAX INTEGER
    {
        cpu(1),
        interface(2),
        nextHop(3)
    }
    MAX-ACCESS read-create
    STATUS current
    DESCRIPTION
        "The type of redirect."
    ::= { ibCBQoSRedirectCfgInfoEntry 1 }

ibCBQoSRedirectIfIndex OBJECT-TYPE
    SYNTAX Integer32
    MAX-ACCESS read-create
    STATUS current
    DESCRIPTION
        "ifIndex.
         Only the value of ibCBQoSRedirectType is interface,
         can be set this node.
        "
    DEFVAL { 0 }
    ::= { ibCBQoSRedirectCfgInfoEntry 2 }

ibCBQoSRedirectIpAddressType OBJECT-TYPE
    SYNTAX InetAddressType
    MAX-ACCESS read-create
    STATUS current
    DESCRIPTION
        "A value that represents a type of Internet address.
          unknown(0)  An unknown address type.  This value MUST
             be used if the value of the corresponding
             InetAddress object is a zero-length string.
             It may also be used to indicate an IP address
             which is not in one of the formats defined
             below.

          ipv4(1)     An IPv4 address as defined by the
             InetAddressIPv4 textual convention.

          ipv6(2)     A global IPv6 address as defined by the
             InetAddressIPv6 textual convention.

          ipv4z(3)    A non-global IPv4 address including a zone
             index as defined by the InetAddressIPv4z
             textual convention.

          ipv6z(4)    A non-global IPv6 address including a zone
             index as defined by the InetAddressIPv6z
             textual convention.

          dns(16)     A DNS domain name as defined by the
             InetAddressDNS textual convention.
          Now supports ipv4 and ipv6.
          Only the value of ibCBQoSRedirectType is next-hop,
          can be set this node and ibCBQoSRedirectIpAddress1 or ibCBQoSRedirectIpAddress2.
        "
    DEFVAL { unknown }
    ::= { ibCBQoSRedirectCfgInfoEntry 3 }

ibCBQoSRedirectIpAddress1 OBJECT-TYPE
    SYNTAX InetAddress
    MAX-ACCESS read-create
    STATUS current
    DESCRIPTION
        "IP Address.
         If the value of ibCBQoSRedirectType is not next-hop,
         zero-length string will be returned when getting.
         If the value of ibCBQoSRedirectIpAddressType is ipv6,
         this node is set necessarily.
        "
    ::= { ibCBQoSRedirectCfgInfoEntry 4 }

ibCBQoSRedirectIpAddress2 OBJECT-TYPE
    SYNTAX InetAddress
    MAX-ACCESS read-create
    STATUS current
    DESCRIPTION
        "IP Address.
         If the value of ibCBQoSRedirectType is not next-hop,
         zero-length string will be returned when getting.
         If the value of ibCBQoSRedirectIpAddressType is ipv6,
         this node is set optionally.
        "
    ::= { ibCBQoSRedirectCfgInfoEntry 5 }

ibCBQoSRedirectRowStatus OBJECT-TYPE
    SYNTAX RowStatus
    MAX-ACCESS read-create
    STATUS current
    DESCRIPTION
        "RowStatus."
    ::= { ibCBQoSRedirectCfgInfoEntry 6 }

ibCBQoSRedirectIpv6Interface1 OBJECT-TYPE
    SYNTAX Integer32
    MAX-ACCESS read-create
    STATUS current
    DESCRIPTION
        "IfIndex for ipv6 next hop .
         If and only if the value of ibCBQoSRedirectIpAddressType is ipv6
         and ibCBQoSRedirectIpAddress1 is set,
         this node can be set.
        "
    DEFVAL { 0 }
    ::= { ibCBQoSRedirectCfgInfoEntry 7 }

ibCBQoSRedirectIpv6Interface2 OBJECT-TYPE
    SYNTAX Integer32
    MAX-ACCESS read-create
    STATUS current
    DESCRIPTION
        "IfIndex for ipv6 next hop .
         If and only if the value of ibCBQoSRedirectIpAddressType is ipv6
         and ibCBQoSRedirectIpAddress2 is set,
         this node can be set.
        "
    DEFVAL { 0 }
    ::= { ibCBQoSRedirectCfgInfoEntry 8 }

ibCBQoSRedirectIfVlanID OBJECT-TYPE
    SYNTAX Integer32 (0..4094 |65535)
    MAX-ACCESS read-create
    STATUS current
    DESCRIPTION
        "VLAN-ID to tag.
         If and only if the value of ibCBQoSRedirectType is interface,
         this node can be set.
        "
    DEFVAL { 65535 }
    ::= { ibCBQoSRedirectCfgInfoEntry 9 }

--
-- nodes of ibCBQoSPriorityMapCfgInfoTable
--
ibCBQoSPriorityMapCfgInfoTable OBJECT-TYPE
    SYNTAX SEQUENCE OF IbCBQoSPriorityMapCfgInfoEntry
    MAX-ACCESS not-accessible
    STATUS current
    DESCRIPTION
        "A table of priority map configuration information."
    ::= { ibCBQoSBehaviorObjects 16 }

ibCBQoSPriorityMapCfgInfoEntry OBJECT-TYPE
    SYNTAX IbCBQoSPriorityMapCfgInfoEntry
    MAX-ACCESS not-accessible
    STATUS current
    DESCRIPTION
        "priority map configuration information entry."
    INDEX { ibCBQoSBehaviorIndex }
    ::= { ibCBQoSPriorityMapCfgInfoTable 1 }

IbCBQoSPriorityMapCfgInfoEntry ::=
    SEQUENCE
    {
        ibCBQoSPriorityMapImportType
            INTEGER,
        ibCBQoSPriorityMapExportType
            INTEGER,
        ibCBQoSPriorityMapGroupIndex
            Integer32,
        ibCBQoSPriorityMapGroupName
            OCTET STRING,
        ibCBQoSPriorityMapAuto
            INTEGER,
        ibCBQoSPriorityMapRowStatus
            RowStatus
    }

ibCBQoSPriorityMapImportType OBJECT-TYPE
    SYNTAX INTEGER
    {
        invalid(1),
        dscp(2),
        dot1p(3),
        exp(4),
        ipPrecedence(5),
        localPrecedence(6),
        dropPrecedence(7)
    }
    MAX-ACCESS read-create
    STATUS current
    DESCRIPTION
        "Import type of map."
    DEFVAL { invalid }
    ::= { ibCBQoSPriorityMapCfgInfoEntry 1 }

ibCBQoSPriorityMapExportType OBJECT-TYPE
    SYNTAX INTEGER
    {
        invalid(1),
        dscp(2),
        dot1p(3),
        exp(4),
        ipPrecedence(5),
        localPrecedence(6),
        dropPrecedence(7)
    }
    MAX-ACCESS read-create
    STATUS current
    DESCRIPTION
        "Export type of map."
    DEFVAL { invalid }
    ::= { ibCBQoSPriorityMapCfgInfoEntry 2 }

ibCBQoSPriorityMapGroupIndex OBJECT-TYPE
    SYNTAX Integer32
    MAX-ACCESS read-create
    STATUS current
    DESCRIPTION
        "Index of map group.
         Map group is managed by IB-IFQOS2-MIB.
        "
    ::= { ibCBQoSPriorityMapCfgInfoEntry 3 }

ibCBQoSPriorityMapGroupName OBJECT-TYPE
    SYNTAX OCTET STRING (SIZE(0..31))
    MAX-ACCESS read-only
    STATUS current
    DESCRIPTION
        "Name of map group.
         Map group is managed by IB-IFQOS2-MIB.
        "
    ::= { ibCBQoSPriorityMapCfgInfoEntry 4 }

ibCBQoSPriorityMapAuto OBJECT-TYPE
    SYNTAX INTEGER
    {
        invalid(1),
        autoDscp(2),
        autoDot1p(3),
        autoMplsExp(4),
        autoIp(5)
    }
    MAX-ACCESS read-create
    STATUS current
    DESCRIPTION
        "Type of priority MAP."
    DEFVAL { invalid }
    ::= { ibCBQoSPriorityMapCfgInfoEntry 5 }

ibCBQoSPriorityMapRowStatus OBJECT-TYPE
    SYNTAX RowStatus
    MAX-ACCESS read-create
    STATUS current
    DESCRIPTION
        "RowStatus."
    ::= { ibCBQoSPriorityMapCfgInfoEntry 6 }

--
-- nodes of ibCBQoSMirrorCfgInfoTable
--
ibCBQoSMirrorCfgInfoTable OBJECT-TYPE
    SYNTAX SEQUENCE OF IbCBQoSMirrorCfgInfoEntry
    MAX-ACCESS not-accessible
    STATUS current
    DESCRIPTION
        "A table of flow mirror configuration information."
    ::= { ibCBQoSBehaviorObjects 17 }

ibCBQoSMirrorCfgInfoEntry OBJECT-TYPE
    SYNTAX IbCBQoSMirrorCfgInfoEntry
    MAX-ACCESS not-accessible
    STATUS current
    DESCRIPTION
        "Flow mirror configuration information entry."
    INDEX { ibCBQoSBehaviorIndex }
    ::= { ibCBQoSMirrorCfgInfoTable 1 }

IbCBQoSMirrorCfgInfoEntry ::=
    SEQUENCE
    {
        ibCBQoSMirrorType
            INTEGER,
        ibCBQoSMirrorIfIndex
            OCTET STRING,
        ibCBQoSMirrorVlanID
            Integer32,
        ibCBQoSMirrorRowStatus
            RowStatus
    }

ibCBQoSMirrorType OBJECT-TYPE
    SYNTAX INTEGER
    {
        interface(1),
        cpu(2),
        vlan(3)
    }
    MAX-ACCESS read-create
    STATUS current
    DESCRIPTION
        "Type of flow mirror."
    ::= { ibCBQoSMirrorCfgInfoEntry 1 }

ibCBQoSMirrorIfIndex OBJECT-TYPE
    SYNTAX OCTET STRING (SIZE (0..255))
    MAX-ACCESS read-create
    STATUS current
    DESCRIPTION
        "IfIndex of destination interface.
         Only the value of ibCBQoSMirrorType is interface,
         can be set this node.
         For example: 1#11#111#1111 means the flow mirror
         destination ifindex is 1,11,111 and 1111.
         '#' is list separator for all IfIndex value.
        "
    ::= { ibCBQoSMirrorCfgInfoEntry 2 }

ibCBQoSMirrorVlanID OBJECT-TYPE
    SYNTAX Integer32 (0..4094)
    MAX-ACCESS read-create
    STATUS current
    DESCRIPTION
        "Destination vlan of flow mirror,
         Only the value of ibCBQoSMirrorType is vlan,
         can be set this node.
        "
    ::= { ibCBQoSMirrorCfgInfoEntry 3 }

ibCBQoSMirrorRowStatus OBJECT-TYPE
    SYNTAX RowStatus
    MAX-ACCESS read-create
    STATUS current
    DESCRIPTION
        "RowStatus."
    ::= { ibCBQoSMirrorCfgInfoEntry 4 }

--
-- nodes of ibCBQoSNestCfgInfoTable
--
ibCBQoSNestCfgInfoTable OBJECT-TYPE
    SYNTAX SEQUENCE OF IbCBQoSNestCfgInfoEntry
    MAX-ACCESS not-accessible
    STATUS current
    DESCRIPTION
        "Insert a service VLAN tag or customer VLAN tag into a packet.
        A VLAN tag contains the VLAN ID field and the 802.1p priority
        field.  Both the service VLAN ID and the customer VLAN ID can
        not be set at the same time.  One of them must be set.  The
        802.1p priority of the service VLAN tag and that of the
        customer VLAN tag can be set optionally.  However, both of
        them can not be set at the same time.  The new setting
        overwrites the previous one."
    ::= { ibCBQoSBehaviorObjects 18 }

ibCBQoSNestCfgInfoEntry OBJECT-TYPE
    SYNTAX IbCBQoSNestCfgInfoEntry
    MAX-ACCESS not-accessible
    STATUS current
    DESCRIPTION
        "VLAN nesting table entry."
    INDEX { ibCBQoSBehaviorIndex }
    ::= { ibCBQoSNestCfgInfoTable 1 }

IbCBQoSNestCfgInfoEntry ::=
    SEQUENCE
    {
        ibCBQoSNestServiceVlanID
            Integer32,
        ibCBQoSNestServiceDot1pValue
            Integer32,
        ibCBQoSNestCustomerVlanID
            Integer32,
        ibCBQoSNestCustomerDot1pValue
            Integer32,
        ibCBQoSNestRowStatus
            RowStatus
    }

ibCBQoSNestServiceVlanID OBJECT-TYPE
    SYNTAX Integer32 (1..4094|65535)
    MAX-ACCESS read-create
    STATUS current
    DESCRIPTION
        "VLAN ID of the service VLAN tag to be inserted.  If the
        customer VLAN tag has been configured, 65535 is returned
        for the service VLAN ID.  The service VLAN ID can not be
        set to 65535."
    ::= { ibCBQoSNestCfgInfoEntry 1 }

ibCBQoSNestServiceDot1pValue OBJECT-TYPE
    SYNTAX Integer32 (0..7|65535)
    MAX-ACCESS read-create
    STATUS current
    DESCRIPTION
        "802.1p priority value in the service VLAN tag to be inserted.
        If the 802.1p priority is not set, 65535 is returned.  The
        802.1p priority value can not be set to 65535."
    ::= { ibCBQoSNestCfgInfoEntry 2 }

ibCBQoSNestCustomerVlanID OBJECT-TYPE
    SYNTAX Integer32 (1..4094|65535)
    MAX-ACCESS read-create
    STATUS current
    DESCRIPTION
        "VLAN ID of the customer VLAN tag to be inserted.  If the
        service VLAN tag has been configured, 65535 is returned for
        the customer VLAN ID.  The customer VLAN ID can not be set
        to 65535."
    ::= { ibCBQoSNestCfgInfoEntry 3 }

ibCBQoSNestCustomerDot1pValue OBJECT-TYPE
    SYNTAX Integer32 (0..7|65535)
    MAX-ACCESS read-create
    STATUS current
    DESCRIPTION
        "802.1p priority value in the customer VLAN tag to be inserted.
        If the 802.1p priority is not set, 65535 is returned.  The
        802.1p priority value can not be set to 65535."
    ::= { ibCBQoSNestCfgInfoEntry 4 }

ibCBQoSNestRowStatus OBJECT-TYPE
    SYNTAX RowStatus
    MAX-ACCESS read-create
    STATUS current
    DESCRIPTION
        "RowStatus"
    ::= { ibCBQoSNestCfgInfoEntry 5 }

-- Nest Policy

ibCBQoSNestPolicyCfgInfoTable OBJECT-TYPE
    SYNTAX SEQUENCE OF IbCBQoSNestPolicyCfgInfoEntry
    MAX-ACCESS not-accessible
    STATUS current
    DESCRIPTION
        "This table is used for configuring nest policy."
    ::= { ibCBQoSBehaviorObjects 19 }

ibCBQoSNestPolicyCfgInfoEntry OBJECT-TYPE
    SYNTAX IbCBQoSNestPolicyCfgInfoEntry
    MAX-ACCESS not-accessible
    STATUS current
    DESCRIPTION
        "Nest policy configuration entry."
    INDEX { ibCBQoSBehaviorIndex }
    ::= { ibCBQoSNestPolicyCfgInfoTable 1 }

IbCBQoSNestPolicyCfgInfoEntry ::=
    SEQUENCE
    {
        ibCBQoSNestPolicyName
            OCTET STRING,
        ibCBQoSNestPolicyRowStatus
            RowStatus
    }

ibCBQoSNestPolicyName OBJECT-TYPE
    SYNTAX OCTET STRING (SIZE(1..31))
    MAX-ACCESS read-create
    STATUS current
    DESCRIPTION
        "Name of the nested policy."
    ::= { ibCBQoSNestPolicyCfgInfoEntry 1 }

ibCBQoSNestPolicyRowStatus OBJECT-TYPE
    SYNTAX RowStatus
    MAX-ACCESS read-create
    STATUS current
    DESCRIPTION
        "RowStatus"
    ::= { ibCBQoSNestPolicyCfgInfoEntry 2 }

--
-- nodes of ibCBQoSMirrorIfCfgInfoTable
--
ibCBQoSMirrorIfCfgInfoTable OBJECT-TYPE
    SYNTAX SEQUENCE OF IbCBQoSMirrorIfCfgInfoEntry
    MAX-ACCESS not-accessible
    STATUS current
    DESCRIPTION
        "A table of flow mirroring to interface configuration information."
    ::= { ibCBQoSBehaviorObjects 20 }

ibCBQoSMirrorIfCfgInfoEntry OBJECT-TYPE
    SYNTAX IbCBQoSMirrorIfCfgInfoEntry
    MAX-ACCESS not-accessible
    STATUS current
    DESCRIPTION
        "Flow mirroring to interface configuration information entry."
    INDEX { ibCBQoSBehaviorIndex, ibCBQoSMirrorIfMainIfIndex }
    ::= { ibCBQoSMirrorIfCfgInfoTable 1 }

IbCBQoSMirrorIfCfgInfoEntry ::=
    SEQUENCE
    {
        ibCBQoSMirrorIfMainIfIndex
            Integer32,
        ibCBQoSMirrorIfMainIfStatus
            INTEGER,
        ibCBQoSMirrorIfBackupIfIndex
            Integer32,
        ibCBQoSMirrorIfBackupIfStatus
            INTEGER,
        ibCBQoSMirrorIfRowStatus
            RowStatus
    }

ibCBQoSMirrorIfMainIfIndex OBJECT-TYPE
    SYNTAX Integer32
    MAX-ACCESS not-accessible
    STATUS current
    DESCRIPTION
        "IfIndex of mirror interface."
    ::= { ibCBQoSMirrorIfCfgInfoEntry 1 }

ibCBQoSMirrorIfMainIfStatus OBJECT-TYPE
    SYNTAX INTEGER
    {
        inactive(1),
        active(2)
    }
    MAX-ACCESS read-only
    STATUS current
    DESCRIPTION
        "Status of main interface."
    DEFVAL {active}
    ::= { ibCBQoSMirrorIfCfgInfoEntry 2 }

ibCBQoSMirrorIfBackupIfIndex OBJECT-TYPE
    SYNTAX Integer32
    MAX-ACCESS read-create
    STATUS current
    DESCRIPTION
        "IfIndex of backup mirror interface."
    ::= { ibCBQoSMirrorIfCfgInfoEntry 3 }

ibCBQoSMirrorIfBackupIfStatus OBJECT-TYPE
    SYNTAX INTEGER
    {
        inactive(1),
        active(2)
    }
    MAX-ACCESS read-only
    STATUS current
    DESCRIPTION
        "Status of backup interface."
    DEFVAL {active}
    ::= { ibCBQoSMirrorIfCfgInfoEntry 4 }

ibCBQoSMirrorIfRowStatus OBJECT-TYPE
    SYNTAX RowStatus
    MAX-ACCESS read-create
    STATUS current
    DESCRIPTION
        "RowStatus."
    ::= { ibCBQoSMirrorIfCfgInfoEntry 5 }

--
-- nodes of ibCBQoSColoredRemarkCfgTable
--
ibCBQoSColoredRemarkCfgTable OBJECT-TYPE
    SYNTAX SEQUENCE OF IbCBQoSColoredRemarkCfgEntry
    MAX-ACCESS not-accessible
    STATUS current
    DESCRIPTION
        "A table of colored remarking feature configuration information."
    ::= { ibCBQoSBehaviorObjects 21 }

ibCBQoSColoredRemarkCfgEntry OBJECT-TYPE
    SYNTAX IbCBQoSColoredRemarkCfgEntry
    MAX-ACCESS not-accessible
    STATUS current
    DESCRIPTION
        "Colored remarking configuration information entry."
    INDEX { ibCBQoSBehaviorIndex, ibCBQoSColoredRemarkType, ibCBQoSColoredRemarkColor }
    ::= { ibCBQoSColoredRemarkCfgTable 1 }

IbCBQoSColoredRemarkCfgEntry ::=
    SEQUENCE
    {
        ibCBQoSColoredRemarkType
            RemarkType,
        ibCBQoSColoredRemarkColor
            INTEGER,
        ibCBQoSColoredRemarkValue
            Integer32,
        ibCBQoSColoredRemarkRowStatus
            RowStatus
    }

ibCBQoSColoredRemarkType OBJECT-TYPE
    SYNTAX RemarkType
    MAX-ACCESS not-accessible
    STATUS current
    DESCRIPTION
        "Remark type."
    ::= { ibCBQoSColoredRemarkCfgEntry 1 }

ibCBQoSColoredRemarkColor OBJECT-TYPE
    SYNTAX INTEGER
    {
        green(1),
        yellow(2),
        red(3)
    }
    MAX-ACCESS not-accessible
    STATUS current
    DESCRIPTION
        "Remark color."
    ::= { ibCBQoSColoredRemarkCfgEntry 2 }

ibCBQoSColoredRemarkValue OBJECT-TYPE
    SYNTAX Integer32 (0..4095)
    MAX-ACCESS read-create
    STATUS current
    DESCRIPTION
        "Value to remark:
         for IpPrecedence: 0~7
         for Dscp: 0~63
         for MplsExp: 0~7
         for Vlan8021p: 0~7
         for AtmClp: 0~1
         for FrDe: 0~1
         for VlanID: 1~4094
         for QosLocalID: 1~4095
         for DropPrecedence: 0~2
         for LocalPrecedence: 0~7
         for TopMostVlanID: 1~4094
         for SecondMplsExp: 0~7
        "
    ::= { ibCBQoSColoredRemarkCfgEntry 3 }

ibCBQoSColoredRemarkRowStatus OBJECT-TYPE
    SYNTAX RowStatus
    MAX-ACCESS read-create
    STATUS current
    DESCRIPTION
        "RowStatus"
    ::= { ibCBQoSColoredRemarkCfgEntry 4 }

--
-- nodes of ibCBQoSPrimapCfgInfoTable
--
ibCBQoSPrimapCfgInfoTable OBJECT-TYPE
    SYNTAX SEQUENCE OF IbCBQoSPrimapCfgInfoEntry
    MAX-ACCESS not-accessible
    STATUS current
    DESCRIPTION
        "A table of referencing priority map configuration information."
    ::= { ibCBQoSBehaviorObjects 22 }

ibCBQoSPrimapCfgInfoEntry OBJECT-TYPE
    SYNTAX IbCBQoSPrimapCfgInfoEntry
    MAX-ACCESS not-accessible
    STATUS current
    DESCRIPTION
        "Referencing priority map configuration information entry."
    INDEX { ibCBQoSBehaviorIndex, ibCBQoSPrimapColorType, ibCBQoSPrePriMapTableType }
    ::= { ibCBQoSPrimapCfgInfoTable 1 }

IbCBQoSPrimapCfgInfoEntry ::=
    SEQUENCE
    {
        ibCBQoSPrimapColorType
            INTEGER,
        ibCBQoSPrePriMapTableType
            INTEGER,
        ibCBQoSPrimapRowStatus
            RowStatus
    }

ibCBQoSPrimapColorType OBJECT-TYPE
    SYNTAX INTEGER
    {
        noColorMap(1),
        colorMap(2)
    }
    MAX-ACCESS not-accessible
    STATUS current
    DESCRIPTION
        "Color type of priority map."
    ::= { ibCBQoSPrimapCfgInfoEntry 1 }

ibCBQoSPrePriMapTableType OBJECT-TYPE
    SYNTAX INTEGER
    {
        dot1pToLp(1),
        dot1pToDp(2),
        expToLp(3),
        dscpToLp(4),
        expToDp(5),
        dscpToDp(6),
        dscpToDot1p(7),
        dot1pToDscp(8),
        dscpToDscp(9),
        dscpToExp(10),
        expToDscp(11),
        expToDot1p(12),
        expToExp(13),
        lpToDot1p(14),
        dot1pToRpr(15),
        dscpToRpr(16),
        expToRpr(17),
        ippreToRpr(18),
        upToDot1p(19),
        upToDscp(20),
        upToExp(21),
        upToDp(22),
        upToLp(23),
        upToRpr(24),
        upToFc(25),
        lpTodscp(26),
        dot11eToLp(27),
        lpToDot11e(28),
        lpToLp(29),
        dot1pToExp(30),
        lpToExp(31),
        lpToDp(32),
        upToUp(33),
        dot1pToDot1p(34)
    }
    MAX-ACCESS not-accessible
    STATUS current
    DESCRIPTION
        "The type of pre-defined priority mapping table."
    ::= { ibCBQoSPrimapCfgInfoEntry 2 }

ibCBQoSPrimapRowStatus OBJECT-TYPE
    SYNTAX RowStatus
    MAX-ACCESS read-create
    STATUS current
    DESCRIPTION
        "RowStatus"
    ::= { ibCBQoSPrimapCfgInfoEntry 3 }

--
-- nodes of ibCBQoSColorMapDpCfgInfoTable
--
ibCBQoSColorMapDpCfgInfoTable OBJECT-TYPE
    SYNTAX SEQUENCE OF IbCBQoSColorMapDpCfgInfoEntry
    MAX-ACCESS not-accessible
    STATUS current
    DESCRIPTION
        "A table of referencing color-map-DP action configuration information."
    ::= { ibCBQoSBehaviorObjects 23 }

ibCBQoSColorMapDpCfgInfoEntry OBJECT-TYPE
    SYNTAX IbCBQoSColorMapDpCfgInfoEntry
    MAX-ACCESS not-accessible
    STATUS current
    DESCRIPTION
        "Referencing color-map-DP action configuration information entry."
    INDEX { ibCBQoSBehaviorIndex }
    ::= { ibCBQoSColorMapDpCfgInfoTable 1 }

IbCBQoSColorMapDpCfgInfoEntry ::=
    SEQUENCE
    {
        ibCBQoSColorMapDpEnable
            TruthValue,
        ibCBQoSColorMapDpRowStatus
            RowStatus
    }

ibCBQoSColorMapDpEnable OBJECT-TYPE
    SYNTAX TruthValue
    MAX-ACCESS read-create
    STATUS current
    DESCRIPTION
        "Color-map-DP enable status."
    ::= { ibCBQoSColorMapDpCfgInfoEntry 1 }

ibCBQoSColorMapDpRowStatus OBJECT-TYPE
    SYNTAX RowStatus
    MAX-ACCESS read-create
    STATUS current
    DESCRIPTION
        "RowStatus"
    ::= { ibCBQoSColorMapDpCfgInfoEntry 2 }

-- ibCBQoSPolicyObjects

ibCBQoSPolicyObjects OBJECT IDENTIFIER ::= { ibCBQoSObjects 3 }

-- Traffic Policy Next Index

ibCBQoSPolicyIndexNext OBJECT-TYPE
    SYNTAX Integer32
    MAX-ACCESS read-only
    STATUS current
    DESCRIPTION
        "This object contains an appropriate value to be used for
         ibCBQoSPolicyIndex when creating rows in the
         ibCBQoSPolicyCfgInfoTable."
    ::= { ibCBQoSPolicyObjects 1 }

-- Traffic Policy

ibCBQoSPolicyCfgInfoTable OBJECT-TYPE
    SYNTAX SEQUENCE OF IbCBQoSPolicyCfgInfoEntry
    MAX-ACCESS not-accessible
    STATUS current
    DESCRIPTION
        "A table of QoS policy configuration information."
    ::= { ibCBQoSPolicyObjects 2 }

ibCBQoSPolicyCfgInfoEntry OBJECT-TYPE
    SYNTAX IbCBQoSPolicyCfgInfoEntry
    MAX-ACCESS not-accessible
    STATUS current
    DESCRIPTION
        "Traffic policy configuration information entry."
    INDEX { ibCBQoSPolicyIndex }
    ::= { ibCBQoSPolicyCfgInfoTable 1 }

IbCBQoSPolicyCfgInfoEntry ::=
    SEQUENCE
    {
        ibCBQoSPolicyIndex
            Integer32,
        ibCBQoSPolicyName
            OCTET STRING,
        ibCBQoSPolicyClassCount
            Integer32,
        ibCBQoSPolicyConfigMode
            INTEGER,
        ibCBQoSPolicyType
            INTEGER,
        ibCBQoSPolicyClassNextIndex
            Integer32,
        ibCBQoSPolicyRowStatus
            RowStatus
    }

ibCBQoSPolicyIndex OBJECT-TYPE
    SYNTAX Integer32
    MAX-ACCESS not-accessible
    STATUS current
    DESCRIPTION
        "Index of Traffic Policy."
    ::= { ibCBQoSPolicyCfgInfoEntry 1 }

ibCBQoSPolicyName OBJECT-TYPE
    SYNTAX OCTET STRING (SIZE (1..31))
    MAX-ACCESS read-create
    STATUS current
    DESCRIPTION
        "Name of Traffic Policy."
    ::= { ibCBQoSPolicyCfgInfoEntry 2 }

ibCBQoSPolicyClassCount OBJECT-TYPE
    SYNTAX Integer32
    MAX-ACCESS read-only
    STATUS current
    DESCRIPTION
        "The counter of policy classes of policy."
    ::= { ibCBQoSPolicyCfgInfoEntry 3 }

ibCBQoSPolicyConfigMode OBJECT-TYPE
    SYNTAX INTEGER
    {
        unavailable(0),
        config(1),
        auto(2)
    }
    MAX-ACCESS read-create
    STATUS current
    DESCRIPTION
        "Configuration mode of Traffic Policy.
         Only hardware QoS support this node.
         'unavailable' is returned only when getting value from software QoS.
         'unavailable' can't be set."
    DEFVAL {config}
    ::= { ibCBQoSPolicyCfgInfoEntry 4 }

ibCBQoSPolicyType OBJECT-TYPE
    SYNTAX INTEGER
    {
        systemDefined(1),
        userDefined(2)
    }
    MAX-ACCESS read-only
    STATUS current
    DESCRIPTION
        "Type of policy."
    ::= { ibCBQoSPolicyCfgInfoEntry 5 }

ibCBQoSPolicyClassNextIndex OBJECT-TYPE
    SYNTAX Integer32
    MAX-ACCESS read-only
    STATUS current
    DESCRIPTION
        "This object contains an appropriate value to be used for
         ibCBQoSPolicyClassIndex when creating rows in the
         ibCBQoSPolicyClassCfgInfoTable.
        "
    ::= { ibCBQoSPolicyCfgInfoEntry 6 }

ibCBQoSPolicyRowStatus OBJECT-TYPE
    SYNTAX RowStatus
    MAX-ACCESS read-create
    STATUS current
    DESCRIPTION
        "RowStatus."
    ::= { ibCBQoSPolicyCfgInfoEntry 7 }

-- Classifier-Behavior in QoS policy

ibCBQoSPolicyClassCfgInfoTable OBJECT-TYPE
    SYNTAX SEQUENCE OF IbCBQoSPolicyClassCfgInfoEntry
    MAX-ACCESS not-accessible
    STATUS current
    DESCRIPTION
        "A table of QoS Policy classifier-behavior configuration information."
    ::= { ibCBQoSPolicyObjects 3 }

ibCBQoSPolicyClassCfgInfoEntry OBJECT-TYPE
    SYNTAX IbCBQoSPolicyClassCfgInfoEntry
    MAX-ACCESS not-accessible
    STATUS current
    DESCRIPTION
        "Traffic policy classifier-behavior configuration information entry."
    INDEX { ibCBQoSPolicyIndex, ibCBQoSPolicyClassIndex }
    ::= { ibCBQoSPolicyClassCfgInfoTable 1 }

IbCBQoSPolicyClassCfgInfoEntry ::=
    SEQUENCE
    {
        ibCBQoSPolicyClassIndex
            Integer32,
        ibCBQoSPolicyClassClassifierIndex
            Integer32,
        ibCBQoSPolicyClassClassifierName
            OCTET STRING,
        ibCBQoSPolicyClassBehaviorIndex
            Integer32,
        ibCBQoSPolicyClassBehaviorName
            OCTET STRING,
        ibCBQoSPolicyClassPrecedence
            Integer32,
        ibCBQoSPolicyClassRowStatus
            RowStatus,
        ibCBQoSPolicyClassMode
            INTEGER,
        ibCBQoSPolicyClassCfgOrder
            Integer32
    }

ibCBQoSPolicyClassIndex OBJECT-TYPE
    SYNTAX Integer32
    MAX-ACCESS not-accessible
    STATUS current
    DESCRIPTION
        "PolicyClass Index in a QoS policy."
    ::= { ibCBQoSPolicyClassCfgInfoEntry 1 }

ibCBQoSPolicyClassClassifierIndex OBJECT-TYPE
    SYNTAX Integer32
    MAX-ACCESS read-create
    STATUS current
    DESCRIPTION
        "Index of classifier applied by a policy.
         It should exist in ibCBQoSClassifierCfgInfoTable."
    ::= { ibCBQoSPolicyClassCfgInfoEntry 2 }

ibCBQoSPolicyClassClassifierName OBJECT-TYPE
    SYNTAX OCTET STRING (SIZE (1..31))
    MAX-ACCESS read-only
    STATUS current
    DESCRIPTION
        "Name of classifier applied by a policy.
         It is corresponding to ibCBQoSPolicyClassClassifierIndex."
    ::= { ibCBQoSPolicyClassCfgInfoEntry 3 }

ibCBQoSPolicyClassBehaviorIndex OBJECT-TYPE
    SYNTAX Integer32
    MAX-ACCESS read-create
    STATUS current
    DESCRIPTION
        "Index of Behavior applied by a policy.
         It should exist in ibCBQoSBehaviorCfgInfoTable."
    ::= { ibCBQoSPolicyClassCfgInfoEntry 4 }

ibCBQoSPolicyClassBehaviorName OBJECT-TYPE
    SYNTAX OCTET STRING (SIZE (1..31))
    MAX-ACCESS read-only
    STATUS current
    DESCRIPTION
        "Name of Behavior applied by a policy.
         It is corresponding to ibCBQoSPolicyClassBehaviorIndex."
    ::= { ibCBQoSPolicyClassCfgInfoEntry 5 }

ibCBQoSPolicyClassPrecedence OBJECT-TYPE
    SYNTAX Integer32 (0..16383|2147483647)
    MAX-ACCESS read-create
    STATUS current
    DESCRIPTION
        "The Precedence of the class in the policy.
         Only hardware QoS support this node.
         2147483647 is returned only when getting value from software QoS.
         2147483647 can't be set."
    ::= { ibCBQoSPolicyClassCfgInfoEntry 6 }

ibCBQoSPolicyClassRowStatus OBJECT-TYPE
    SYNTAX RowStatus
    MAX-ACCESS read-create
    STATUS current
    DESCRIPTION
        "RowStatus."
    ::= { ibCBQoSPolicyClassCfgInfoEntry 7 }

ibCBQoSPolicyClassMode OBJECT-TYPE
    SYNTAX INTEGER
    {
        modeNo(1),
        modeDot1q(2),
        modeQppb(3),
        modeIpSourceGuard(4),
        modeVoiceVlan(5),
        modeDCBX(6)
    }
    MAX-ACCESS read-create
    STATUS current
    DESCRIPTION
        "Set the mode of the classifier-behavior association.  The
        default mode modeNo is a normal mode.
        modeDot1q indicates that the association is used for VLAN mapping.
        modeQppb indicates that the association is used for BGP routing policy.
        modeIpSourceGuard indicates that the association is used for packets
        undergo IP source guard.
        modeVoiceVlan indicates that the association is used for voice data
        packets.
        modeDCBX indicates that the association is used for DCBX.
        "
    DEFVAL {modeNo}
    ::= { ibCBQoSPolicyClassCfgInfoEntry 8 }

ibCBQoSPolicyClassCfgOrder OBJECT-TYPE
    SYNTAX Integer32
    MAX-ACCESS read-only
    STATUS current
    DESCRIPTION
        "A QoS policy contains multiple classifier-behavior
        associations.  A node indicates the configuration order of
        the corresponding classifier-behavior association."
    ::= { ibCBQoSPolicyClassCfgInfoEntry 9 }

-- ibCBQoSApplyPolicyObjects

ibCBQoSApplyPolicyObjects OBJECT IDENTIFIER ::= { ibCBQoSObjects 4 }

-- Policy Instance on interface Table

ibCBQoSIfApplyPolicyTable OBJECT-TYPE
    SYNTAX SEQUENCE OF IbCBQoSIfApplyPolicyEntry
    MAX-ACCESS not-accessible
    STATUS current
    DESCRIPTION
        "A table of QoS policy instance."
    ::= { ibCBQoSApplyPolicyObjects 1 }

ibCBQoSIfApplyPolicyEntry OBJECT-TYPE
    SYNTAX IbCBQoSIfApplyPolicyEntry
    MAX-ACCESS not-accessible
    STATUS current
    DESCRIPTION
        "Policy applied on interface Configuration Information Entry."
    INDEX { ibCBQoSIfApplyPolicyIfIndex, ibCBQoSIfApplyPolicyDirection }
    ::= { ibCBQoSIfApplyPolicyTable 1 }

IbCBQoSIfApplyPolicyEntry ::=
    SEQUENCE
    {
        ibCBQoSIfApplyPolicyIfIndex
            Integer32,
        ibCBQoSIfApplyPolicyDirection
            DirectionType,
        ibCBQoSIfApplyPolicyName
            OCTET STRING,
        ibCBQoSIfApplyPolicyEnableDynamic
            INTEGER,
        ibCBQoSIfApplyPolicyRowStatus
            RowStatus,
        ibCBQoSIfApplyPolicyStatus
            INTEGER
    }

ibCBQoSIfApplyPolicyIfIndex OBJECT-TYPE
    SYNTAX Integer32
    MAX-ACCESS accessible-for-notify
    STATUS current
    DESCRIPTION
        "Interface Index, equal to ifIndex."
    ::= { ibCBQoSIfApplyPolicyEntry 1 }

ibCBQoSIfApplyPolicyDirection OBJECT-TYPE
    SYNTAX DirectionType
    MAX-ACCESS accessible-for-notify
    STATUS current
    DESCRIPTION
        "Policy direction:
         inbound (1)
         outbound (2)
        "
    ::= { ibCBQoSIfApplyPolicyEntry 2 }

ibCBQoSIfApplyPolicyName OBJECT-TYPE
    SYNTAX OCTET STRING (SIZE (1..31))
    MAX-ACCESS read-create
    STATUS current
    DESCRIPTION
        "Name of Traffic Policy."
    ::= { ibCBQoSIfApplyPolicyEntry 3 }

ibCBQoSIfApplyPolicyEnableDynamic OBJECT-TYPE
    SYNTAX INTEGER
    {
        unavailable(1),
        true(2),
        false(3)
    }
    MAX-ACCESS read-create
    STATUS current
    DESCRIPTION
        "If the value of it is specified 'true',Enable dynamic qos policy.
         'unavailable' is returned if device don't support dynamic QoS.
         'unavailable' can't be set.
        "
    ::= { ibCBQoSIfApplyPolicyEntry 4 }

ibCBQoSIfApplyPolicyRowStatus OBJECT-TYPE
    SYNTAX RowStatus
    MAX-ACCESS read-create
    STATUS current
    DESCRIPTION
        "RowStatus."
    ::= { ibCBQoSIfApplyPolicyEntry 5 }

ibCBQoSIfApplyPolicyStatus OBJECT-TYPE
    SYNTAX INTEGER
    {
        proccessing(1),
        success(2),
        partialItemFailed(3)
    }
    MAX-ACCESS read-only
    STATUS current
    DESCRIPTION
        "Status of policy applied on interface."
    ::= { ibCBQoSIfApplyPolicyEntry 6 }

-- Policy Instance on ATM PVC Table

ibCBQoSAtmPvcApplyPolicyTable OBJECT-TYPE
    SYNTAX SEQUENCE OF IbCBQoSAtmPvcApplyPolicyEntry
    MAX-ACCESS not-accessible
    STATUS current
    DESCRIPTION
        "A table of QoS policy instance."
    ::= { ibCBQoSApplyPolicyObjects 2 }

ibCBQoSAtmPvcApplyPolicyEntry OBJECT-TYPE
    SYNTAX IbCBQoSAtmPvcApplyPolicyEntry
    MAX-ACCESS not-accessible
    STATUS current
    DESCRIPTION
        "Policy applied on ATM PVC Configuration Information Entry."
    INDEX { ibCBQoSAtmPvcApplyPolicyIfIndex,
            ibCBQoSAtmPvcApplyPolicyVPI,
            ibCBQoSAtmPvcApplyPolicyVCI,
            ibCBQoSAtmPvcApplyPolicyDirection }
    ::= { ibCBQoSAtmPvcApplyPolicyTable 1 }

IbCBQoSAtmPvcApplyPolicyEntry ::=
    SEQUENCE
    {
        ibCBQoSAtmPvcApplyPolicyIfIndex
            Integer32,
        ibCBQoSAtmPvcApplyPolicyVPI
            Integer32,
        ibCBQoSAtmPvcApplyPolicyVCI
            Integer32,
        ibCBQoSAtmPvcApplyPolicyDirection
            DirectionType,
        ibCBQoSAtmPvcApplyPolicyName
            OCTET STRING,
        ibCBQoSAtmPvcApplyPolicyRowStatus
            RowStatus
    }

ibCBQoSAtmPvcApplyPolicyIfIndex OBJECT-TYPE
    SYNTAX Integer32
    MAX-ACCESS not-accessible
    STATUS current
    DESCRIPTION
        "ATM Interface Index, equal to ifIndex."
    ::= { ibCBQoSAtmPvcApplyPolicyEntry 1 }

ibCBQoSAtmPvcApplyPolicyVPI OBJECT-TYPE
    SYNTAX Integer32
    MAX-ACCESS not-accessible
    STATUS current
    DESCRIPTION
        "VPI value of ATM Interface."
    ::= { ibCBQoSAtmPvcApplyPolicyEntry 2 }

ibCBQoSAtmPvcApplyPolicyVCI OBJECT-TYPE
    SYNTAX Integer32
    MAX-ACCESS not-accessible
    STATUS current
    DESCRIPTION
        "VCI value of ATM Interface."
    ::= { ibCBQoSAtmPvcApplyPolicyEntry 3 }

ibCBQoSAtmPvcApplyPolicyDirection OBJECT-TYPE
    SYNTAX DirectionType
    MAX-ACCESS not-accessible
    STATUS current
    DESCRIPTION
        "Policy direction:
         inbound (1)
         outbound (2)"
    ::= { ibCBQoSAtmPvcApplyPolicyEntry 4 }

ibCBQoSAtmPvcApplyPolicyName OBJECT-TYPE
    SYNTAX OCTET STRING (SIZE (1..31))
    MAX-ACCESS read-create
    STATUS current
    DESCRIPTION
        "Name of Traffic Policy."
    ::= { ibCBQoSAtmPvcApplyPolicyEntry 5 }

ibCBQoSAtmPvcApplyPolicyRowStatus OBJECT-TYPE
    SYNTAX RowStatus
    MAX-ACCESS read-create
    STATUS current
    DESCRIPTION
        "RowStatus"
    ::= { ibCBQoSAtmPvcApplyPolicyEntry 6 }

-- Policy Instance on VLAN Table

ibCBQoSVlanApplyPolicyTable OBJECT-TYPE
    SYNTAX SEQUENCE OF IbCBQoSVlanApplyPolicyEntry
    MAX-ACCESS not-accessible
    STATUS current
    DESCRIPTION
        "A table of QoS policy instance."
    ::= { ibCBQoSApplyPolicyObjects 3 }

ibCBQoSVlanApplyPolicyEntry OBJECT-TYPE
    SYNTAX IbCBQoSVlanApplyPolicyEntry
    MAX-ACCESS not-accessible
    STATUS current
    DESCRIPTION
        "Policy applied on Ethernet VLAN Configuration Information Entry."
    INDEX { ibCBQoSVlanApplyPolicyVlanid,
            ibCBQoSVlanApplyPolicyDirection }
    ::= { ibCBQoSVlanApplyPolicyTable 1 }

IbCBQoSVlanApplyPolicyEntry ::=
    SEQUENCE
    {
        ibCBQoSVlanApplyPolicyVlanid
            Integer32,
        ibCBQoSVlanApplyPolicyDirection
            DirectionType,
        ibCBQoSVlanApplyPolicyName
            OCTET STRING,
        ibCBQoSVlanApplyPriority
            Integer32,
        ibCBQoSVlanApplyPolicyRowStatus
            RowStatus,
        ibCBQoSVlanApplyPolicyStatus
            INTEGER
    }

ibCBQoSVlanApplyPolicyVlanid OBJECT-TYPE
    SYNTAX Integer32
    MAX-ACCESS accessible-for-notify
    STATUS current
    DESCRIPTION
        "Vlan of Ethernet Interface."
    ::= { ibCBQoSVlanApplyPolicyEntry 1 }

ibCBQoSVlanApplyPolicyDirection OBJECT-TYPE
    SYNTAX DirectionType
    MAX-ACCESS accessible-for-notify
    STATUS current
    DESCRIPTION
        "Policy direction:
         inbound (1)
         outbound (2)"
    ::= { ibCBQoSVlanApplyPolicyEntry 2 }

ibCBQoSVlanApplyPolicyName OBJECT-TYPE
    SYNTAX OCTET STRING (SIZE (0..31))
    MAX-ACCESS read-create
    STATUS current
    DESCRIPTION
        "Name of Traffic Policy."
    ::= { ibCBQoSVlanApplyPolicyEntry 3 }

ibCBQoSVlanApplyPriority OBJECT-TYPE
    SYNTAX Integer32 (0..4095)
    MAX-ACCESS read-create
    STATUS current
    DESCRIPTION
        "The priority of policy."
    ::= { ibCBQoSVlanApplyPolicyEntry 4 }

ibCBQoSVlanApplyPolicyRowStatus OBJECT-TYPE
    SYNTAX RowStatus
    MAX-ACCESS read-create
    STATUS current
    DESCRIPTION
        "RowStatus."
    ::= { ibCBQoSVlanApplyPolicyEntry 5 }

ibCBQoSVlanApplyPolicyStatus OBJECT-TYPE
    SYNTAX INTEGER
    {
        proccessing(1),
        success(2),
        partialItemFailed(3)
    }
    MAX-ACCESS read-only
    STATUS current
    DESCRIPTION
        "Status of policy applied on VLAN."
    ::= { ibCBQoSVlanApplyPolicyEntry 6 }

-- Policy Instance on FR class Table

ibCBQoSFrClassApplyPolicyTable OBJECT-TYPE
    SYNTAX SEQUENCE OF IbCBQoSFrClassApplyPolicyEntry
    MAX-ACCESS not-accessible
    STATUS current
    DESCRIPTION
        "A table of QoS policy instance."
    ::= { ibCBQoSApplyPolicyObjects 4 }

ibCBQoSFrClassApplyPolicyEntry OBJECT-TYPE
    SYNTAX IbCBQoSFrClassApplyPolicyEntry
    MAX-ACCESS not-accessible
    STATUS current
    DESCRIPTION
        "Policy applied on FR class Configuration Information Entry."
    INDEX { ibCBQoSFrClassApplyPolicyFrClassName,
            ibCBQoSFrClassApplyPolicyDirection }
    ::= { ibCBQoSFrClassApplyPolicyTable 1 }

IbCBQoSFrClassApplyPolicyEntry ::=
    SEQUENCE
    {
        ibCBQoSFrClassApplyPolicyFrClassName
            OCTET STRING,
        ibCBQoSFrClassApplyPolicyDirection
            DirectionType,
        ibCBQoSFrClassApplyPolicyName
            OCTET STRING,
        ibCBQoSFrClassApplyPolicyRowStatus
            RowStatus
    }

ibCBQoSFrClassApplyPolicyFrClassName OBJECT-TYPE
    SYNTAX OCTET STRING (SIZE (1..31))
    MAX-ACCESS not-accessible
    STATUS current
    DESCRIPTION
        "The name of FR class."
    ::= { ibCBQoSFrClassApplyPolicyEntry 1 }

ibCBQoSFrClassApplyPolicyDirection OBJECT-TYPE
    SYNTAX DirectionType
    MAX-ACCESS not-accessible
    STATUS current
    DESCRIPTION
        "Policy direction:
         inbound (1)
         outbound (2)"
    ::= { ibCBQoSFrClassApplyPolicyEntry 2 }

ibCBQoSFrClassApplyPolicyName OBJECT-TYPE
    SYNTAX OCTET STRING (SIZE (1..31))
    MAX-ACCESS read-create
    STATUS current
    DESCRIPTION
        "Name of Traffic Policy."
    ::= { ibCBQoSFrClassApplyPolicyEntry 3 }

ibCBQoSFrClassApplyPolicyRowStatus OBJECT-TYPE
    SYNTAX RowStatus
    MAX-ACCESS read-create
    STATUS current
    DESCRIPTION
        "RowStatus."
    ::= { ibCBQoSFrClassApplyPolicyEntry 4 }

-- Policy Instance on FR PVC Table

ibCBQoSFrPvcApplyPolicyTable OBJECT-TYPE
    SYNTAX SEQUENCE OF IbCBQoSFrPvcApplyPolicyEntry
    MAX-ACCESS not-accessible
    STATUS current
    DESCRIPTION
        "A table of QoS policy instance."
    ::= { ibCBQoSApplyPolicyObjects 5 }

ibCBQoSFrPvcApplyPolicyEntry OBJECT-TYPE
    SYNTAX IbCBQoSFrPvcApplyPolicyEntry
    MAX-ACCESS not-accessible
    STATUS current
    DESCRIPTION
        "Policy applied on FR PVC Configuration Information Entry."
    INDEX { ibCBQoSFrPvcApplyPolicyIfIndex,
            ibCBQoSFrPvcApplyPolicyDlciNum,
            ibCBQoSFrPvcApplyPolicyDirection }
    ::= { ibCBQoSFrPvcApplyPolicyTable 1 }

IbCBQoSFrPvcApplyPolicyEntry ::=
    SEQUENCE
    {
        ibCBQoSFrPvcApplyPolicyIfIndex
            Integer32,
        ibCBQoSFrPvcApplyPolicyDlciNum
            Integer32,
        ibCBQoSFrPvcApplyPolicyDirection
            DirectionType,
        ibCBQoSFrPvcApplyPolicyName
            OCTET STRING,
        ibCBQoSFrPvcApplyPolicyRowStatus
            RowStatus
    }

ibCBQoSFrPvcApplyPolicyIfIndex OBJECT-TYPE
    SYNTAX Integer32
    MAX-ACCESS not-accessible
    STATUS current
    DESCRIPTION
        "Fr Interface Index, equal to ifIndex."
    ::= { ibCBQoSFrPvcApplyPolicyEntry 1 }

ibCBQoSFrPvcApplyPolicyDlciNum OBJECT-TYPE
    SYNTAX Integer32 (16..1007)
    MAX-ACCESS not-accessible
    STATUS current
    DESCRIPTION
        "Fr DLCI number."
    ::= { ibCBQoSFrPvcApplyPolicyEntry 2 }

ibCBQoSFrPvcApplyPolicyDirection OBJECT-TYPE
    SYNTAX DirectionType
    MAX-ACCESS not-accessible
    STATUS current
    DESCRIPTION
        "Policy direction:
         inbound (1)
         outbound (2)"
    ::= { ibCBQoSFrPvcApplyPolicyEntry 3 }

ibCBQoSFrPvcApplyPolicyName OBJECT-TYPE
    SYNTAX OCTET STRING (SIZE (1..31))
    MAX-ACCESS read-only
    STATUS current
    DESCRIPTION
        "Name of Traffic Policy."
    ::= { ibCBQoSFrPvcApplyPolicyEntry 4 }

ibCBQoSFrPvcApplyPolicyRowStatus OBJECT-TYPE
    SYNTAX RowStatus
    MAX-ACCESS read-only
    STATUS current
    DESCRIPTION
        "RowStatus."
    ::= { ibCBQoSFrPvcApplyPolicyEntry 5 }

-- Policy Instance on Global

ibCBQoSGlobalApplyTable OBJECT-TYPE
    SYNTAX SEQUENCE OF IbCBQoSGlobalApplyEntry
    MAX-ACCESS not-accessible
    STATUS current
    DESCRIPTION
        "A table of QoS policies applied globally.  A QoS policy
        applied globally takes effect on all ports of the device."
    ::= { ibCBQoSApplyPolicyObjects 6 }

ibCBQoSGlobalApplyEntry OBJECT-TYPE
    SYNTAX IbCBQoSGlobalApplyEntry
    MAX-ACCESS not-accessible
    STATUS current
    DESCRIPTION
        "A global policy entry."
    INDEX { ibCBQoSGlobalApplyDirection }
    ::= { ibCBQoSGlobalApplyTable 1 }

IbCBQoSGlobalApplyEntry ::=
    SEQUENCE
    {
        ibCBQoSGlobalApplyDirection
            DirectionType,
        ibCBQoSGlobalApplyName
            OCTET STRING,
        ibCBQoSGlobalApplyRowStatus
            RowStatus,
        ibCBQoSGlobalApplyStatus
            INTEGER
    }

ibCBQoSGlobalApplyDirection OBJECT-TYPE
    SYNTAX DirectionType
    MAX-ACCESS not-accessible
    STATUS current
    DESCRIPTION
        "Policy direction:
         inbound (1)
         outbound (2)"
    ::= { ibCBQoSGlobalApplyEntry 1 }

ibCBQoSGlobalApplyName OBJECT-TYPE
    SYNTAX OCTET STRING (SIZE (1..31))
    MAX-ACCESS read-create
    STATUS current
    DESCRIPTION
        "Name of a global policy."
    ::= { ibCBQoSGlobalApplyEntry 2 }

ibCBQoSGlobalApplyRowStatus OBJECT-TYPE
    SYNTAX RowStatus
    MAX-ACCESS read-create
    STATUS current
    DESCRIPTION
        "RowStatus."
    ::= { ibCBQoSGlobalApplyEntry 3 }

ibCBQoSGlobalApplyStatus OBJECT-TYPE
    SYNTAX INTEGER
    {
        proccessing(1),
        success(2),
        partialItemFailed(3)
    }
    MAX-ACCESS read-only
    STATUS current
    DESCRIPTION
        "Status of policy applied globally."
    ::= { ibCBQoSGlobalApplyEntry 4 }

-- Policy Instance on controlPlane

ibCBQoSCpApplyPolicyTable OBJECT-TYPE
    SYNTAX SEQUENCE OF IbCBQoSCpApplyPolicyEntry
    MAX-ACCESS not-accessible
    STATUS current
    DESCRIPTION
        "A table of QoS policies applied on control plane."
    ::= { ibCBQoSApplyPolicyObjects 7 }

ibCBQoSCpApplyPolicyEntry OBJECT-TYPE
    SYNTAX IbCBQoSCpApplyPolicyEntry
    MAX-ACCESS not-accessible
    STATUS current
    DESCRIPTION
        "Policy applied on control plane configuration information entry."
    INDEX { ibCBQoSCpApplyPolicyChassis,
            ibCBQoSCpApplyPolicySlot,
            ibCBQoSCpApplyPolicyDirection }
    ::= { ibCBQoSCpApplyPolicyTable 1 }

IbCBQoSCpApplyPolicyEntry ::=
    SEQUENCE
    {
        ibCBQoSCpApplyPolicyChassis
            Unsigned32,
        ibCBQoSCpApplyPolicySlot
            Unsigned32,
        ibCBQoSCpApplyPolicyDirection
            DirectionType,
        ibCBQoSCpApplyPolicyName
            OCTET STRING,
        ibCBQoSCpApplyPolicyStatus
            INTEGER,
        ibCBQoSCpApplyRowStatus
            RowStatus
    }

ibCBQoSCpApplyPolicyChassis OBJECT-TYPE
    SYNTAX Unsigned32
    MAX-ACCESS not-accessible
    STATUS current
    DESCRIPTION
        "Chassis number."
    ::= { ibCBQoSCpApplyPolicyEntry 1 }

ibCBQoSCpApplyPolicySlot OBJECT-TYPE
    SYNTAX Unsigned32
    MAX-ACCESS not-accessible
    STATUS current
    DESCRIPTION
        "Slot number."
    ::= { ibCBQoSCpApplyPolicyEntry 2 }

ibCBQoSCpApplyPolicyDirection OBJECT-TYPE
    SYNTAX DirectionType
    MAX-ACCESS not-accessible
    STATUS current
    DESCRIPTION
        "Policy direction:
         inbound (1)
         outbound (2)"
    ::= { ibCBQoSCpApplyPolicyEntry 3 }

ibCBQoSCpApplyPolicyName OBJECT-TYPE
    SYNTAX OCTET STRING (SIZE (1..31))
    MAX-ACCESS read-create
    STATUS current
    DESCRIPTION
        "Name of traffic policy."
    ::= { ibCBQoSCpApplyPolicyEntry 4 }

ibCBQoSCpApplyPolicyStatus OBJECT-TYPE
    SYNTAX INTEGER
    {
        proccessing(1),
        success(2),
        partialItemFailed(3)
    }
    MAX-ACCESS read-only
    STATUS current
    DESCRIPTION
        "Status of policy applied on control plane."
    ::= { ibCBQoSCpApplyPolicyEntry 5 }

ibCBQoSCpApplyRowStatus OBJECT-TYPE
    SYNTAX RowStatus
    MAX-ACCESS read-create
    STATUS current
    DESCRIPTION
        "RowStatus."
    ::= { ibCBQoSCpApplyPolicyEntry 6 }

-- Running statistics information

ibCBQoSApplyPolicyStaticsObjects OBJECT IDENTIFIER ::= { ibCBQoSObjects 5 }

-- Interface: policy Running statistics information

ibCBQoSIfStaticsObjects OBJECT IDENTIFIER ::= { ibCBQoSApplyPolicyStaticsObjects 1 }

-- Interface CBQ statistics

ibCBQoSIfCbqRunInfoTable OBJECT-TYPE
    SYNTAX SEQUENCE OF IbCBQoSIfCbqRunInfoEntry
    MAX-ACCESS not-accessible
    STATUS current
    DESCRIPTION
        "A table of interface CBQ Running statistics.
         When policy using queue behavior is applied on
         interface the interface will using Class Based Queuing."
    ::= { ibCBQoSIfStaticsObjects 1 }

ibCBQoSIfCbqRunInfoEntry OBJECT-TYPE
    SYNTAX IbCBQoSIfCbqRunInfoEntry
    MAX-ACCESS not-accessible
    STATUS current
    DESCRIPTION
        "Interface CBQ statistics entry."
    INDEX { ibCBQoSIfApplyPolicyIfIndex }
    ::= { ibCBQoSIfCbqRunInfoTable 1 }

IbCBQoSIfCbqRunInfoEntry ::=
    SEQUENCE
    {
        ibCBQoSIfCbqQueueSize
            Integer32,
        ibCBQoSIfCbqDiscard
            Counter64,
        ibCBQoSIfCbqEfQueueSize
            Integer32,
        ibCBQoSIfCbqAfQueueSize
            Integer32,
        ibCBQoSIfCbqBeQueueSize
            Integer32,
        ibCBQoSIfCbqBeActiveQueueNum
            Integer32,
        ibCBQoSIfCbqBeMaxActiveQueueNum
            Integer32,
        ibCBQoSIfCbqBeTotalQueueNum
            Integer32,
        ibCBQoSIfCbqAfAllocatedQueueNum
            Integer32
    }

ibCBQoSIfCbqQueueSize OBJECT-TYPE
    SYNTAX Integer32
    MAX-ACCESS read-only
    STATUS current
    DESCRIPTION
        "Packet number of CBQ queue"
    ::= { ibCBQoSIfCbqRunInfoEntry 1 }

ibCBQoSIfCbqDiscard OBJECT-TYPE
    SYNTAX Counter64
    MAX-ACCESS read-only
    STATUS current
    DESCRIPTION
        "The number of discarded packets which couldn't be enqueued."
    ::= { ibCBQoSIfCbqRunInfoEntry 2 }

ibCBQoSIfCbqEfQueueSize OBJECT-TYPE
    SYNTAX Integer32
    MAX-ACCESS read-only
    STATUS current
    DESCRIPTION
        "Packet number of EF queue."
    ::= { ibCBQoSIfCbqRunInfoEntry 3 }

ibCBQoSIfCbqAfQueueSize OBJECT-TYPE
    SYNTAX Integer32
    MAX-ACCESS read-only
    STATUS current
    DESCRIPTION
        "Packet number of AF queue."
    ::= { ibCBQoSIfCbqRunInfoEntry 4 }

ibCBQoSIfCbqBeQueueSize OBJECT-TYPE
    SYNTAX Integer32
    MAX-ACCESS read-only
    STATUS current
    DESCRIPTION
        "Packet number of BE queue."
    ::= { ibCBQoSIfCbqRunInfoEntry 5 }

ibCBQoSIfCbqBeActiveQueueNum OBJECT-TYPE
    SYNTAX Integer32
    MAX-ACCESS read-only
    STATUS current
    DESCRIPTION
        "The Packet number of Active BE Queue."
    ::= { ibCBQoSIfCbqRunInfoEntry 6 }

ibCBQoSIfCbqBeMaxActiveQueueNum OBJECT-TYPE
    SYNTAX Integer32
    MAX-ACCESS read-only
    STATUS current
    DESCRIPTION
        "The max Packet number of Active BE Queue."
    ::= { ibCBQoSIfCbqRunInfoEntry 7 }

ibCBQoSIfCbqBeTotalQueueNum OBJECT-TYPE
    SYNTAX Integer32
    MAX-ACCESS read-only
    STATUS current
    DESCRIPTION
        "The total Packet number of BE Queue."
    ::= { ibCBQoSIfCbqRunInfoEntry 8 }

ibCBQoSIfCbqAfAllocatedQueueNum OBJECT-TYPE
    SYNTAX Integer32
    MAX-ACCESS read-only
    STATUS current
    DESCRIPTION
        "The Allocated Packet number of AF Queue."
    ::= { ibCBQoSIfCbqRunInfoEntry 9 }

-- Class match statistics

ibCBQoSIfClassMatchRunInfoTable OBJECT-TYPE
    SYNTAX SEQUENCE OF IbCBQoSIfClassMatchRunInfoEntry
    MAX-ACCESS not-accessible
    STATUS current
    DESCRIPTION
        "A table of Running statistics for matching a classifier
         in a QoS policy applied on the interface."
    ::= { ibCBQoSIfStaticsObjects 2 }

ibCBQoSIfClassMatchRunInfoEntry OBJECT-TYPE
    SYNTAX IbCBQoSIfClassMatchRunInfoEntry
    MAX-ACCESS not-accessible
    STATUS current
    DESCRIPTION
        "Classifier's matching statistics information entry."
    INDEX { ibCBQoSIfApplyPolicyIfIndex,
            ibCBQoSIfApplyPolicyDirection,
            ibCBQoSPolicyClassIndex }
    ::= { ibCBQoSIfClassMatchRunInfoTable 1 }

IbCBQoSIfClassMatchRunInfoEntry ::=
    SEQUENCE
    {
        ibCBQoSIfClassMatchedPackets
            Counter64,
        ibCBQoSIfClassMatchedBytes
            Counter64,
        ibCBQoSIfClassAverageRate
            Counter64
    }

ibCBQoSIfClassMatchedPackets OBJECT-TYPE
    SYNTAX Counter64
    MAX-ACCESS read-only
    STATUS current
    DESCRIPTION
        "Number of packets matching a class in a QoS policy."
    ::= { ibCBQoSIfClassMatchRunInfoEntry 1 }

ibCBQoSIfClassMatchedBytes OBJECT-TYPE
    SYNTAX Counter64
    MAX-ACCESS read-only
    STATUS current
    DESCRIPTION
        "Number of bytes matching a class in a QoS policy.
         Only software QoS support this node."
    ::= { ibCBQoSIfClassMatchRunInfoEntry 2 }

ibCBQoSIfClassAverageRate OBJECT-TYPE
    SYNTAX Counter64
    MAX-ACCESS read-only
    STATUS current
    DESCRIPTION
        "Average rate matching a class of the last 5 minutes."
    ::= { ibCBQoSIfClassMatchRunInfoEntry 3 }

-- CAR statistics

ibCBQoSIfCarRunInfoTable OBJECT-TYPE
    SYNTAX SEQUENCE OF IbCBQoSIfCarRunInfoEntry
    MAX-ACCESS not-accessible
    STATUS current
    DESCRIPTION
        "A table of Running statistics for CAR
         in a QoS policy applied on the interface."
    ::= { ibCBQoSIfStaticsObjects 3 }

ibCBQoSIfCarRunInfoEntry OBJECT-TYPE
    SYNTAX IbCBQoSIfCarRunInfoEntry
    MAX-ACCESS not-accessible
    STATUS current
    DESCRIPTION
        "CAR statistics information entry."
    INDEX { ibCBQoSIfApplyPolicyIfIndex,
            ibCBQoSIfApplyPolicyDirection,
            ibCBQoSPolicyClassIndex }
    ::= { ibCBQoSIfCarRunInfoTable 1 }

IbCBQoSIfCarRunInfoEntry ::=
    SEQUENCE
    {
        ibCBQoSIfCarGreenPackets
            Counter64,
        ibCBQoSIfCarGreenBytes
            Counter64,
        ibCBQoSIfCarRedPackets
            Counter64,
        ibCBQoSIfCarRedBytes
            Counter64,
        ibCBQoSIfCarYellowPackets
            Counter64,
        ibCBQoSIfCarYellowBytes
            Counter64
    }

ibCBQoSIfCarGreenPackets OBJECT-TYPE
    SYNTAX Counter64
    MAX-ACCESS read-only
    STATUS current
    DESCRIPTION
        "Number of green packets."
    ::= { ibCBQoSIfCarRunInfoEntry 1 }

ibCBQoSIfCarGreenBytes OBJECT-TYPE
    SYNTAX Counter64
    MAX-ACCESS read-only
    STATUS current
    DESCRIPTION
        "Number of green bytes."
    ::= { ibCBQoSIfCarRunInfoEntry 2 }

ibCBQoSIfCarRedPackets OBJECT-TYPE
    SYNTAX Counter64
    MAX-ACCESS read-only
    STATUS current
    DESCRIPTION
        "Number of red packets."
    ::= { ibCBQoSIfCarRunInfoEntry 3 }

ibCBQoSIfCarRedBytes OBJECT-TYPE
    SYNTAX Counter64
    MAX-ACCESS read-only
    STATUS current
    DESCRIPTION
        "Number of red bytes."
    ::= { ibCBQoSIfCarRunInfoEntry 4 }

ibCBQoSIfCarYellowPackets OBJECT-TYPE
    SYNTAX Counter64
    MAX-ACCESS read-only
    STATUS current
    DESCRIPTION
        "Number of yellow packets."
    ::= { ibCBQoSIfCarRunInfoEntry 5 }

ibCBQoSIfCarYellowBytes OBJECT-TYPE
    SYNTAX Counter64
    MAX-ACCESS read-only
    STATUS current
    DESCRIPTION
        "Number of yellow bytes."
    ::= { ibCBQoSIfCarRunInfoEntry 6 }

-- GTS statistics

ibCBQoSIfGtsRunInfoTable OBJECT-TYPE
    SYNTAX SEQUENCE OF IbCBQoSIfGtsRunInfoEntry
    MAX-ACCESS not-accessible
    STATUS current
    DESCRIPTION
        "A table of Running statistics for GTS
         in a QoS policy applied on the interface."
    ::= { ibCBQoSIfStaticsObjects 4 }

ibCBQoSIfGtsRunInfoEntry OBJECT-TYPE
    SYNTAX IbCBQoSIfGtsRunInfoEntry
    MAX-ACCESS not-accessible
    STATUS current
    DESCRIPTION
        "GTS statistics entry."
    INDEX { ibCBQoSIfApplyPolicyIfIndex,
            ibCBQoSIfApplyPolicyDirection,
            ibCBQoSPolicyClassIndex }
    ::= { ibCBQoSIfGtsRunInfoTable 1 }

IbCBQoSIfGtsRunInfoEntry ::=
    SEQUENCE
    {
        ibCBQoSIfGtsPassedPackets
            Counter64,
        ibCBQoSIfGtsPassedBytes
            Counter64,
        ibCBQoSIfGtsDiscardedPackets
            Counter64,
        ibCBQoSIfGtsDiscardedBytes
            Counter64,
        ibCBQoSIfGtsDelayedPackets
            Counter64,
        ibCBQoSIfGtsDelayedBytes
            Counter64,
        ibCBQoSIfGtsQueueSize
            Integer32
    }

ibCBQoSIfGtsPassedPackets OBJECT-TYPE
    SYNTAX Counter64
    MAX-ACCESS read-only
    STATUS current
    DESCRIPTION
        "Number of packets passed by GTS."
    ::= { ibCBQoSIfGtsRunInfoEntry 1 }

ibCBQoSIfGtsPassedBytes OBJECT-TYPE
    SYNTAX Counter64
    MAX-ACCESS read-only
    STATUS current
    DESCRIPTION
        "Number of bytes passed by GTS."
    ::= { ibCBQoSIfGtsRunInfoEntry 2 }

ibCBQoSIfGtsDiscardedPackets OBJECT-TYPE
    SYNTAX Counter64
    MAX-ACCESS read-only
    STATUS current
    DESCRIPTION
        "Number of packets discarded by GTS."
    ::= { ibCBQoSIfGtsRunInfoEntry 3 }

ibCBQoSIfGtsDiscardedBytes OBJECT-TYPE
    SYNTAX Counter64
    MAX-ACCESS read-only
    STATUS current
    DESCRIPTION
        "Number of bytes discarded by GTS."
    ::= { ibCBQoSIfGtsRunInfoEntry 4 }

ibCBQoSIfGtsDelayedPackets OBJECT-TYPE
    SYNTAX Counter64
    MAX-ACCESS read-only
    STATUS current
    DESCRIPTION
        "Number of packets delayed by GTS."
    ::= { ibCBQoSIfGtsRunInfoEntry 5 }

ibCBQoSIfGtsDelayedBytes OBJECT-TYPE
    SYNTAX Counter64
    MAX-ACCESS read-only
    STATUS current
    DESCRIPTION
        "Number of bytes delayed by GTS."
    ::= { ibCBQoSIfGtsRunInfoEntry 6 }

ibCBQoSIfGtsQueueSize OBJECT-TYPE
    SYNTAX Integer32
    MAX-ACCESS read-only
    STATUS current
    DESCRIPTION
        "Packet number of GTS queue."
    ::= { ibCBQoSIfGtsRunInfoEntry 7 }

-- Remark statistics

ibCBQoSIfRemarkRunInfoTable OBJECT-TYPE
    SYNTAX SEQUENCE OF IbCBQoSIfRemarkRunInfoEntry
    MAX-ACCESS not-accessible
    STATUS current
    DESCRIPTION
        "A table of Running statistics for remarking
         in a QoS policy applied on the interface."
    ::= { ibCBQoSIfStaticsObjects 5 }

ibCBQoSIfRemarkRunInfoEntry OBJECT-TYPE
    SYNTAX IbCBQoSIfRemarkRunInfoEntry
    MAX-ACCESS not-accessible
    STATUS current
    DESCRIPTION
        "Remarking statistics entry."
    INDEX { ibCBQoSIfApplyPolicyIfIndex,
            ibCBQoSIfApplyPolicyDirection,
            ibCBQoSPolicyClassIndex }
    ::= { ibCBQoSIfRemarkRunInfoTable 1 }

IbCBQoSIfRemarkRunInfoEntry ::=
    SEQUENCE
    {
        ibCBQoSIfRemarkedPackets
            Counter64
    }

ibCBQoSIfRemarkedPackets OBJECT-TYPE
    SYNTAX Counter64
    MAX-ACCESS read-only
    STATUS current
    DESCRIPTION
        "Number of packets remarked."
    ::= { ibCBQoSIfRemarkRunInfoEntry 1 }

-- Queue statistics

ibCBQoSIfQueueRunInfoTable OBJECT-TYPE
    SYNTAX SEQUENCE OF IbCBQoSIfQueueRunInfoEntry
    MAX-ACCESS not-accessible
    STATUS current
    DESCRIPTION
        "A table of Running statistics for queue
         in a QoS policy applied on the interface."
    ::= { ibCBQoSIfStaticsObjects 6 }

ibCBQoSIfQueueRunInfoEntry OBJECT-TYPE
    SYNTAX IbCBQoSIfQueueRunInfoEntry
    MAX-ACCESS not-accessible
    STATUS current
    DESCRIPTION
        "Queue statistics entry."
    INDEX { ibCBQoSIfApplyPolicyIfIndex,
            ibCBQoSIfApplyPolicyDirection,
            ibCBQoSPolicyClassIndex }
    ::= { ibCBQoSIfQueueRunInfoTable 1 }

IbCBQoSIfQueueRunInfoEntry ::=
    SEQUENCE
    {
        ibCBQoSIfQueueMatchedPackets
            Counter64,
        ibCBQoSIfQueueMatchedBytes
            Counter64,
        ibCBQoSIfQueueEnqueuedPackets
            Counter64,
        ibCBQoSIfQueueEnqueuedBytes
            Counter64,
        ibCBQoSIfQueueDiscardedPackets
            Counter64,
        ibCBQoSIfQueueDiscardedBytes
            Counter64
    }

ibCBQoSIfQueueMatchedPackets OBJECT-TYPE
    SYNTAX Counter64
    MAX-ACCESS read-only
    STATUS current
    DESCRIPTION
        "Number of packets matched to enqueue."
    ::= { ibCBQoSIfQueueRunInfoEntry 1 }

ibCBQoSIfQueueMatchedBytes OBJECT-TYPE
    SYNTAX Counter64
    MAX-ACCESS read-only
    STATUS current
    DESCRIPTION
        "Number of bytes matched to enqueue."
    ::= { ibCBQoSIfQueueRunInfoEntry 2 }

ibCBQoSIfQueueEnqueuedPackets OBJECT-TYPE
    SYNTAX Counter64
    MAX-ACCESS read-only
    STATUS current
    DESCRIPTION
        "Number of packets enqueued."
    ::= { ibCBQoSIfQueueRunInfoEntry 3 }

ibCBQoSIfQueueEnqueuedBytes OBJECT-TYPE
    SYNTAX Counter64
    MAX-ACCESS read-only
    STATUS current
    DESCRIPTION
        "Number of bytes enqueued."
    ::= { ibCBQoSIfQueueRunInfoEntry 4 }

ibCBQoSIfQueueDiscardedPackets OBJECT-TYPE
    SYNTAX Counter64
    MAX-ACCESS read-only
    STATUS current
    DESCRIPTION
        "Number of packets discarded when enqueued by discard method."
    ::= { ibCBQoSIfQueueRunInfoEntry 5 }

ibCBQoSIfQueueDiscardedBytes OBJECT-TYPE
    SYNTAX Counter64
    MAX-ACCESS read-only
    STATUS current
    DESCRIPTION
        "Number of bytes discarded when enqueued by discard method."
    ::= { ibCBQoSIfQueueRunInfoEntry 6 }

-- WRED statistics

ibCBQoSIfWredRunInfoTable OBJECT-TYPE
    SYNTAX SEQUENCE OF IbCBQoSIfWredRunInfoEntry
    MAX-ACCESS not-accessible
    STATUS current
    DESCRIPTION
        "A table of Running statistics for WRED
         in a QoS policy applied on the interface."
    ::= { ibCBQoSIfStaticsObjects 7 }

ibCBQoSIfWredRunInfoEntry OBJECT-TYPE
    SYNTAX IbCBQoSIfWredRunInfoEntry
    MAX-ACCESS not-accessible
    STATUS current
    DESCRIPTION
        "WRED statistics entry."
    INDEX { ibCBQoSIfApplyPolicyIfIndex,
            ibCBQoSIfApplyPolicyDirection,
            ibCBQoSPolicyClassIndex,
            ibCBQoSWredClassValue }
    ::= { ibCBQoSIfWredRunInfoTable 1 }

IbCBQoSIfWredRunInfoEntry ::=
    SEQUENCE
    {
        ibCBQoSIfWredRandomDiscardedPackets
            Counter64,
        ibCBQoSIfWredTailDiscardedPackets
            Counter64
    }

ibCBQoSIfWredRandomDiscardedPackets OBJECT-TYPE
    SYNTAX Counter64
    MAX-ACCESS read-only
    STATUS current
    DESCRIPTION
        "Number of packets that random-discarded by WRED."
    ::= { ibCBQoSIfWredRunInfoEntry 1 }

ibCBQoSIfWredTailDiscardedPackets OBJECT-TYPE
    SYNTAX Counter64
    MAX-ACCESS read-only
    STATUS current
    DESCRIPTION
        "Number of packets that tail-discarded by WRED."
    ::= { ibCBQoSIfWredRunInfoEntry 2 }

--
-- nodes of ibCBQoSIfAccountingRunInfoTable
--
ibCBQoSIfAccountingRunInfoTable OBJECT-TYPE
    SYNTAX SEQUENCE OF IbCBQoSIfAccountingRunInfoEntry
    MAX-ACCESS not-accessible
    STATUS current
    DESCRIPTION
        "A table of Running statistics for account
         in a QoS policy applied on the interface."
    ::= { ibCBQoSIfStaticsObjects 8 }

ibCBQoSIfAccountingRunInfoEntry OBJECT-TYPE
    SYNTAX IbCBQoSIfAccountingRunInfoEntry
    MAX-ACCESS not-accessible
    STATUS current
    DESCRIPTION
        "Account statistics entry."
    INDEX { ibCBQoSIfApplyPolicyIfIndex,
            ibCBQoSIfApplyPolicyDirection,
            ibCBQoSPolicyClassIndex
          }
    ::= { ibCBQoSIfAccountingRunInfoTable 1 }

IbCBQoSIfAccountingRunInfoEntry ::=
    SEQUENCE
    {
        ibCBQoSIfAccountingPackets
            Counter64,
        ibCBQoSIfAccountingBytes
            Counter64
    }

ibCBQoSIfAccountingPackets OBJECT-TYPE
    SYNTAX Counter64
    MAX-ACCESS read-only
    STATUS current
    DESCRIPTION
        "Number of packets."
    ::= { ibCBQoSIfAccountingRunInfoEntry 1 }

ibCBQoSIfAccountingBytes OBJECT-TYPE
    SYNTAX Counter64
    MAX-ACCESS read-only
    STATUS current
    DESCRIPTION
        "Number of bytes."
    ::= { ibCBQoSIfAccountingRunInfoEntry 2 }

-- ATM Interface PVC: policy Running statistics information

ibCBQoSAtmPvcStaticsObjects OBJECT IDENTIFIER ::= { ibCBQoSApplyPolicyStaticsObjects 2 }

-- ATM PVC CBQ statistics

ibCBQoSAtmPvcCbqRunInfoTable OBJECT-TYPE
    SYNTAX SEQUENCE OF IbCBQoSAtmPvcCbqRunInfoEntry
    MAX-ACCESS not-accessible
    STATUS current
    DESCRIPTION
        "A table of ATM PVC CBQ Running statistics.
         When policy using queue behavior is applied on
         ATM PVC.  ATM PVC will using Class Based Queuing."
    ::= { ibCBQoSAtmPvcStaticsObjects 1 }

ibCBQoSAtmPvcCbqRunInfoEntry OBJECT-TYPE
    SYNTAX IbCBQoSAtmPvcCbqRunInfoEntry
    MAX-ACCESS not-accessible
    STATUS current
    DESCRIPTION
        "FR PVC CBQ statistics entry."
    INDEX { ibCBQoSAtmPvcApplyPolicyIfIndex,
            ibCBQoSAtmPvcApplyPolicyVPI,
            ibCBQoSAtmPvcApplyPolicyVCI }
    ::= { ibCBQoSAtmPvcCbqRunInfoTable 1 }

IbCBQoSAtmPvcCbqRunInfoEntry ::=
    SEQUENCE
    {
        ibCBQoSAtmPvcCbqQueueSize
            Integer32,
        ibCBQoSAtmPvcCbqDiscard
            Counter64,
        ibCBQoSAtmPvcCbqEfQueueSize
            Integer32,
        ibCBQoSAtmPvcCbqAfQueueSize
            Integer32,
        ibCBQoSAtmPvcCbqBeQueueSize
            Integer32,
        ibCBQoSAtmPvcCbqBeActiveQueueNum
            Integer32,
        ibCBQoSAtmPvcCbqBeMaxActiveQueueNum
            Integer32,
        ibCBQoSAtmPvcCbqBeTotalQueueNum
            Integer32,
        ibCBQoSAtmPvcCbqAfAllocatedQueueNum
            Integer32
    }

ibCBQoSAtmPvcCbqQueueSize OBJECT-TYPE
    SYNTAX Integer32
    MAX-ACCESS read-only
    STATUS current
    DESCRIPTION
        "Packet number of CBQ queue."
    ::= { ibCBQoSAtmPvcCbqRunInfoEntry 1 }

ibCBQoSAtmPvcCbqDiscard OBJECT-TYPE
    SYNTAX Counter64
    MAX-ACCESS read-only
    STATUS current
    DESCRIPTION
        "The number of discarded packets which couldn't be enqueued."
    ::= { ibCBQoSAtmPvcCbqRunInfoEntry 2 }

ibCBQoSAtmPvcCbqEfQueueSize OBJECT-TYPE
    SYNTAX Integer32
    MAX-ACCESS read-only
    STATUS current
    DESCRIPTION
        "Packet number of EF queue."
    ::= { ibCBQoSAtmPvcCbqRunInfoEntry 3 }

ibCBQoSAtmPvcCbqAfQueueSize OBJECT-TYPE
    SYNTAX Integer32
    MAX-ACCESS read-only
    STATUS current
    DESCRIPTION
        "Packet number of AF queue."
    ::= { ibCBQoSAtmPvcCbqRunInfoEntry 4 }

ibCBQoSAtmPvcCbqBeQueueSize OBJECT-TYPE
    SYNTAX Integer32
    MAX-ACCESS read-only
    STATUS current
    DESCRIPTION
        "Packet number of BE queue."
    ::= { ibCBQoSAtmPvcCbqRunInfoEntry 5 }

ibCBQoSAtmPvcCbqBeActiveQueueNum OBJECT-TYPE
    SYNTAX Integer32
    MAX-ACCESS read-only
    STATUS current
    DESCRIPTION
        "The packet number of Active Be Queue."
    ::= { ibCBQoSAtmPvcCbqRunInfoEntry 6 }

ibCBQoSAtmPvcCbqBeMaxActiveQueueNum OBJECT-TYPE
    SYNTAX Integer32
    MAX-ACCESS read-only
    STATUS current
    DESCRIPTION
        "The max packet number of Active Be Queue."
    ::= { ibCBQoSAtmPvcCbqRunInfoEntry 7 }

ibCBQoSAtmPvcCbqBeTotalQueueNum OBJECT-TYPE
    SYNTAX Integer32
    MAX-ACCESS read-only
    STATUS current
    DESCRIPTION
        "The total packet number of Be Queue."
    ::= { ibCBQoSAtmPvcCbqRunInfoEntry 8 }

ibCBQoSAtmPvcCbqAfAllocatedQueueNum OBJECT-TYPE
    SYNTAX Integer32
    MAX-ACCESS read-only
    STATUS current
    DESCRIPTION
        "The Allocated packet number of AF Queue."
    ::= { ibCBQoSAtmPvcCbqRunInfoEntry 9 }

-- Class match statistics

ibCBQoSAtmPvcClassMatchRunInfoTable OBJECT-TYPE
    SYNTAX SEQUENCE OF IbCBQoSAtmPvcClassMatchRunInfoEntry
    MAX-ACCESS not-accessible
    STATUS current
    DESCRIPTION
        "A table of Running statistics for matching a classifier
         in a QoS policy applied on ATM PVC."
    ::= { ibCBQoSAtmPvcStaticsObjects 2 }

ibCBQoSAtmPvcClassMatchRunInfoEntry OBJECT-TYPE
    SYNTAX IbCBQoSAtmPvcClassMatchRunInfoEntry
    MAX-ACCESS not-accessible
    STATUS current
    DESCRIPTION
        "Classifier matching statistics entry."
    INDEX { ibCBQoSAtmPvcApplyPolicyIfIndex,
            ibCBQoSAtmPvcApplyPolicyVPI,
            ibCBQoSAtmPvcApplyPolicyVCI,
            ibCBQoSAtmPvcApplyPolicyDirection,
            ibCBQoSPolicyClassIndex }
    ::= { ibCBQoSAtmPvcClassMatchRunInfoTable 1 }

IbCBQoSAtmPvcClassMatchRunInfoEntry ::=
    SEQUENCE
    {
        ibCBQoSAtmPvcClassMatchPackets
            Counter64,
        ibCBQoSAtmPvcClassMatchBytes
            Counter64,
        ibCBQoSAtmPvcClassAverageRate
            Integer32
    }

ibCBQoSAtmPvcClassMatchPackets OBJECT-TYPE
    SYNTAX Counter64
    MAX-ACCESS read-only
    STATUS current
    DESCRIPTION
        "Number of packets matching a class in a QoS policy."
    ::= { ibCBQoSAtmPvcClassMatchRunInfoEntry 1 }

ibCBQoSAtmPvcClassMatchBytes OBJECT-TYPE
    SYNTAX Counter64
    MAX-ACCESS read-only
    STATUS current
    DESCRIPTION
        "Number of bytes matching a class in a QoS policy."
    ::= { ibCBQoSAtmPvcClassMatchRunInfoEntry 2 }

ibCBQoSAtmPvcClassAverageRate OBJECT-TYPE
    SYNTAX Integer32
    MAX-ACCESS read-only
    STATUS current
    DESCRIPTION
        "Average rate matching a class in the last 5 minutes."
    ::= { ibCBQoSAtmPvcClassMatchRunInfoEntry 3 }

-- CAR statistics

ibCBQoSAtmPvcCarRunInfoTable OBJECT-TYPE
    SYNTAX SEQUENCE OF IbCBQoSAtmPvcCarRunInfoEntry
    MAX-ACCESS not-accessible
    STATUS current
    DESCRIPTION
        "A table of Running statistics for CAR
         in a QoS policy applied on ATM PVC."
    ::= { ibCBQoSAtmPvcStaticsObjects 3 }

ibCBQoSAtmPvcCarRunInfoEntry OBJECT-TYPE
    SYNTAX IbCBQoSAtmPvcCarRunInfoEntry
    MAX-ACCESS not-accessible
    STATUS current
    DESCRIPTION
        "CAR statistics entry."
    INDEX { ibCBQoSAtmPvcApplyPolicyIfIndex,
            ibCBQoSAtmPvcApplyPolicyVPI,
            ibCBQoSAtmPvcApplyPolicyVCI,
            ibCBQoSAtmPvcApplyPolicyDirection,
            ibCBQoSPolicyClassIndex }
    ::= { ibCBQoSAtmPvcCarRunInfoTable 1 }

IbCBQoSAtmPvcCarRunInfoEntry ::=
    SEQUENCE
    {
        ibCBQoSAtmPvcCarConformPackets
            Counter64,
        ibCBQoSAtmPvcCarConformBytes
            Counter64,
        ibCBQoSAtmPvcCarExceedPackets
            Counter64,
        ibCBQoSAtmPvcCarExceedBytes
            Counter64
    }

ibCBQoSAtmPvcCarConformPackets OBJECT-TYPE
    SYNTAX Counter64
    MAX-ACCESS read-only
    STATUS current
    DESCRIPTION
        "Number of packets that conforming specified CIR."
    ::= { ibCBQoSAtmPvcCarRunInfoEntry 1 }

ibCBQoSAtmPvcCarConformBytes OBJECT-TYPE
    SYNTAX Counter64
    MAX-ACCESS read-only
    STATUS current
    DESCRIPTION
        "Number of bytes that conforming specified CIR."
    ::= { ibCBQoSAtmPvcCarRunInfoEntry 2 }

ibCBQoSAtmPvcCarExceedPackets OBJECT-TYPE
    SYNTAX Counter64
    MAX-ACCESS read-only
    STATUS current
    DESCRIPTION
        "Number of packets exceeded CIR."
    ::= { ibCBQoSAtmPvcCarRunInfoEntry 3 }

ibCBQoSAtmPvcCarExceedBytes OBJECT-TYPE
    SYNTAX Counter64
    MAX-ACCESS read-only
    STATUS current
    DESCRIPTION
        "Number of bytes exceeded CIR."
    ::= { ibCBQoSAtmPvcCarRunInfoEntry 4 }

-- GTS statistics

ibCBQoSAtmPvcGtsRunInfoTable OBJECT-TYPE
    SYNTAX SEQUENCE OF IbCBQoSAtmPvcGtsRunInfoEntry
    MAX-ACCESS not-accessible
    STATUS current
    DESCRIPTION
        "A table of Running statistics for GTS
         in a QoS policy applied on ATM PVC."
    ::= { ibCBQoSAtmPvcStaticsObjects 4 }

ibCBQoSAtmPvcGtsRunInfoEntry OBJECT-TYPE
    SYNTAX IbCBQoSAtmPvcGtsRunInfoEntry
    MAX-ACCESS not-accessible
    STATUS current
    DESCRIPTION
        "GTS statistics entry."
    INDEX { ibCBQoSAtmPvcApplyPolicyIfIndex,
            ibCBQoSAtmPvcApplyPolicyVPI,
            ibCBQoSAtmPvcApplyPolicyVCI,
            ibCBQoSAtmPvcApplyPolicyDirection,
            ibCBQoSPolicyClassIndex }
    ::= { ibCBQoSAtmPvcGtsRunInfoTable 1 }

IbCBQoSAtmPvcGtsRunInfoEntry ::=
    SEQUENCE
    {
        ibCBQoSAtmPvcGtsPassedPackets
            Counter64,
        ibCBQoSAtmPvcGtsPassedBytes
            Counter64,
        ibCBQoSAtmPvcGtsDiscardedPackets
            Counter64,
        ibCBQoSAtmPvcGtsDiscardedBytes
            Counter64,
        ibCBQoSAtmPvcGtsDelayedPackets
            Counter64,
        ibCBQoSAtmPvcGtsDelayedBytes
            Counter64,
        ibCBQoSAtmPvcGtsQueueSize
            Integer32
    }

ibCBQoSAtmPvcGtsPassedPackets OBJECT-TYPE
    SYNTAX Counter64
    MAX-ACCESS read-only
    STATUS current
    DESCRIPTION
        "Number of packets passed by GTS."
    ::= { ibCBQoSAtmPvcGtsRunInfoEntry 1 }

ibCBQoSAtmPvcGtsPassedBytes OBJECT-TYPE
    SYNTAX Counter64
    MAX-ACCESS read-only
    STATUS current
    DESCRIPTION
        "Number of bytes passed by GTS."
    ::= { ibCBQoSAtmPvcGtsRunInfoEntry 2 }

ibCBQoSAtmPvcGtsDiscardedPackets OBJECT-TYPE
    SYNTAX Counter64
    MAX-ACCESS read-only
    STATUS current
    DESCRIPTION
        "Number of packets discarded by GTS."
    ::= { ibCBQoSAtmPvcGtsRunInfoEntry 3 }

ibCBQoSAtmPvcGtsDiscardedBytes OBJECT-TYPE
    SYNTAX Counter64
    MAX-ACCESS read-only
    STATUS current
    DESCRIPTION
        "Number of bytes discarded by GTS."
    ::= { ibCBQoSAtmPvcGtsRunInfoEntry 4 }

ibCBQoSAtmPvcGtsDelayedPackets OBJECT-TYPE
    SYNTAX Counter64
    MAX-ACCESS read-only
    STATUS current
    DESCRIPTION
        "Number of packets delayed by GTS."
    ::= { ibCBQoSAtmPvcGtsRunInfoEntry 5 }

ibCBQoSAtmPvcGtsDelayedBytes OBJECT-TYPE
    SYNTAX Counter64
    MAX-ACCESS read-only
    STATUS current
    DESCRIPTION
        "Number of bytes delayed by GTS."
    ::= { ibCBQoSAtmPvcGtsRunInfoEntry 6 }

ibCBQoSAtmPvcGtsQueueSize OBJECT-TYPE
    SYNTAX Integer32
    MAX-ACCESS read-only
    STATUS current
    DESCRIPTION
        "packet number of GTS queue."
    ::= { ibCBQoSAtmPvcGtsRunInfoEntry 7 }

-- Remark statistics

ibCBQoSAtmPvcRemarkRunInfoTable OBJECT-TYPE
    SYNTAX SEQUENCE OF IbCBQoSAtmPvcRemarkRunInfoEntry
    MAX-ACCESS not-accessible
    STATUS current
    DESCRIPTION
        "A table of Running statistics for remarking
         in a QoS policy applied on ATM PVC."
    ::= { ibCBQoSAtmPvcStaticsObjects 5 }

ibCBQoSAtmPvcRemarkRunInfoEntry OBJECT-TYPE
    SYNTAX IbCBQoSAtmPvcRemarkRunInfoEntry
    MAX-ACCESS not-accessible
    STATUS current
    DESCRIPTION
        "Remarking statistics entry."
    INDEX { ibCBQoSAtmPvcApplyPolicyIfIndex,
            ibCBQoSAtmPvcApplyPolicyVPI,
            ibCBQoSAtmPvcApplyPolicyVCI,
            ibCBQoSAtmPvcApplyPolicyDirection,
            ibCBQoSPolicyClassIndex }
    ::= { ibCBQoSAtmPvcRemarkRunInfoTable 1 }

IbCBQoSAtmPvcRemarkRunInfoEntry ::=
    SEQUENCE
    {
        ibCBQoSAtmPvcRemarkedPackets
            Counter64
    }

ibCBQoSAtmPvcRemarkedPackets OBJECT-TYPE
    SYNTAX Counter64
    MAX-ACCESS read-only
    STATUS current
    DESCRIPTION
        "Number of packets remarked."
    ::= { ibCBQoSAtmPvcRemarkRunInfoEntry 1 }

-- Queue statistics

ibCBQoSAtmPvcQueueRunInfoTable OBJECT-TYPE
    SYNTAX SEQUENCE OF IbCBQoSAtmPvcQueueRunInfoEntry
    MAX-ACCESS not-accessible
    STATUS current
    DESCRIPTION
        "A table of Running statistics for queue
         in a QoS policy applied on ATM PVC."
    ::= { ibCBQoSAtmPvcStaticsObjects 6 }

ibCBQoSAtmPvcQueueRunInfoEntry OBJECT-TYPE
    SYNTAX IbCBQoSAtmPvcQueueRunInfoEntry
    MAX-ACCESS not-accessible
    STATUS current
    DESCRIPTION
        "Queue statistics entry."
    INDEX { ibCBQoSAtmPvcApplyPolicyIfIndex,
            ibCBQoSAtmPvcApplyPolicyVPI,
            ibCBQoSAtmPvcApplyPolicyVCI,
            ibCBQoSAtmPvcApplyPolicyDirection,
            ibCBQoSPolicyClassIndex }
    ::= { ibCBQoSAtmPvcQueueRunInfoTable 1}

IbCBQoSAtmPvcQueueRunInfoEntry ::=
    SEQUENCE
    {
        ibCBQoSAtmPvcQueueMatchedPackets
            Counter64,
        ibCBQoSAtmPvcQueueMatchedBytes
            Counter64,
        ibCBQoSAtmPvcQueueEnqueuedPackets
            Counter64,
        ibCBQoSAtmPvcQueueEnqueuedBytes
            Counter64,
        ibCBQoSAtmPvcQueueDiscardedPackets
            Counter64,
        ibCBQoSAtmPvcQueueDiscardedBytes
            Counter64
    }

ibCBQoSAtmPvcQueueMatchedPackets OBJECT-TYPE
    SYNTAX Counter64
    MAX-ACCESS read-only
    STATUS current
    DESCRIPTION
        "Number of packets matched to enqueue."
    ::= { ibCBQoSAtmPvcQueueRunInfoEntry 1 }

ibCBQoSAtmPvcQueueMatchedBytes OBJECT-TYPE
    SYNTAX Counter64
    MAX-ACCESS read-only
    STATUS current
    DESCRIPTION
        "Number of bytes matched to enqueue."
    ::= { ibCBQoSAtmPvcQueueRunInfoEntry 2 }

ibCBQoSAtmPvcQueueEnqueuedPackets OBJECT-TYPE
    SYNTAX Counter64
    MAX-ACCESS read-only
    STATUS current
    DESCRIPTION
        "Number of packets enqueued."
    ::= { ibCBQoSAtmPvcQueueRunInfoEntry 3 }

ibCBQoSAtmPvcQueueEnqueuedBytes OBJECT-TYPE
    SYNTAX Counter64
    MAX-ACCESS read-only
    STATUS current
    DESCRIPTION
        "Number of bytes enqueued."
    ::= { ibCBQoSAtmPvcQueueRunInfoEntry 4 }

ibCBQoSAtmPvcQueueDiscardedPackets OBJECT-TYPE
    SYNTAX Counter64
    MAX-ACCESS read-only
    STATUS current
    DESCRIPTION
        "Number of packets discard when enqueued by discard method."
    ::= { ibCBQoSAtmPvcQueueRunInfoEntry 5 }

ibCBQoSAtmPvcQueueDiscardedBytes OBJECT-TYPE
    SYNTAX Counter64
    MAX-ACCESS read-only
    STATUS current
    DESCRIPTION
        "Number of bytes discard when enqueued by discard method."
    ::= { ibCBQoSAtmPvcQueueRunInfoEntry 6 }

-- WRED statistics

ibCBQoSAtmPvcWredRunInfoTable OBJECT-TYPE
    SYNTAX SEQUENCE OF IbCBQoSAtmPvcWredRunInfoEntry
    MAX-ACCESS not-accessible
    STATUS current
    DESCRIPTION
        "A table of Running statistics for WRED
         in a QoS policy applied on ATM PVC."
    ::= { ibCBQoSAtmPvcStaticsObjects 7 }

ibCBQoSAtmPvcWredRunInfoEntry OBJECT-TYPE
    SYNTAX IbCBQoSAtmPvcWredRunInfoEntry
    MAX-ACCESS not-accessible
    STATUS current
    DESCRIPTION
        "WRED statistics entry."
    INDEX { ibCBQoSAtmPvcApplyPolicyIfIndex,
            ibCBQoSAtmPvcApplyPolicyVPI,
            ibCBQoSAtmPvcApplyPolicyVCI,
            ibCBQoSAtmPvcApplyPolicyDirection,
            ibCBQoSPolicyClassIndex,
            ibCBQoSWredClassValue }
    ::= { ibCBQoSAtmPvcWredRunInfoTable 1 }

IbCBQoSAtmPvcWredRunInfoEntry ::=
    SEQUENCE
    {
        ibCBQoSAtmPvcWredRandomDiscardedPackets
            Counter64,
        ibCBQoSAtmPvcWredTailDiscardedPackets
            Counter64
    }

ibCBQoSAtmPvcWredRandomDiscardedPackets OBJECT-TYPE
    SYNTAX Counter64
    MAX-ACCESS read-only
    STATUS current
    DESCRIPTION
        "Number of packets randomly discarded by WRED."
    ::= { ibCBQoSAtmPvcWredRunInfoEntry 1 }

ibCBQoSAtmPvcWredTailDiscardedPackets OBJECT-TYPE
    SYNTAX Counter64
    MAX-ACCESS read-only
    STATUS current
    DESCRIPTION
        "Number of packets tail-discarded by WRED."
    ::= { ibCBQoSAtmPvcWredRunInfoEntry 2 }

--
-- nodes of ibCBQoSAtmPvcAccountingRunInfoTable
--
ibCBQoSAtmPvcAccountingRunInfoTable OBJECT-TYPE
    SYNTAX SEQUENCE OF IbCBQoSAtmPvcAccountingRunInfoEntry
    MAX-ACCESS not-accessible
    STATUS current
    DESCRIPTION
        "A table of Running statistics for account
         in a QoS policy applied on the ATM PVC."
    ::= { ibCBQoSAtmPvcStaticsObjects 8 }

ibCBQoSAtmPvcAccountingRunInfoEntry OBJECT-TYPE
    SYNTAX IbCBQoSAtmPvcAccountingRunInfoEntry
    MAX-ACCESS not-accessible
    STATUS current
    DESCRIPTION
        "Account statistics entry."
    INDEX { ibCBQoSAtmPvcApplyPolicyIfIndex,
            ibCBQoSAtmPvcApplyPolicyVPI,
            ibCBQoSAtmPvcApplyPolicyVCI,
            ibCBQoSAtmPvcApplyPolicyDirection,
            ibCBQoSPolicyClassIndex,
            ibCBQoSWredClassValue
          }
    ::= { ibCBQoSAtmPvcAccountingRunInfoTable 1 }

IbCBQoSAtmPvcAccountingRunInfoEntry ::=
    SEQUENCE
    {
        ibCBQoSAtmPvcAccountingPackets
            Counter64,
        ibCBQoSAtmPvcAccountingBytes
            Counter64
    }

ibCBQoSAtmPvcAccountingPackets OBJECT-TYPE
    SYNTAX Counter64
    MAX-ACCESS read-only
    STATUS current
    DESCRIPTION
        "Number of packets."
    ::= { ibCBQoSAtmPvcAccountingRunInfoEntry 1 }

ibCBQoSAtmPvcAccountingBytes OBJECT-TYPE
    SYNTAX Counter64
    MAX-ACCESS read-only
    STATUS current
    DESCRIPTION
        "Number of bytes."
    ::= { ibCBQoSAtmPvcAccountingRunInfoEntry 2 }

-- FR Interface PVC: policy Running statistics information

ibCBQoSFrPvcStaticsObjects OBJECT IDENTIFIER ::= { ibCBQoSApplyPolicyStaticsObjects 3 }

-- FR PVC CBQ statistics

ibCBQoSFrPvcCbqRunInfoTable OBJECT-TYPE
    SYNTAX SEQUENCE OF IbCBQoSFrPvcCbqRunInfoEntry
    MAX-ACCESS not-accessible
    STATUS current
    DESCRIPTION
        "A table of FR PVC CBQ Running statistics.
         When policy using queue behavior is applied on FR PVC
         will using Class Based Queuing."
    ::= { ibCBQoSFrPvcStaticsObjects 1 }

ibCBQoSFrPvcCbqRunInfoEntry OBJECT-TYPE
    SYNTAX IbCBQoSFrPvcCbqRunInfoEntry
    MAX-ACCESS not-accessible
    STATUS current
    DESCRIPTION
        "FR PVC CBQ statistics entry."
    INDEX { ibCBQoSFrPvcApplyPolicyIfIndex, ibCBQoSFrPvcApplyPolicyDlciNum }
    ::= { ibCBQoSFrPvcCbqRunInfoTable 1 }

IbCBQoSFrPvcCbqRunInfoEntry ::=
    SEQUENCE
    {
        ibCBQoSFrPvcCbqQueueSize
            Integer32,
        ibCBQoSFrPvcCbqDiscard
            Counter64,
        ibCBQoSFrPvcCbqEfQueueSize
            Integer32,
        ibCBQoSFrPvcCbqAfQueueSize
            Integer32,
        ibCBQoSFrPvcCbqBeQueueSize
            Integer32,
        ibCBQoSFrPvcCbqBeActiveQueueNum
            Integer32,
        ibCBQoSFrPvcCbqBeMaxActiveQueueNum
            Integer32,
        ibCBQoSFrPvcCbqBeTotalQueueNum
            Integer32,
        ibCBQoSFrPvcCbqAfAllocatedQueueNum
            Integer32
    }

ibCBQoSFrPvcCbqQueueSize OBJECT-TYPE
    SYNTAX Integer32
    MAX-ACCESS read-only
    STATUS current
    DESCRIPTION
        "Packet number of CBQ queue."
    ::= { ibCBQoSFrPvcCbqRunInfoEntry 1 }

ibCBQoSFrPvcCbqDiscard OBJECT-TYPE
    SYNTAX Counter64
    MAX-ACCESS read-only
    STATUS current
    DESCRIPTION
        "The number of discarded packets which could not be enqueued."
    ::= { ibCBQoSFrPvcCbqRunInfoEntry 2 }

ibCBQoSFrPvcCbqEfQueueSize OBJECT-TYPE
    SYNTAX Integer32
    MAX-ACCESS read-only
    STATUS current
    DESCRIPTION
        "Packet number of EF queue."
    ::= { ibCBQoSFrPvcCbqRunInfoEntry 3 }

ibCBQoSFrPvcCbqAfQueueSize OBJECT-TYPE
    SYNTAX Integer32
    MAX-ACCESS read-only
    STATUS current
    DESCRIPTION
        "Packet number of AF queue."
    ::= { ibCBQoSFrPvcCbqRunInfoEntry 4 }

ibCBQoSFrPvcCbqBeQueueSize OBJECT-TYPE
    SYNTAX Integer32
    MAX-ACCESS read-only
    STATUS current
    DESCRIPTION
        "Packet number of BE queue."
    ::= { ibCBQoSFrPvcCbqRunInfoEntry 5 }

ibCBQoSFrPvcCbqBeActiveQueueNum OBJECT-TYPE
    SYNTAX Integer32
    MAX-ACCESS read-only
    STATUS current
    DESCRIPTION
        "The packet number of Active Be Queue."
    ::= { ibCBQoSFrPvcCbqRunInfoEntry 6 }

ibCBQoSFrPvcCbqBeMaxActiveQueueNum OBJECT-TYPE
    SYNTAX Integer32
    MAX-ACCESS read-only
    STATUS current
    DESCRIPTION
        "The max packet number of Active Be Queue."
    ::= { ibCBQoSFrPvcCbqRunInfoEntry 7 }

ibCBQoSFrPvcCbqBeTotalQueueNum OBJECT-TYPE
    SYNTAX Integer32
    MAX-ACCESS read-only
    STATUS current
    DESCRIPTION
        "The total packet number of Be Queue."
    ::= { ibCBQoSFrPvcCbqRunInfoEntry 8 }

ibCBQoSFrPvcCbqAfAllocatedQueueNum OBJECT-TYPE
    SYNTAX Integer32
    MAX-ACCESS read-only
    STATUS current
    DESCRIPTION
        "The Allocated packet number of AF Queue."
    ::= { ibCBQoSFrPvcCbqRunInfoEntry 9 }

-- Class match statistics

ibCBQoSFrPvcClassMatchRunInfoTable OBJECT-TYPE
    SYNTAX SEQUENCE OF IbCBQoSFrPvcClassMatchRunInfoEntry
    MAX-ACCESS not-accessible
    STATUS current
    DESCRIPTION
        "A table of Running statistics for matching a classifier
         in a QoS policy applied on FR PVC."
    ::= { ibCBQoSFrPvcStaticsObjects 2 }

ibCBQoSFrPvcClassMatchRunInfoEntry OBJECT-TYPE
    SYNTAX IbCBQoSFrPvcClassMatchRunInfoEntry
    MAX-ACCESS not-accessible
    STATUS current
    DESCRIPTION
        "Classifier matching statistics entry."
    INDEX { ibCBQoSFrPvcApplyPolicyIfIndex,
            ibCBQoSFrPvcApplyPolicyDlciNum,
            ibCBQoSFrPvcApplyPolicyDirection,
            ibCBQoSPolicyClassIndex }
    ::= { ibCBQoSFrPvcClassMatchRunInfoTable 1 }

IbCBQoSFrPvcClassMatchRunInfoEntry ::=
    SEQUENCE
    {
        ibCBQoSFrPvcClassMatchedPackets
            Counter64,
        ibCBQoSFrPvcClassMatchedBytes
            Counter64,
        ibCBQoSFrPvcClassAverageRate
            Counter64
    }

ibCBQoSFrPvcClassMatchedPackets OBJECT-TYPE
    SYNTAX Counter64
    MAX-ACCESS read-only
    STATUS current
    DESCRIPTION
        "Number of packets matching a class in a QoS policy."
    ::= { ibCBQoSFrPvcClassMatchRunInfoEntry 1 }

ibCBQoSFrPvcClassMatchedBytes OBJECT-TYPE
    SYNTAX Counter64
    MAX-ACCESS read-only
    STATUS current
    DESCRIPTION
        "Number of bytes matching a class in a QoS policy."
    ::= { ibCBQoSFrPvcClassMatchRunInfoEntry 2 }

ibCBQoSFrPvcClassAverageRate OBJECT-TYPE
    SYNTAX Counter64
    MAX-ACCESS read-only
    STATUS current
    DESCRIPTION
        "Average rate matching a class of the last 5 minutes."
    ::= { ibCBQoSFrPvcClassMatchRunInfoEntry 3 }

-- CAR statistics

ibCBQoSFrPvcCarRunInfoTable OBJECT-TYPE
    SYNTAX SEQUENCE OF IbCBQoSFrPvcCarRunInfoEntry
    MAX-ACCESS not-accessible
    STATUS current
    DESCRIPTION
        "A table of Running statistics for CAR
         in a QoS policy applied on FR PVC."
    ::= { ibCBQoSFrPvcStaticsObjects 3 }

ibCBQoSFrPvcCarRunInfoEntry OBJECT-TYPE
    SYNTAX IbCBQoSFrPvcCarRunInfoEntry
    MAX-ACCESS not-accessible
    STATUS current
    DESCRIPTION
        "CAR statistics entry."
    INDEX { ibCBQoSFrPvcApplyPolicyIfIndex,
            ibCBQoSFrPvcApplyPolicyDlciNum,
            ibCBQoSFrPvcApplyPolicyDirection,
            ibCBQoSPolicyClassIndex }
    ::= { ibCBQoSFrPvcCarRunInfoTable 1 }

IbCBQoSFrPvcCarRunInfoEntry ::=
    SEQUENCE
    {
        ibCBQoSFrPvcCarConformPackets
            Counter64,
        ibCBQoSFrPvcCarConformBytes
            Counter64,
        ibCBQoSFrPvcCarExceedPackets
            Counter64,
        ibCBQoSFrPvcCarExceedBytes
            Counter64
    }

ibCBQoSFrPvcCarConformPackets OBJECT-TYPE
    SYNTAX Counter64
    MAX-ACCESS read-only
    STATUS current
    DESCRIPTION
        "Number of packets conform CIR."
    ::= { ibCBQoSFrPvcCarRunInfoEntry 1 }

ibCBQoSFrPvcCarConformBytes OBJECT-TYPE
    SYNTAX Counter64
    MAX-ACCESS read-only
    STATUS current
    DESCRIPTION
        "Number of bytes conform CIR."
    ::= { ibCBQoSFrPvcCarRunInfoEntry 2 }

ibCBQoSFrPvcCarExceedPackets OBJECT-TYPE
    SYNTAX Counter64
    MAX-ACCESS read-only
    STATUS current
    DESCRIPTION
        "Number of packets exceed CIR."
    ::= { ibCBQoSFrPvcCarRunInfoEntry 3 }

ibCBQoSFrPvcCarExceedBytes OBJECT-TYPE
    SYNTAX Counter64
    MAX-ACCESS read-only
    STATUS current
    DESCRIPTION
        "Number of bytes exceed CIR."
    ::= { ibCBQoSFrPvcCarRunInfoEntry 4 }

-- GTS statistics

ibCBQoSFrPvcGtsRunInfoTable OBJECT-TYPE
    SYNTAX SEQUENCE OF IbCBQoSFrPvcGtsRunInfoEntry
    MAX-ACCESS not-accessible
    STATUS current
    DESCRIPTION
        "A table of Running statistics for GTS
         in a QoS policy applied on FR PVC."
    ::= { ibCBQoSFrPvcStaticsObjects 4 }

ibCBQoSFrPvcGtsRunInfoEntry OBJECT-TYPE
    SYNTAX IbCBQoSFrPvcGtsRunInfoEntry
    MAX-ACCESS not-accessible
    STATUS current
    DESCRIPTION
        "GTS statistics entry."
    INDEX { ibCBQoSFrPvcApplyPolicyIfIndex,
            ibCBQoSFrPvcApplyPolicyDlciNum,
            ibCBQoSFrPvcApplyPolicyDirection,
            ibCBQoSPolicyClassIndex }
    ::= { ibCBQoSFrPvcGtsRunInfoTable 1 }

IbCBQoSFrPvcGtsRunInfoEntry ::=
    SEQUENCE
    {
        ibCBQoSFrPvcGtsPassedPackets
            Counter64,
        ibCBQoSFrPvcGtsPassedBytes
            Counter64,
        ibCBQoSFrPvcGtsDiscardedPackets
            Counter64,
        ibCBQoSFrPvcGtsDiscardedBytes
            Counter64,
        ibCBQoSFrPvcGtsDelayedPackets
            Counter64,
        ibCBQoSFrPvcGtsDelayedBytes
            Counter64,
        ibCBQoSFrPvcGtsQueueSize
            Integer32
    }

ibCBQoSFrPvcGtsPassedPackets OBJECT-TYPE
    SYNTAX Counter64
    MAX-ACCESS read-only
    STATUS current
    DESCRIPTION
        "Number of packets passed by GTS."
    ::= { ibCBQoSFrPvcGtsRunInfoEntry 1 }

ibCBQoSFrPvcGtsPassedBytes OBJECT-TYPE
    SYNTAX Counter64
    MAX-ACCESS read-only
    STATUS current
    DESCRIPTION
        "Number of bytes passed by GTS."
    ::= { ibCBQoSFrPvcGtsRunInfoEntry 2 }

ibCBQoSFrPvcGtsDiscardedPackets OBJECT-TYPE
    SYNTAX Counter64
    MAX-ACCESS read-only
    STATUS current
    DESCRIPTION
        "Number of packets discarded by GTS."
    ::= { ibCBQoSFrPvcGtsRunInfoEntry 3 }

ibCBQoSFrPvcGtsDiscardedBytes OBJECT-TYPE
    SYNTAX Counter64
    MAX-ACCESS read-only
    STATUS current
    DESCRIPTION
        "Number of bytes discarded by GTS."
    ::= { ibCBQoSFrPvcGtsRunInfoEntry 4 }

ibCBQoSFrPvcGtsDelayedPackets OBJECT-TYPE
    SYNTAX Counter64
    MAX-ACCESS read-only
    STATUS current
    DESCRIPTION
        "Number of packets delayed by GTS."
    ::= { ibCBQoSFrPvcGtsRunInfoEntry 5 }

ibCBQoSFrPvcGtsDelayedBytes OBJECT-TYPE
    SYNTAX Counter64
    MAX-ACCESS read-only
    STATUS current
    DESCRIPTION
        "Number of bytes delayed by GTS."
    ::= { ibCBQoSFrPvcGtsRunInfoEntry 6 }

ibCBQoSFrPvcGtsQueueSize OBJECT-TYPE
    SYNTAX Integer32
    MAX-ACCESS read-only
    STATUS current
    DESCRIPTION
        "Packet number of GTS queue."
    ::= { ibCBQoSFrPvcGtsRunInfoEntry 7 }

-- Remark statistics

ibCBQoSFrPvcRemarkRunInfoTable OBJECT-TYPE
    SYNTAX SEQUENCE OF IbCBQoSFrPvcRemarkRunInfoEntry
    MAX-ACCESS not-accessible
    STATUS current
    DESCRIPTION
        "A table of Running statistics for remarking
         in a QoS policy applied on FR PVC."
    ::= { ibCBQoSFrPvcStaticsObjects 5 }

ibCBQoSFrPvcRemarkRunInfoEntry OBJECT-TYPE
    SYNTAX IbCBQoSFrPvcRemarkRunInfoEntry
    MAX-ACCESS not-accessible
    STATUS current
    DESCRIPTION
        "Remarking statistics entry."
    INDEX { ibCBQoSFrPvcApplyPolicyIfIndex,
            ibCBQoSFrPvcApplyPolicyDlciNum,
            ibCBQoSFrPvcApplyPolicyDirection,
            ibCBQoSPolicyClassIndex }
    ::= { ibCBQoSFrPvcRemarkRunInfoTable 1 }

IbCBQoSFrPvcRemarkRunInfoEntry ::=
    SEQUENCE
    {
        ibCBQoSFrPvcRemarkedPackets
            Counter64
    }

ibCBQoSFrPvcRemarkedPackets OBJECT-TYPE
    SYNTAX Counter64
    MAX-ACCESS read-only
    STATUS current
    DESCRIPTION
        "Number of packets remarked."
    ::= { ibCBQoSFrPvcRemarkRunInfoEntry 1 }

-- Queue statistics

ibCBQoSFrPvcQueueRunInfoTable OBJECT-TYPE
    SYNTAX SEQUENCE OF IbCBQoSFrPvcQueueRunInfoEntry
    MAX-ACCESS not-accessible
    STATUS current
    DESCRIPTION
        "A table of Running statistics for queue
        in a QoS policy applied on FR PVC."
    ::= { ibCBQoSFrPvcStaticsObjects 6 }

ibCBQoSFrPvcQueueRunInfoEntry OBJECT-TYPE
    SYNTAX IbCBQoSFrPvcQueueRunInfoEntry
    MAX-ACCESS not-accessible
    STATUS current
    DESCRIPTION
        "Queue statistics entry."
    INDEX { ibCBQoSFrPvcApplyPolicyIfIndex,
            ibCBQoSFrPvcApplyPolicyDlciNum,
            ibCBQoSFrPvcApplyPolicyDirection,
            ibCBQoSPolicyClassIndex }
    ::= { ibCBQoSFrPvcQueueRunInfoTable 1 }

IbCBQoSFrPvcQueueRunInfoEntry ::=
    SEQUENCE
    {
        ibCBQoSFrPvcQueueMatchedPackets
            Counter64,
        ibCBQoSFrPvcQueueMatchedBytes
            Counter64,
        ibCBQoSFrPvcQueueEnqueuedPackets
            Counter64,
        ibCBQoSFrPvcQueueEnqueuedBytes
            Counter64,
        ibCBQoSFrPvcQueueDiscardedPackets
            Counter64,
        ibCBQoSFrPvcQueueDiscardedBytes
            Counter64
    }

ibCBQoSFrPvcQueueMatchedPackets OBJECT-TYPE
    SYNTAX Counter64
    MAX-ACCESS read-only
    STATUS current
    DESCRIPTION
        "Number of packets matched to enqueue."
    ::= { ibCBQoSFrPvcQueueRunInfoEntry 1 }

ibCBQoSFrPvcQueueMatchedBytes OBJECT-TYPE
    SYNTAX Counter64
    MAX-ACCESS read-only
    STATUS current
    DESCRIPTION
        "Number of bytes matched to en-queue."
    ::= { ibCBQoSFrPvcQueueRunInfoEntry 2 }

ibCBQoSFrPvcQueueEnqueuedPackets OBJECT-TYPE
    SYNTAX Counter64
    MAX-ACCESS read-only
    STATUS current
    DESCRIPTION
        "Number of packets en-queued."
    ::= { ibCBQoSFrPvcQueueRunInfoEntry 3 }

ibCBQoSFrPvcQueueEnqueuedBytes OBJECT-TYPE
    SYNTAX Counter64
    MAX-ACCESS read-only
    STATUS current
    DESCRIPTION
        "Number of bytes enqueued."
    ::= { ibCBQoSFrPvcQueueRunInfoEntry 4 }

ibCBQoSFrPvcQueueDiscardedPackets OBJECT-TYPE
    SYNTAX Counter64
    MAX-ACCESS read-only
    STATUS current
    DESCRIPTION
        "Number of packets discarded when enqueued by discard method."
    ::= { ibCBQoSFrPvcQueueRunInfoEntry 5 }

ibCBQoSFrPvcQueueDiscardedBytes OBJECT-TYPE
    SYNTAX Counter64
    MAX-ACCESS read-only
    STATUS current
    DESCRIPTION
        "Number of bytes discarded when enqueued by discard method."
    ::= { ibCBQoSFrPvcQueueRunInfoEntry 6 }

-- WRED statistics

ibCBQoSFrPvcWredRunInfoTable OBJECT-TYPE
    SYNTAX SEQUENCE OF IbCBQoSFrPvcWredRunInfoEntry
    MAX-ACCESS not-accessible
    STATUS current
    DESCRIPTION
        "A table of Running statistics for WRED
         in a QoS policy applied on FR PVC.
        "
    ::= { ibCBQoSFrPvcStaticsObjects 7 }

ibCBQoSFrPvcWredRunInfoEntry OBJECT-TYPE
    SYNTAX IbCBQoSFrPvcWredRunInfoEntry
    MAX-ACCESS not-accessible
    STATUS current
    DESCRIPTION
        "WRED statistics entry."
    INDEX { ibCBQoSFrPvcApplyPolicyIfIndex,
            ibCBQoSFrPvcApplyPolicyDlciNum,
            ibCBQoSFrPvcApplyPolicyDirection,
            ibCBQoSPolicyClassIndex,
            ibCBQoSWredClassValue }
    ::= { ibCBQoSFrPvcWredRunInfoTable 1 }

IbCBQoSFrPvcWredRunInfoEntry ::=
    SEQUENCE
    {
        ibCBQoSFrPvcWredRandomDiscardedPackets
            Counter64,
        ibCBQoSFrPvcWredTailDiscardedPackets
            Counter64
    }

ibCBQoSFrPvcWredRandomDiscardedPackets OBJECT-TYPE
    SYNTAX Counter64
    MAX-ACCESS read-only
    STATUS current
    DESCRIPTION
        "Number of packets randomly discarded by WRED."
    ::= { ibCBQoSFrPvcWredRunInfoEntry 1 }

ibCBQoSFrPvcWredTailDiscardedPackets OBJECT-TYPE
    SYNTAX Counter64
    MAX-ACCESS read-only
    STATUS current
    DESCRIPTION
        "Number of packets tail-discarded by WRED."
    ::= { ibCBQoSFrPvcWredRunInfoEntry 2 }

--
-- nodes of ibCBQoSFrPvcAccountingRunInfoTable
--
ibCBQoSFrPvcAccountingRunInfoTable OBJECT-TYPE
    SYNTAX SEQUENCE OF IbCBQoSFrPvcAccountingRunInfoEntry
    MAX-ACCESS not-accessible
    STATUS current
    DESCRIPTION
        "A table of Running statistics for account
         in a QoS policy applied on the interface."
    ::= { ibCBQoSFrPvcStaticsObjects 8 }

ibCBQoSFrPvcAccountingRunInfoEntry OBJECT-TYPE
    SYNTAX IbCBQoSFrPvcAccountingRunInfoEntry
    MAX-ACCESS not-accessible
    STATUS current
    DESCRIPTION
        "Account statistics entry."
    INDEX { ibCBQoSFrPvcApplyPolicyIfIndex,
            ibCBQoSFrPvcApplyPolicyDlciNum,
            ibCBQoSFrPvcApplyPolicyDirection,
            ibCBQoSPolicyClassIndex,
            ibCBQoSWredClassValue
          }
    ::= { ibCBQoSFrPvcAccountingRunInfoTable 1 }

IbCBQoSFrPvcAccountingRunInfoEntry ::=
    SEQUENCE
    {
        ibCBQoSFrPvcAccountingPackets
            Counter64,
        ibCBQoSFrPvcAccountingBytes
            Counter64
    }

ibCBQoSFrPvcAccountingPackets OBJECT-TYPE
    SYNTAX Counter64
    MAX-ACCESS read-only
    STATUS current
    DESCRIPTION
        "Number of packets."
    ::= { ibCBQoSFrPvcAccountingRunInfoEntry 1 }

ibCBQoSFrPvcAccountingBytes OBJECT-TYPE
    SYNTAX Counter64
    MAX-ACCESS read-only
    STATUS current
    DESCRIPTION
        "Number of bytes."
    ::= { ibCBQoSFrPvcAccountingRunInfoEntry 2 }

-- Ethernet Interface VLAN: policy Running statistics information

ibCBQoSVlanStaticsObjects OBJECT IDENTIFIER ::= { ibCBQoSApplyPolicyStaticsObjects 4 }

-- Class match statistics

ibCBQoSVlanClassMatchRunInfoTable OBJECT-TYPE
    SYNTAX SEQUENCE OF IbCBQoSVlanClassMatchRunInfoEntry
    MAX-ACCESS not-accessible
    STATUS current
    DESCRIPTION
        "A table of Running statistics for matching a classifier
         in a QoS policy applied on Ethernet VLAN.
        "
    ::= { ibCBQoSVlanStaticsObjects 1 }

ibCBQoSVlanClassMatchRunInfoEntry OBJECT-TYPE
    SYNTAX IbCBQoSVlanClassMatchRunInfoEntry
    MAX-ACCESS not-accessible
    STATUS current
    DESCRIPTION
        "Classifier matching statistics entry."
    INDEX { ibCBQoSVlanApplyPolicyVlanid,
            ibCBQoSVlanApplyPolicyDirection,
            ibCBQoSPolicyClassIndex }
    ::= { ibCBQoSVlanClassMatchRunInfoTable 1 }

IbCBQoSVlanClassMatchRunInfoEntry ::=
    SEQUENCE
    {
        ibCBQoSVlanClassMatchedPackets
            Counter64
    }

ibCBQoSVlanClassMatchedPackets OBJECT-TYPE
    SYNTAX Counter64
    MAX-ACCESS read-only
    STATUS current
    DESCRIPTION
        "Number of packets matching a class in a QoS policy."
    ::= { ibCBQoSVlanClassMatchRunInfoEntry 1 }

--
-- nodes of ibCBQoSIfVlanAccountingRunInfoTable
--
ibCBQoSVlanAccountingRunInfoTable OBJECT-TYPE
    SYNTAX SEQUENCE OF IbCBQoSVlanAccountingRunInfoEntry
    MAX-ACCESS not-accessible
    STATUS current
    DESCRIPTION
        "A table of Running statistics for account
         in a QoS policy applied on the interface."
    ::= { ibCBQoSVlanStaticsObjects 2 }

ibCBQoSVlanAccountingRunInfoEntry OBJECT-TYPE
    SYNTAX IbCBQoSVlanAccountingRunInfoEntry
    MAX-ACCESS not-accessible
    STATUS current
    DESCRIPTION
        "Account statistics entry."
    INDEX { ibCBQoSVlanApplyPolicyVlanid,
            ibCBQoSVlanApplyPolicyDirection,
            ibCBQoSPolicyClassIndex }
    ::= { ibCBQoSVlanAccountingRunInfoTable 1 }

IbCBQoSVlanAccountingRunInfoEntry ::=
    SEQUENCE
    {
        ibCBQoSVlanAccountingPackets
            Counter64,
        ibCBQoSVlanAccountingBytes
            Counter64
    }

ibCBQoSVlanAccountingPackets OBJECT-TYPE
    SYNTAX Counter64
    MAX-ACCESS read-only
    STATUS current
    DESCRIPTION
        "Number of packets."
    ::= { ibCBQoSVlanAccountingRunInfoEntry 1 }

ibCBQoSVlanAccountingBytes OBJECT-TYPE
    SYNTAX Counter64
    MAX-ACCESS read-only
    STATUS current
    DESCRIPTION
        "Number of bytes."
    ::= { ibCBQoSVlanAccountingRunInfoEntry 2 }

-- Index Object
ibCBQoSApplyPolicyIndexObjects OBJECT IDENTIFIER
    ::= { ibCBQoSApplyPolicyStaticsObjects 5 }

--
-- ApplyObjectTable
--
ibCBQoSApplyObjectTable OBJECT-TYPE
    SYNTAX SEQUENCE OF IbCBQoSApplyObjectEntry
    MAX-ACCESS not-accessible
    STATUS current
    DESCRIPTION
        "A table of QoS apply object index.  It provides the function
         of querying the information of QoS apply object, which
         consists of interface type, interface index, ATM PVC, FR DLCI
         and nesting policy index, using QoS apply object index."
    ::= { ibCBQoSApplyPolicyIndexObjects 1 }

ibCBQoSApplyObjectEntry OBJECT-TYPE
    SYNTAX IbCBQoSApplyObjectEntry
    MAX-ACCESS not-accessible
    STATUS current
    DESCRIPTION
        "QoS apply object index entry."
    INDEX { ibCBQoSApplyObjectIndex }
    ::= { ibCBQoSApplyObjectTable 1 }

IbCBQoSApplyObjectEntry ::=
    SEQUENCE
    {
        ibCBQoSApplyObjectIndex
            Unsigned32,
        ibCBQoSApplyObjectType
            ApplyObjectType,
        ibCBQoSApplyObjectDirection
            DirectionType,
        ibCBQoSApplyObjectMainSite
            Unsigned32,
        ibCBQoSApplyObjectSubChannel
            Unsigned32,
        ibCBQoSApplyObjectSubClass
            Unsigned32,
        ibCBQoSApplyObjectSubClassSec
            Unsigned32
    }

ibCBQoSApplyObjectIndex OBJECT-TYPE
    SYNTAX Unsigned32
    MAX-ACCESS not-accessible
    STATUS current
    DESCRIPTION
        "QoS apply object index.  It represents the unique identifier
         of QoS policy applied position.  It generates when QoS policy
         is applied considering ifIndex, VLAN ID, ATM PVC, FR DLCI and
         policy nesting."
    ::= { ibCBQoSApplyObjectEntry 1 }

ibCBQoSApplyObjectType OBJECT-TYPE
    SYNTAX ApplyObjectType
    MAX-ACCESS read-only
    STATUS current
    DESCRIPTION
        "Apply object type."
    ::= { ibCBQoSApplyObjectEntry 2 }

ibCBQoSApplyObjectDirection OBJECT-TYPE
    SYNTAX DirectionType
    MAX-ACCESS read-only
    STATUS current
    DESCRIPTION
        "The direction of QoS apply object."
    ::= { ibCBQoSApplyObjectEntry 3 }

ibCBQoSApplyObjectMainSite OBJECT-TYPE
    SYNTAX Unsigned32
    MAX-ACCESS read-only
    STATUS current
    DESCRIPTION
        "Its value depends on ibCBQoSApplyObjectType.
         It represents VLAN ID when ibCBQoSApplyObjectType
         is vlan, and represents chassis ID when ibCBQoSApplyObjectType
         is controlPlane, otherwise it represents ifIndex."
    ::= { ibCBQoSApplyObjectEntry 4 }

ibCBQoSApplyObjectSubChannel OBJECT-TYPE
    SYNTAX Unsigned32
    MAX-ACCESS read-only
    STATUS current
    DESCRIPTION
        "Its value depends on ibCBQoSApplyObjectType.
         It represents the value of VPI/VCI, of which high 16-bits
         is VPI and low 16-bits is VCI, when ibCBQoSApplyObjectType
         is atmPvc.
         It represents the value of data link connection identifier
         in FR network, when ibCBQoSApplyObjectType is frDlci.
         It represents slot ID, when ibCBQoSApplyObjectType is controlPlane.
         Otherwise the value is '0xFFFFFFFF'."
    ::= { ibCBQoSApplyObjectEntry 5 }

ibCBQoSApplyObjectSubClass OBJECT-TYPE
    SYNTAX Unsigned32
    MAX-ACCESS read-only
    STATUS current
    DESCRIPTION
        "The value represents level-1 sub class index when the QoS
         apply object is level-2 or level-3 nesting policy.  Otherwise
         the value is '0xFFFFFFFF'."
    ::= { ibCBQoSApplyObjectEntry 6 }

ibCBQoSApplyObjectSubClassSec OBJECT-TYPE
    SYNTAX Unsigned32
    MAX-ACCESS read-only
    STATUS current
    DESCRIPTION
        "The value represents level-2 sub class index when the QoS
         apply object is level-3 nesting policy.  Otherwise
         the value is '0xFFFFFFFF'."
    ::= { ibCBQoSApplyObjectEntry 7 }

--
-- IntApplyObjectTable
--
ibCBQoSIntApplyObjectTable OBJECT-TYPE
    SYNTAX SEQUENCE OF IbCBQoSIntApplyObjectEntry
    MAX-ACCESS not-accessible
    STATUS current
    DESCRIPTION
        "A table used for querying the QoS apply object indexes by
         interface index.  It is suitable for querying QoS apply
         object indexes for policies applied on Ethernet ports, ATM
         ports and FR ports."
    ::= { ibCBQoSApplyPolicyIndexObjects 2 }

ibCBQoSIntApplyObjectEntry OBJECT-TYPE
    SYNTAX IbCBQoSIntApplyObjectEntry
    MAX-ACCESS not-accessible
    STATUS current
    DESCRIPTION
        "QoS apply object on interface index querying entry."
    INDEX { ibCBQoSIntApplyObjectIfIndex,
            ibCBQoSApplyObjectDirection }
    ::= { ibCBQoSIntApplyObjectTable 1 }

IbCBQoSIntApplyObjectEntry ::=
    SEQUENCE
    {
        ibCBQoSIntApplyObjectIfIndex
            Unsigned32,
        ibCBQoSIntApplyObjectIndex
            Unsigned32
    }

ibCBQoSIntApplyObjectIfIndex OBJECT-TYPE
    SYNTAX Unsigned32
    MAX-ACCESS not-accessible
    STATUS current
    DESCRIPTION
        "Interface index."
    ::= { ibCBQoSIntApplyObjectEntry 1 }

ibCBQoSIntApplyObjectIndex OBJECT-TYPE
    SYNTAX Unsigned32
    MAX-ACCESS read-only
    STATUS current
    DESCRIPTION
        "QoS apply object index."
    ::= { ibCBQoSIntApplyObjectEntry 2 }

--
-- VlanApplyObjectTable
--
ibCBQoSVlanApplyObjectTable OBJECT-TYPE
    SYNTAX SEQUENCE OF IbCBQoSVlanApplyObjectEntry
    MAX-ACCESS not-accessible
    STATUS current
    DESCRIPTION
        "A table used for querying the QoS apply object indexes by VLAN
         ID and policy direction.  It is suitable for querying QoS
         apply object indexes for policies applied on VLANs.  If the
         value of ibCBQoSVlanApplyObjectVlanID is 0, it means querying
         Qos apply object index for policy applied on global."
    ::= { ibCBQoSApplyPolicyIndexObjects 3 }

ibCBQoSVlanApplyObjectEntry OBJECT-TYPE
    SYNTAX IbCBQoSVlanApplyObjectEntry
    MAX-ACCESS not-accessible
    STATUS current
    DESCRIPTION
        "VLAN apply object entry."
    INDEX { ibCBQoSVlanApplyObjectVlanID,
            ibCBQoSApplyObjectDirection }
    ::= { ibCBQoSVlanApplyObjectTable 1 }

IbCBQoSVlanApplyObjectEntry ::=
    SEQUENCE
    {
        ibCBQoSVlanApplyObjectVlanID
            Unsigned32,
        ibCBQoSVlanApplyObjectIndex
            Unsigned32
    }

ibCBQoSVlanApplyObjectVlanID OBJECT-TYPE
    SYNTAX Unsigned32 (0..4094)
    MAX-ACCESS not-accessible
    STATUS current
    DESCRIPTION
        "VLAN ID."
    ::= { ibCBQoSVlanApplyObjectEntry 1 }

ibCBQoSVlanApplyObjectIndex OBJECT-TYPE
    SYNTAX Unsigned32
    MAX-ACCESS read-only
    STATUS current
    DESCRIPTION
        "QoS apply object index."
    ::= { ibCBQoSVlanApplyObjectEntry 2 }

--
-- PvcApplyObjectTable
--
ibCBQoSPvcApplyObjectTable OBJECT-TYPE
    SYNTAX SEQUENCE OF IbCBQoSPvcApplyObjectEntry
    MAX-ACCESS not-accessible
    STATUS current
    DESCRIPTION
        "A table used for querying the QoS apply object indexes by ATM
         PVC or FR DLCI, ifIndex and policy direction.  It is suitable
         for querying QoS apply object indexes for policies applied on
         ATM PVCs or FR DLCIs."
    ::= { ibCBQoSApplyPolicyIndexObjects 4 }

ibCBQoSPvcApplyObjectEntry OBJECT-TYPE
    SYNTAX IbCBQoSPvcApplyObjectEntry
    MAX-ACCESS not-accessible
    STATUS current
    DESCRIPTION
        "QoS apply object querying entry for ATM PVC or FR
         DLCI."
    INDEX { ibCBQoSPvcApplyObjectIfIndex,
            ibCBQoSPvcApplyObjectPvcID,
            ibCBQoSApplyObjectDirection }
    ::= { ibCBQoSPvcApplyObjectTable 1 }

IbCBQoSPvcApplyObjectEntry ::=
    SEQUENCE
    {
        ibCBQoSPvcApplyObjectIfIndex
            Unsigned32,
        ibCBQoSPvcApplyObjectPvcID
            Unsigned32,
        ibCBQoSPvcApplyObjectIndex
            Unsigned32
    }

ibCBQoSPvcApplyObjectIfIndex OBJECT-TYPE
    SYNTAX Unsigned32
    MAX-ACCESS not-accessible
    STATUS current
    DESCRIPTION
        "Interface index."
    ::= { ibCBQoSPvcApplyObjectEntry 1 }

ibCBQoSPvcApplyObjectPvcID OBJECT-TYPE
    SYNTAX Unsigned32
    MAX-ACCESS not-accessible
    STATUS current
    DESCRIPTION
        "If the QoS apply object queried is a ATM PVC, its input value
         represents a VPI/VCI.  If the QoS apply object queried is a FR
         DLCI, its input value represents a value of FR DLCI."
    ::= { ibCBQoSPvcApplyObjectEntry 2 }

ibCBQoSPvcApplyObjectIndex OBJECT-TYPE
    SYNTAX Unsigned32
    MAX-ACCESS read-only
    STATUS current
    DESCRIPTION
        "QoS apply object index."
    ::= { ibCBQoSPvcApplyObjectEntry 3 }

--
-- ibCBQoSNestPolicyApplyObjectTable
--
ibCBQoSNestPolicyApplyObjectTable OBJECT-TYPE
    SYNTAX SEQUENCE OF IbCBQoSNestPolicyApplyObjectEntry
    MAX-ACCESS not-accessible
    STATUS current
    DESCRIPTION
        "A table used for querying the nested QoS policy apply object indexes.
         It is suitable for querying nested QoS apply object indexes for policies
         applied on ifIndex, VLAN ID, ATM PVC or FR DLCI."
    ::= { ibCBQoSApplyPolicyIndexObjects 5 }

ibCBQoSNestPolicyApplyObjectEntry OBJECT-TYPE
    SYNTAX IbCBQoSNestPolicyApplyObjectEntry
    MAX-ACCESS not-accessible
    STATUS current
    DESCRIPTION
        "QoS apply object on policy querying entry."
    INDEX { ibCBQoSApplyObjectIndex,
            ibCBQoSNestPolicyClassIndex}
    ::= { ibCBQoSNestPolicyApplyObjectTable 1 }

IbCBQoSNestPolicyApplyObjectEntry ::=
    SEQUENCE
    {
        ibCBQoSNestPolicyClassIndex
            Unsigned32,
        ibCBQoSNestPolicyApplyObjectIndex
            Unsigned32
    }

ibCBQoSNestPolicyClassIndex OBJECT-TYPE
    SYNTAX Unsigned32
    MAX-ACCESS not-accessible
    STATUS current
    DESCRIPTION
        "Policyclass index in father policy."
    ::= { ibCBQoSNestPolicyApplyObjectEntry 1 }

ibCBQoSNestPolicyApplyObjectIndex OBJECT-TYPE
    SYNTAX Unsigned32
    MAX-ACCESS read-only
    STATUS current
    DESCRIPTION
        "QoS apply object index of the son policy."
    ::= { ibCBQoSNestPolicyApplyObjectEntry 2 }

--
-- ibCBQoSCpApplyObjectTable
--
ibCBQoSCpApplyObjectTable OBJECT-TYPE
    SYNTAX SEQUENCE OF IbCBQoSCpApplyObjectEntry
    MAX-ACCESS not-accessible
    STATUS current
    DESCRIPTION
        "A table used for querying the QoS policy apply object indexes
         by chassis ID and slot ID.  It is suitable for querying QoS apply
         object indexes for policies applied on control plane."
    ::= { ibCBQoSApplyPolicyIndexObjects 6 }

ibCBQoSCpApplyObjectEntry OBJECT-TYPE
    SYNTAX IbCBQoSCpApplyObjectEntry
    MAX-ACCESS not-accessible
    STATUS current
    DESCRIPTION
        "QoS policy apply object on control plane querying entry."
    INDEX { ibCBQoSCpApplyObjectChassis,
            ibCBQoSCpApplyObjectSlot,
            ibCBQoSApplyObjectDirection}
    ::= { ibCBQoSCpApplyObjectTable 1 }

IbCBQoSCpApplyObjectEntry ::=
    SEQUENCE
    {
        ibCBQoSCpApplyObjectChassis
            Unsigned32,
        ibCBQoSCpApplyObjectSlot
            Unsigned32,
        ibCBQoSCpApplyObjectIndex
            Unsigned32
    }

ibCBQoSCpApplyObjectChassis OBJECT-TYPE
    SYNTAX Unsigned32
    MAX-ACCESS not-accessible
    STATUS current
    DESCRIPTION
        "Chassis ID."
    ::= { ibCBQoSCpApplyObjectEntry 1 }

ibCBQoSCpApplyObjectSlot OBJECT-TYPE
    SYNTAX Unsigned32
    MAX-ACCESS not-accessible
    STATUS current
    DESCRIPTION
        "Slot ID."
    ::= { ibCBQoSCpApplyObjectEntry 2 }

ibCBQoSCpApplyObjectIndex OBJECT-TYPE
    SYNTAX Unsigned32
    MAX-ACCESS read-only
    STATUS current
    DESCRIPTION
        "QoS apply object index."
    ::= { ibCBQoSCpApplyObjectEntry 3 }

-- Statistics

ibCBQoSStaticsObjects OBJECT IDENTIFIER
    ::= { ibCBQoSApplyPolicyStaticsObjects 6 }

-- CBQ statistics

ibCBQoSCbqRunInfoTable OBJECT-TYPE
    SYNTAX SEQUENCE OF IbCBQoSCbqRunInfoEntry
    MAX-ACCESS not-accessible
    STATUS current
    DESCRIPTION
        "A table of CBQ running statistics.
         When policy using queue behavior is applied on QoS apply
         object, the QoS apply object will use Class Based Queuing."
    ::= { ibCBQoSStaticsObjects 1 }

ibCBQoSCbqRunInfoEntry OBJECT-TYPE
    SYNTAX IbCBQoSCbqRunInfoEntry
    MAX-ACCESS not-accessible
    STATUS current
    DESCRIPTION
        "CBQ statistics entry of QoS apply object."
    INDEX { ibCBQoSApplyObjectIndex }
    ::= { ibCBQoSCbqRunInfoTable 1 }

IbCBQoSCbqRunInfoEntry ::=
    SEQUENCE
    {
        ibCBQoSCbqQueueSize
            Integer32,
        ibCBQoSCbqDiscard
            Counter64,
        ibCBQoSCbqEfQueueSize
            Integer32,
        ibCBQoSCbqAfQueueSize
            Integer32,
        ibCBQoSCbqBeQueueSize
            Integer32,
        ibCBQoSCbqBeActiveQueueNum
            Integer32,
        ibCBQoSCbqBeMaxActiveQueueNum
            Integer32,
        ibCBQoSCbqBeTotalQueueNum
            Integer32,
        ibCBQoSCbqAfAllocatedQueueNum
            Integer32
    }

ibCBQoSCbqQueueSize OBJECT-TYPE
    SYNTAX Integer32
    MAX-ACCESS read-only
    STATUS current
    DESCRIPTION
        "Number of packets in CBQ queue."
    ::= { ibCBQoSCbqRunInfoEntry 1 }

ibCBQoSCbqDiscard OBJECT-TYPE
    SYNTAX Counter64
    MAX-ACCESS read-only
    STATUS current
    DESCRIPTION
        "Number of discarded packets which couldn't queue."
    ::= { ibCBQoSCbqRunInfoEntry 2 }

ibCBQoSCbqEfQueueSize OBJECT-TYPE
    SYNTAX Integer32
    MAX-ACCESS read-only
    STATUS current
    DESCRIPTION
        "Number of packets in EF queue."
    ::= { ibCBQoSCbqRunInfoEntry 3 }

ibCBQoSCbqAfQueueSize OBJECT-TYPE
    SYNTAX Integer32
    MAX-ACCESS read-only
    STATUS current
    DESCRIPTION
        "Number of packets in AF queue."
    ::= { ibCBQoSCbqRunInfoEntry 4 }

ibCBQoSCbqBeQueueSize OBJECT-TYPE
    SYNTAX Integer32
    MAX-ACCESS read-only
    STATUS current
    DESCRIPTION
        "Number of packets in BE Queue."
    ::= { ibCBQoSCbqRunInfoEntry 5 }

ibCBQoSCbqBeActiveQueueNum OBJECT-TYPE
    SYNTAX Integer32
    MAX-ACCESS read-only
    STATUS current
    DESCRIPTION
        "Number of Active BE Queues."
    ::= { ibCBQoSCbqRunInfoEntry 6 }

ibCBQoSCbqBeMaxActiveQueueNum OBJECT-TYPE
    SYNTAX Integer32
    MAX-ACCESS read-only
    STATUS current
    DESCRIPTION
        "The max number of Active BE Queues."
    ::= { ibCBQoSCbqRunInfoEntry 7 }

ibCBQoSCbqBeTotalQueueNum OBJECT-TYPE
    SYNTAX Integer32
    MAX-ACCESS read-only
    STATUS current
    DESCRIPTION
        "Number of total BE Queues."
    ::= { ibCBQoSCbqRunInfoEntry 8 }

ibCBQoSCbqAfAllocatedQueueNum OBJECT-TYPE
    SYNTAX Integer32
    MAX-ACCESS read-only
    STATUS current
    DESCRIPTION
        "Number of allocated AF Queues."
    ::= { ibCBQoSCbqRunInfoEntry 9 }

-- Class match statistics

ibCBQoSClassMatchRunInfoTable OBJECT-TYPE
    SYNTAX SEQUENCE OF IbCBQoSClassMatchRunInfoEntry
    MAX-ACCESS not-accessible
    STATUS current
    DESCRIPTION
        "A table of running statistics for matching a classifier on a
         QoS apply object."
    ::= { ibCBQoSStaticsObjects 2 }

ibCBQoSClassMatchRunInfoEntry OBJECT-TYPE
    SYNTAX IbCBQoSClassMatchRunInfoEntry
    MAX-ACCESS not-accessible
    STATUS current
    DESCRIPTION
        "Classifier's matching statistics information entry."
    INDEX { ibCBQoSApplyObjectIndex,
            ibCBQoSPolicyClassIndex }
    ::= { ibCBQoSClassMatchRunInfoTable 1 }

IbCBQoSClassMatchRunInfoEntry ::=
    SEQUENCE
    {
        ibCBQoSClassMatchedPackets
            Counter64,
        ibCBQoSClassMatchedBytes
            Counter64,
        ibCBQoSClassFwdPktpps
            Unsigned32,
        ibCBQoSClassFwdPktbps
            Unsigned32,
        ibCBQoSClassDropPktpps
            Unsigned32,
        ibCBQoSClassDropPktbps
            Unsigned32,
        ibCBQoSClassFlowStatInterval
            Unsigned32,
        ibCBQoSClassBehaviorStatus
            INTEGER
    }

ibCBQoSClassMatchedPackets OBJECT-TYPE
    SYNTAX Counter64
    MAX-ACCESS read-only
    STATUS current
    DESCRIPTION
        "Number of packets matching a class in a QoS policy."
    ::= { ibCBQoSClassMatchRunInfoEntry 1 }

ibCBQoSClassMatchedBytes OBJECT-TYPE
    SYNTAX Counter64
    MAX-ACCESS read-only
    STATUS current
    DESCRIPTION
        "Number of bytes matching a class in a QoS policy."
    ::= { ibCBQoSClassMatchRunInfoEntry 2 }

ibCBQoSClassFwdPktpps OBJECT-TYPE
    SYNTAX Unsigned32
    MAX-ACCESS read-only
    STATUS current
    DESCRIPTION
        "Average number of packets macthing the class forwarded
         per second in the last interval.
         Unit: pps."
    ::= { ibCBQoSClassMatchRunInfoEntry 3 }

ibCBQoSClassFwdPktbps OBJECT-TYPE
    SYNTAX Unsigned32
    MAX-ACCESS read-only
    STATUS current
    DESCRIPTION
        "Average bits of packets matching the class forwarded
         per second in the last interval.
         Unit: bps."
    ::= { ibCBQoSClassMatchRunInfoEntry 4 }

ibCBQoSClassDropPktpps OBJECT-TYPE
    SYNTAX Unsigned32
    MAX-ACCESS read-only
    STATUS current
    DESCRIPTION
        "Average number of packets matching the class dropped
         per second in the last interval.
         Unit: pps."
    ::= { ibCBQoSClassMatchRunInfoEntry 5 }

ibCBQoSClassDropPktbps OBJECT-TYPE
    SYNTAX Unsigned32
    MAX-ACCESS read-only
    STATUS current
    DESCRIPTION
        "Average bits of packets matching the class dropped
         per second in the last interval.
         Unit: bps."
    ::= { ibCBQoSClassMatchRunInfoEntry 6 }

ibCBQoSClassFlowStatInterval OBJECT-TYPE
    SYNTAX Unsigned32
    MAX-ACCESS read-only
    STATUS current
    DESCRIPTION
        "Interval of collecting traffic statistics.
         Unit: minute."
    ::= { ibCBQoSClassMatchRunInfoEntry 7 }

ibCBQoSClassBehaviorStatus OBJECT-TYPE
    SYNTAX INTEGER
    {
        success(1),
        failure(2),
        partialSuccess(3)
    }
    MAX-ACCESS read-only
    STATUS current
    DESCRIPTION
        "Classifier-behavior applying status."
    ::= { ibCBQoSClassMatchRunInfoEntry 8 }

-- CAR statistics

ibCBQoSCarRunInfoTable OBJECT-TYPE
    SYNTAX SEQUENCE OF IbCBQoSCarRunInfoEntry
    MAX-ACCESS not-accessible
    STATUS current
    DESCRIPTION
        "A table of running statistics for CAR on a QoS apply object."
    ::= { ibCBQoSStaticsObjects 3 }

ibCBQoSCarRunInfoEntry OBJECT-TYPE
    SYNTAX IbCBQoSCarRunInfoEntry
    MAX-ACCESS not-accessible
    STATUS current
    DESCRIPTION
        "CAR statistics information entry."
    INDEX { ibCBQoSApplyObjectIndex,
            ibCBQoSPolicyClassIndex }
    ::= { ibCBQoSCarRunInfoTable 1 }

IbCBQoSCarRunInfoEntry ::=
    SEQUENCE
    {
        ibCBQoSCarGreenPackets
            Counter64,
        ibCBQoSCarGreenBytes
            Counter64,
        ibCBQoSCarRedPackets
            Counter64,
        ibCBQoSCarRedBytes
            Counter64,
        ibCBQoSCarYellowPackets
            Counter64,
        ibCBQoSCarYellowBytes
            Counter64,
        ibCBQoSCarClassName
            OCTET STRING,
        ibCBQoSCarGreenpps
            Counter64,
        ibCBQoSCarGreenbps
            Counter64,
        ibCBQoSCarRedpps
            Counter64,
        ibCBQoSCarRedbps
            Counter64,
        ibCBQoSCarYellowpps
            Counter64,
        ibCBQoSCarYellowbps
            Counter64
    }

ibCBQoSCarGreenPackets OBJECT-TYPE
    SYNTAX Counter64
    MAX-ACCESS read-only
    STATUS current
    DESCRIPTION
        "Number of green packets."
    ::= { ibCBQoSCarRunInfoEntry 1 }

ibCBQoSCarGreenBytes OBJECT-TYPE
    SYNTAX Counter64
    MAX-ACCESS read-only
    STATUS current
    DESCRIPTION
        "Number of green bytes."
    ::= { ibCBQoSCarRunInfoEntry 2 }

ibCBQoSCarRedPackets OBJECT-TYPE
    SYNTAX Counter64
    MAX-ACCESS read-only
    STATUS current
    DESCRIPTION
        "Number of red packets."
    ::= { ibCBQoSCarRunInfoEntry 3 }

ibCBQoSCarRedBytes OBJECT-TYPE
    SYNTAX Counter64
    MAX-ACCESS read-only
    STATUS current
    DESCRIPTION
        "Number of red bytes."
    ::= { ibCBQoSCarRunInfoEntry 4 }

ibCBQoSCarYellowPackets OBJECT-TYPE
    SYNTAX Counter64
    MAX-ACCESS read-only
    STATUS current
    DESCRIPTION
        "Number of yellow packets."
    ::= { ibCBQoSCarRunInfoEntry 5 }

ibCBQoSCarYellowBytes OBJECT-TYPE
    SYNTAX Counter64
    MAX-ACCESS read-only
    STATUS current
    DESCRIPTION
        "Number of yellow bytes."
    ::= { ibCBQoSCarRunInfoEntry 6 }

ibCBQoSCarClassName OBJECT-TYPE
    SYNTAX OCTET STRING (SIZE (1..31))
    MAX-ACCESS read-only
    STATUS current
    DESCRIPTION
        "Name of classifier."
    ::= { ibCBQoSCarRunInfoEntry 7 }

ibCBQoSCarGreenpps OBJECT-TYPE
    SYNTAX Counter64
    MAX-ACCESS read-only
    STATUS current
    DESCRIPTION
        "Average number of green packets matching a class in a QoS policy
         per second in the last interval.
         Unit: pps."
    ::= { ibCBQoSCarRunInfoEntry 8 }

ibCBQoSCarGreenbps OBJECT-TYPE
    SYNTAX Counter64
    MAX-ACCESS read-only
    STATUS current
    DESCRIPTION
       "Average bits of green packets matching a class in a QoS policy
         per second in the last interval.
         Unit: bps."
    ::= { ibCBQoSCarRunInfoEntry 9 }

ibCBQoSCarRedpps OBJECT-TYPE
    SYNTAX Counter64
    MAX-ACCESS read-only
    STATUS current
    DESCRIPTION
        "Average number of red packets matching a class in a QoS policy
         per second in the last interval.
         Unit: pps."
    ::= { ibCBQoSCarRunInfoEntry 10 }

ibCBQoSCarRedbps OBJECT-TYPE
    SYNTAX Counter64
    MAX-ACCESS read-only
    STATUS current
    DESCRIPTION
        "Average bits of red packets matching a class in a QoS policy
         per second in the last interval.
         Unit: bps."
    ::= { ibCBQoSCarRunInfoEntry 11 }

ibCBQoSCarYellowpps OBJECT-TYPE
    SYNTAX Counter64
    MAX-ACCESS read-only
    STATUS current
    DESCRIPTION
        "Average number of yellow packets matching a class in a QoS policy
         per second in the last interval.
         Unit: pps."
    ::= { ibCBQoSCarRunInfoEntry 12 }

ibCBQoSCarYellowbps OBJECT-TYPE
    SYNTAX Counter64
    MAX-ACCESS read-only
    STATUS current
    DESCRIPTION
        "Average bits of yellow packets matching a class in a QoS policy
         per second in the last interval.
         Unit: bps."
    ::= { ibCBQoSCarRunInfoEntry 13 }

-- GTS statistics

ibCBQoSGtsRunInfoTable OBJECT-TYPE
    SYNTAX SEQUENCE OF IbCBQoSGtsRunInfoEntry
    MAX-ACCESS not-accessible
    STATUS current
    DESCRIPTION
        "A table of running statistics for GTS on a QoS apply object."
    ::= { ibCBQoSStaticsObjects 4 }

ibCBQoSGtsRunInfoEntry OBJECT-TYPE
    SYNTAX IbCBQoSGtsRunInfoEntry
    MAX-ACCESS not-accessible
    STATUS current
    DESCRIPTION
        "GTS statistics entry."
    INDEX { ibCBQoSApplyObjectIndex,
            ibCBQoSPolicyClassIndex }
    ::= { ibCBQoSGtsRunInfoTable 1 }

IbCBQoSGtsRunInfoEntry ::=
    SEQUENCE
    {
        ibCBQoSGtsPassedPackets
            Counter64,
        ibCBQoSGtsPassedBytes
            Counter64,
        ibCBQoSGtsDiscardedPackets
            Counter64,
        ibCBQoSGtsDiscardedBytes
            Counter64,
        ibCBQoSGtsDelayedPackets
            Counter64,
        ibCBQoSGtsDelayedBytes
            Counter64,
        ibCBQoSGtsQueueSize
            Integer32
    }

ibCBQoSGtsPassedPackets OBJECT-TYPE
    SYNTAX Counter64
    MAX-ACCESS read-only
    STATUS current
    DESCRIPTION
        "Number of packets passed by GTS."
    ::= { ibCBQoSGtsRunInfoEntry 1 }

ibCBQoSGtsPassedBytes OBJECT-TYPE
    SYNTAX Counter64
    MAX-ACCESS read-only
    STATUS current
    DESCRIPTION
        "Number of bytes passed by GTS."
    ::= { ibCBQoSGtsRunInfoEntry 2 }

ibCBQoSGtsDiscardedPackets OBJECT-TYPE
    SYNTAX Counter64
    MAX-ACCESS read-only
    STATUS current
    DESCRIPTION
        "Number of packets discarded by GTS."
    ::= { ibCBQoSGtsRunInfoEntry 3 }

ibCBQoSGtsDiscardedBytes OBJECT-TYPE
    SYNTAX Counter64
    MAX-ACCESS read-only
    STATUS current
    DESCRIPTION
        "Number of bytes discarded by GTS."
    ::= { ibCBQoSGtsRunInfoEntry 4 }

ibCBQoSGtsDelayedPackets OBJECT-TYPE
    SYNTAX Counter64
    MAX-ACCESS read-only
    STATUS current
    DESCRIPTION
        "Number of packets delayed by GTS."
    ::= { ibCBQoSGtsRunInfoEntry 5 }

ibCBQoSGtsDelayedBytes OBJECT-TYPE
    SYNTAX Counter64
    MAX-ACCESS read-only
    STATUS current
    DESCRIPTION
        "Number of bytes delayed by GTS."
    ::= { ibCBQoSGtsRunInfoEntry 6 }

ibCBQoSGtsQueueSize OBJECT-TYPE
    SYNTAX Integer32
    MAX-ACCESS read-only
    STATUS current
    DESCRIPTION
        "Number of packets in GTS queue."
    ::= { ibCBQoSGtsRunInfoEntry 7 }

-- Remark statistics

ibCBQoSRemarkRunInfoTable OBJECT-TYPE
    SYNTAX SEQUENCE OF IbCBQoSRemarkRunInfoEntry
    MAX-ACCESS not-accessible
    STATUS current
    DESCRIPTION
        "A table of running statistics for remarking on a QoS apply
         object."
    ::= { ibCBQoSStaticsObjects 5 }

ibCBQoSRemarkRunInfoEntry OBJECT-TYPE
    SYNTAX IbCBQoSRemarkRunInfoEntry
    MAX-ACCESS not-accessible
    STATUS current
    DESCRIPTION
        "Remarking statistics entry."
    INDEX { ibCBQoSApplyObjectIndex,
            ibCBQoSPolicyClassIndex }
    ::= { ibCBQoSRemarkRunInfoTable 1 }

IbCBQoSRemarkRunInfoEntry ::=
    SEQUENCE
    {
        ibCBQoSRemarkedPackets
            Counter64
    }

ibCBQoSRemarkedPackets OBJECT-TYPE
    SYNTAX Counter64
    MAX-ACCESS read-only
    STATUS current
    DESCRIPTION
        "Number of remarked packets."
    ::= { ibCBQoSRemarkRunInfoEntry 1 }

-- Queue statistics

ibCBQoSQueueRunInfoTable OBJECT-TYPE
    SYNTAX SEQUENCE OF IbCBQoSQueueRunInfoEntry
    MAX-ACCESS not-accessible
    STATUS current
    DESCRIPTION
        "A table of running statistics for queue on a QoS apply
         object."
    ::= { ibCBQoSStaticsObjects 6 }

ibCBQoSQueueRunInfoEntry OBJECT-TYPE
    SYNTAX IbCBQoSQueueRunInfoEntry
    MAX-ACCESS not-accessible
    STATUS current
    DESCRIPTION
        "Queue statistics entry."
    INDEX { ibCBQoSApplyObjectIndex,
            ibCBQoSPolicyClassIndex }
    ::= { ibCBQoSQueueRunInfoTable 1 }

IbCBQoSQueueRunInfoEntry ::=
    SEQUENCE
    {
        ibCBQoSQueueMatchedPackets
            Counter64,
        ibCBQoSQueueMatchedBytes
            Counter64,
        ibCBQoSQueueEnqueuedPackets
            Counter64,
        ibCBQoSQueueEnqueuedBytes
            Counter64,
        ibCBQoSQueueDiscardedPackets
            Counter64,
        ibCBQoSQueueDiscardedBytes
            Counter64
    }

ibCBQoSQueueMatchedPackets OBJECT-TYPE
    SYNTAX Counter64
    MAX-ACCESS read-only
    STATUS current
    DESCRIPTION
        "Number of packets matched to queue."
    ::= { ibCBQoSQueueRunInfoEntry 1 }

ibCBQoSQueueMatchedBytes OBJECT-TYPE
    SYNTAX Counter64
    MAX-ACCESS read-only
    STATUS current
    DESCRIPTION
        "Number of bytes matched to queue."
    ::= { ibCBQoSQueueRunInfoEntry 2 }

ibCBQoSQueueEnqueuedPackets OBJECT-TYPE
    SYNTAX Counter64
    MAX-ACCESS read-only
    STATUS current
    DESCRIPTION
        "Number of packets queued."
    ::= { ibCBQoSQueueRunInfoEntry 3 }

ibCBQoSQueueEnqueuedBytes OBJECT-TYPE
    SYNTAX Counter64
    MAX-ACCESS read-only
    STATUS current
    DESCRIPTION
        "Number of bytes queued."
    ::= { ibCBQoSQueueRunInfoEntry 4 }

ibCBQoSQueueDiscardedPackets OBJECT-TYPE
    SYNTAX Counter64
    MAX-ACCESS read-only
    STATUS current
    DESCRIPTION
        "Number of packets discarded when queued by discard method."
    ::= { ibCBQoSQueueRunInfoEntry 5 }

ibCBQoSQueueDiscardedBytes OBJECT-TYPE
    SYNTAX Counter64
    MAX-ACCESS read-only
    STATUS current
    DESCRIPTION
        "Number of bytes discarded when queued by discard method."
    ::= { ibCBQoSQueueRunInfoEntry 6 }

-- WRED statistics

ibCBQoSWredRunInfoTable OBJECT-TYPE
    SYNTAX SEQUENCE OF IbCBQoSWredRunInfoEntry
    MAX-ACCESS not-accessible
    STATUS current
    DESCRIPTION
        "A table of running statistics for WRED on a QoS apply object."
    ::= { ibCBQoSStaticsObjects 7 }

ibCBQoSWredRunInfoEntry OBJECT-TYPE
    SYNTAX IbCBQoSWredRunInfoEntry
    MAX-ACCESS not-accessible
    STATUS current
    DESCRIPTION
        "WRED statistics entry."
    INDEX { ibCBQoSApplyObjectIndex,
            ibCBQoSPolicyClassIndex,
            ibCBQoSWredClassValue }
    ::= { ibCBQoSWredRunInfoTable 1 }

IbCBQoSWredRunInfoEntry ::=
    SEQUENCE
    {
        ibCBQoSWredRandomDiscardedPackets
            Counter64,
        ibCBQoSWredTailDiscardedPackets
            Counter64
    }

ibCBQoSWredRandomDiscardedPackets OBJECT-TYPE
    SYNTAX Counter64
    MAX-ACCESS read-only
    STATUS current
    DESCRIPTION
        "Number of packets random-discarded by WRED."
    ::= { ibCBQoSWredRunInfoEntry 1 }

ibCBQoSWredTailDiscardedPackets OBJECT-TYPE
    SYNTAX Counter64
    MAX-ACCESS read-only
    STATUS current
    DESCRIPTION
        "Number of packets tail-discarded by WRED."
    ::= { ibCBQoSWredRunInfoEntry 2 }

--
-- Accounting RunInfo
--
ibCBQoSAccountingRunInfoTable OBJECT-TYPE
    SYNTAX SEQUENCE OF IbCBQoSAccountingRunInfoEntry
    MAX-ACCESS not-accessible
    STATUS current
    DESCRIPTION
        "A table of running statistics for account on a QoS apply
         object."
    ::= { ibCBQoSStaticsObjects 8 }

ibCBQoSAccountingRunInfoEntry OBJECT-TYPE
    SYNTAX IbCBQoSAccountingRunInfoEntry
    MAX-ACCESS not-accessible
    STATUS current
    DESCRIPTION
        "Account statistics entry."
    INDEX { ibCBQoSApplyObjectIndex,
            ibCBQoSPolicyClassIndex
          }
    ::= { ibCBQoSAccountingRunInfoTable 1 }

IbCBQoSAccountingRunInfoEntry ::=
    SEQUENCE
    {
        ibCBQoSAccountingPackets
            Counter64,
        ibCBQoSAccountingBytes
            Counter64,
        ibCBQoSAccountingPktpps
            Counter64,
        ibCBQoSAccountingPktbps
            Counter64
    }

ibCBQoSAccountingPackets OBJECT-TYPE
    SYNTAX Counter64
    MAX-ACCESS read-only
    STATUS current
    DESCRIPTION
        "Number of packets matching a class in a QoS policy."
    ::= { ibCBQoSAccountingRunInfoEntry 1 }

ibCBQoSAccountingBytes OBJECT-TYPE
    SYNTAX Counter64
    MAX-ACCESS read-only
    STATUS current
    DESCRIPTION
        "Number of bytes matching a class in a QoS policy."
    ::= { ibCBQoSAccountingRunInfoEntry 2 }

ibCBQoSAccountingPktpps OBJECT-TYPE
    SYNTAX Counter64
    MAX-ACCESS read-only
    STATUS current
    DESCRIPTION
        "Average number of packets matching a class in a QoS policy
         per second in the last interval.
         Unit: pps."
    ::= { ibCBQoSAccountingRunInfoEntry 3 }

ibCBQoSAccountingPktbps OBJECT-TYPE
    SYNTAX Counter64
    MAX-ACCESS read-only
    STATUS current
    DESCRIPTION
        "Average bits of packets matching a class in a QoS policy
         per second in the last interval.
         Unit: bps."
    ::= { ibCBQoSAccountingRunInfoEntry 4 }

--
-- Policy Accounting RunInfo
--
ibCBQoSPolicyAccRunInfoTable OBJECT-TYPE
    SYNTAX SEQUENCE OF IbCBQoSPolicyAccRunInfoEntry
    MAX-ACCESS not-accessible
    STATUS current
    DESCRIPTION
        "A table of running statistics for account on a QoS apply
         object."
    ::= { ibCBQoSStaticsObjects 9 }

ibCBQoSPolicyAccRunInfoEntry OBJECT-TYPE
    SYNTAX IbCBQoSPolicyAccRunInfoEntry
    MAX-ACCESS not-accessible
    STATUS current
    DESCRIPTION
        "Policy account statistics entry."
    INDEX { ibCBQoSApplyObjectIndex }
    ::= { ibCBQoSPolicyAccRunInfoTable 1 }

IbCBQoSPolicyAccRunInfoEntry ::=
    SEQUENCE
    {
        ibCBQoSPolicyAccPackets
            Counter64,
        ibCBQoSPolicyAccBytes
            Counter64
    }

ibCBQoSPolicyAccPackets OBJECT-TYPE
    SYNTAX Counter64
    MAX-ACCESS read-only
    STATUS current
    DESCRIPTION
        "Number of packets matching a QoS policy."
    ::= { ibCBQoSPolicyAccRunInfoEntry 1 }

ibCBQoSPolicyAccBytes OBJECT-TYPE
    SYNTAX Counter64
    MAX-ACCESS read-only
    STATUS current
    DESCRIPTION
        "Number of bytes matching a QoS policy."
    ::= { ibCBQoSPolicyAccRunInfoEntry 2 }

-- Policy applying status

ibCBQoSApplyingStatusObjects OBJECT IDENTIFIER ::= { ibCBQoSObjects 6 }

-- System status when applying policy

ibCBQoSApplyingStatus OBJECT-TYPE
    SYNTAX INTEGER
    {
        idle(1),
        busy(2)
    }
    MAX-ACCESS read-only
    STATUS current
    DESCRIPTION
        "This object shows the status of the system when applying policy.
        It is forbidden to set or read in this MIB module except current
        table when the value is busy."
    ::= { ibCBQoSApplyingStatusObjects 1 }

-- Notifications

ibCBQoSNotifications OBJECT IDENTIFIER ::= { ibCBQoSObjects 7 }

-- All trap definitions should be placed under this object.

ibCBQoSNotificationsPrefix OBJECT IDENTIFIER ::= { ibCBQoSNotifications 0 }

-- All objects used for TRAP only are defined here.

ibCBQoSIfPolicyChanged NOTIFICATION-TYPE
    OBJECTS
        {
            ibCBQoSIfApplyPolicyIfIndex,
            ibCBQoSIfApplyPolicyDirection
        }
    STATUS current
    DESCRIPTION
        "This notification will be sent when the applying status
        of the policy on the interface is changed."
    ::= { ibCBQoSNotificationsPrefix 1 }

ibCBQoSVlanPolicyChanged NOTIFICATION-TYPE
    OBJECTS
        {
            ibCBQoSVlanApplyPolicyVlanid,
            ibCBQoSVlanApplyPolicyDirection
        }
    STATUS current
    DESCRIPTION
        "This notification will be sent when the applying status
        of the policy on the VLAN is changed."
    ::= { ibCBQoSNotificationsPrefix 2 }

ibCBQoSGlobalAclNotSupport NOTIFICATION-TYPE
    OBJECTS
    {
        ibCBQoSChassis,
        ibCBQoSSlot,
        ibCBQoSCPU,
        ibCBQoSDirection
    }
    STATUS current
    DESCRIPTION
        "The global ACL configuration cannot work."
    ::= { ibCBQoSNotificationsPrefix 3 }

ibCBQoSGlobalQPPBNotSupport NOTIFICATION-TYPE
    OBJECTS
    {
        ibCBQoSChassis,
        ibCBQoSSlot,
        ibCBQoSCPU,
        ibCBQoSDirection
    }
    STATUS current
    DESCRIPTION
        "The global QPPB will not be effective."
    ::= { ibCBQoSNotificationsPrefix 4 }

ibCBQoSRedirectInvalidAlarm NOTIFICATION-TYPE
    OBJECTS
    {
        ibCBQoSRedirectAlarmBehaviorName,
        ibCBQoSRedirectAlarmProtoFamily,
        ibCBQoSRedirectAlarmNextHop
    }
    STATUS current
    DESCRIPTION
        "The redirection action becomes invalid."
    ::= { ibCBQoSNotificationsPrefix 5 }

ibCBQoSRedirectInvalidAlarmRecover NOTIFICATION-TYPE
    OBJECTS
    {
        ibCBQoSRedirectAlarmBehaviorName,
        ibCBQoSRedirectAlarmProtoFamily,
        ibCBQoSRedirectAlarmNextHop
    }
    STATUS current
    DESCRIPTION
        "The redirection action has been recovered."
    ::= { ibCBQoSNotificationsPrefix 6 }

ibCBQoSRdtNHLackResAlarm NOTIFICATION-TYPE
    OBJECTS
    {
        ibCBQoSRedirectAlarmBehaviorName,
        ibCBQoSSlot,
        ibCBQoSRedirectAlarmProtoFamily,
        ibCBQoSRedirectAlarmNextHop,
        ibCBQoSDirection,
        ibCBQoSApplyObject
    }
    STATUS current
    DESCRIPTION
        "Redirect the next hop resource shortage alarm."
    ::= { ibCBQoSNotificationsPrefix 7 }

ibCBQoSRdtNHLackResRecover NOTIFICATION-TYPE
    OBJECTS
    {
        ibCBQoSRedirectAlarmBehaviorName,
        ibCBQoSSlot,
        ibCBQoSRedirectAlarmProtoFamily,
        ibCBQoSRedirectAlarmNextHop,
        ibCBQoSDirection,
        ibCBQoSApplyObject
    }
    STATUS current
    DESCRIPTION
        "Redirect to next hop Recovery from resource shortage."
    ::= { ibCBQoSNotificationsPrefix 8 }
--
-- Nodes of ibCBQoSNotificationsBindings
--

ibCBQoSNotificationsBindings OBJECT IDENTIFIER ::= { ibCBQoSObjects 8 }

ibCBQoSChassis OBJECT-TYPE
    SYNTAX Integer32   (0..65534)
    MAX-ACCESS accessible-for-notify
    STATUS current
    DESCRIPTION
        "The chassis number."
    ::= { ibCBQoSNotificationsBindings 1 }

ibCBQoSSlot OBJECT-TYPE
    SYNTAX Integer32   (0..65534)
    MAX-ACCESS accessible-for-notify
    STATUS current
    DESCRIPTION
        "The slot number."
    ::= { ibCBQoSNotificationsBindings 2 }

ibCBQoSCPU OBJECT-TYPE
    SYNTAX Integer32   (0..65534)
    MAX-ACCESS accessible-for-notify
    STATUS current
    DESCRIPTION
        "The CPU number."
    ::= { ibCBQoSNotificationsBindings 3 }

ibCBQoSDirection OBJECT-TYPE
    SYNTAX DirectionType
    MAX-ACCESS accessible-for-notify
    STATUS current
    DESCRIPTION
        "Policy direction:
         inbound (1)
         outbound (2)"
    ::= { ibCBQoSNotificationsBindings 4 }

ibCBQoSRedirectAlarmBehaviorName OBJECT-TYPE
    SYNTAX OCTET STRING (SIZE (1..31))
    MAX-ACCESS accessible-for-notify
    STATUS current
    DESCRIPTION
        "Name of the traffic behavior."
    ::= { ibCBQoSNotificationsBindings 5 }

ibCBQoSRedirectAlarmProtoFamily OBJECT-TYPE
    SYNTAX InetAddressType
    MAX-ACCESS accessible-for-notify
    STATUS current
    DESCRIPTION
        "Protocol family of the redirection next-hop."
    ::= { ibCBQoSNotificationsBindings 6 }

ibCBQoSRedirectAlarmNextHop OBJECT-TYPE
    SYNTAX InetAddress
    MAX-ACCESS accessible-for-notify
    STATUS current
    DESCRIPTION
        "Next-hop addresss of the traffic redirection action."
    ::= { ibCBQoSNotificationsBindings 7 }

ibCBQoSApplyObject OBJECT-TYPE
    SYNTAX OCTET STRING (SIZE (1..127))
    MAX-ACCESS accessible-for-notify
    STATUS current
    DESCRIPTION
        "Name of the applying object."
    ::= { ibCBQoSNotificationsBindings 8 }

END
