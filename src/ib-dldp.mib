-- =====================================================================
-- Copyright (C) 2023 Intelbras S.A. All rights reserved.
--
-- Description: Device link detection protocol (DLDP) MIB.
-- Device Link Detection Protocol is private Layer2 protocol,
-- which is used for automatically detecting unidirectional link to
-- prevent a loop communication.
-- Reference:
-- Version: V1.3
-- History:
-- V1.0 2004-12-13 created by tangshun
-- V1.1 2006-11-24 modify SYNTAX and DEFVAL of ibDLDPInterval by yubo
-- V1.2 2011-11-23 modify SYNTAX and DESCRIPTION of
--                 ibDLDPAuthenticationPassword by zhangwei
-- V1.3 2021-01-06 modify SYNTAX and DESCRIPTION of
--                 ibDLDPUnidirectionalShutdown by wangmeng
-- =====================================================================
IB-DLDP-MIB DEFINITIONS ::= BEGIN
IMPORTS
    TruthValue, MacAddress, TEXTUAL-CONVENTION
        FROM SNMPv2-TC
    MODULE-IDENTITY, OBJECT-TYPE, Integer32, NOTIFICATION-TYPE
        FROM SNMPv2-SMI
    ifIndex
        FROM IF-MIB
    ibCommon
        FROM IB-OID-MIB;

-- ==================================================================
--
-- module identity part
--
-- ==================================================================
ibDldp MODULE-IDENTITY
    LAST-UPDATED
        "202101060000Z"
    ORGANIZATION
        "Intelbras S.A. Industria de Telecomunicacao Eletronica Brasileria."
    CONTACT-INFO
        ""
    DESCRIPTION "DLDP (Device Link Detection Protocol) MIB"
    REVISION
        "202101060000Z"
    DESCRIPTION
        "Modify ibDLDPUnidirectionalShutdown."
    REVISION
        "200412130000Z"
    DESCRIPTION
        "The initial version of this MIB module."
    ::= { ibCommon 43 }

-- ==================================================================
-- Textual Conventions
-- ==================================================================
EnabledStatus ::=  TEXTUAL-CONVENTION
    STATUS      current
    DESCRIPTION
        "The current state of the Ethernet port.
        This object has two defined values:
        - 'enabled', which indicates that the Ethernet port enables DLDP.
        - 'disabled', which indicates that the Ethernet port does not enable DLDP.
        "
    SYNTAX      INTEGER
        {
            enabled(1),
            disabled(2)
        }


DLDPStatus ::=  TEXTUAL-CONVENTION
    STATUS      current
    DESCRIPTION
        "Operating state of DLDP on the port.
        This object has six defined values:
        - 'initial', which indicates that the Ethernet port does not enable DLDP.
        This status does not appear in the 'ibDLDPPortDLDPState' object (below)
        because the port which is not enabled DLDP does not appear in
        'ibDLDPPortDLDPTable', it appears in 'ibDLDPPortStateTable'.
        - 'inactive', which indicates that the Ethernet port enables DLDP and
        the link status of the port is down.
        - 'active', which indicates that the Ethernet port enables DLDP and
        the link status of the port is up.
        - 'advertisement', which indicates that all neighbors of the port are
        bidirectional communication.
        - 'probe', which indicates that the port sends PDU to detect
        the communication mode between it and it's neighbors.
        - 'disable', which indicates that an unidirectional communication
        between the port and it's neighbor.

        When the user get or walk the 'ibDLDPPortDLDPState' objects (below)
        these status will output."
    SYNTAX      INTEGER
        {
            initial(1),
            inactive(2),
            active(3),
            advertisement(4),
            probe(5),
            disable(6)
        }


DLDPNeighborStatus ::=  TEXTUAL-CONVENTION
    STATUS      current
    DESCRIPTION
        "The current state of the neighbor of a port.
        This object has three defined values:
        - 'unidirection', which indicates an unidirectional communication
        between the port and it's neighbor.
        - 'bidirection', which indicates a bidirectional communication
        between the port and it's neighbor.
        - 'unknown', which indicates that the port does not know
        the communication mode between it and it's neighbor.

        When the user get or walk the 'ibDLDPNeighborState' objects (below)
        these status will output. "
    SYNTAX      INTEGER
        {
            unidirection(1),
            bidirection(2),
            unknown(3)
        }

-- ==================================================================
--
-- =====================object definition begin======================
--
-- ==================================================================
ibDLDPMibObject        OBJECT IDENTIFIER ::= { ibDldp 1 }
ibDLDPConfigGroup      OBJECT IDENTIFIER ::= { ibDLDPMibObject 1 }

ibDLDPWorkMode OBJECT-TYPE
    SYNTAX      INTEGER
        {
            normal(1),
            enhance(2)
        }
    MAX-ACCESS  read-write
    STATUS      current
    DESCRIPTION
        "The work mode of DLDP.
        Normal mode means DLDP does not detect neighbor on its own initiative
        when all neighbors aged.
        Enhance mode means DLDP detects neighbor on its own initiative
        when all neighbors aged.
        "
    DEFVAL          { normal }
    ::= { ibDLDPConfigGroup 1 }

ibDLDPSystemEnable OBJECT-TYPE
    SYNTAX      TruthValue
    MAX-ACCESS  read-write
    STATUS      current
    DESCRIPTION
        "DLDP enable or disable systematically.
        This node only supports set operation.
        If setting it to true, all the fiber ports will enable DLDP and
        the agent automatically creates new rows for each port in
        ibDLDPPortDLDPTable.
        If setting it to false, all the fiber ports will disable DLDP
        and the agent automatically destroy the corresponding rows in
        ibDLDPPortDLDPTable."
    ::= { ibDLDPConfigGroup 2 }

ibDLDPSystemReset OBJECT-TYPE
    SYNTAX      TruthValue
    MAX-ACCESS  read-write
    STATUS      current
    DESCRIPTION
        "DLDP reset systematically.
        This node only supports set operation.
        If the value of ibDLDPSystemReset is true,
        and the current state is disable,
        it will change to inactive while the port is down
        or active while the port is up.
        If ibDLDPPortDLDPState is not disable, it does not change.
        "
    ::= { ibDLDPConfigGroup 3 }

ibDLDPInterval OBJECT-TYPE
    SYNTAX      Integer32(1..100)
    MAX-ACCESS  read-write
    STATUS      current
    DESCRIPTION
        "The interval of sending an advertisement PDU.
        unit : second
        "
    DEFVAL          { 5 }
    ::= { ibDLDPConfigGroup 4 }

ibDLDPAuthenticationMode OBJECT-TYPE
    SYNTAX      INTEGER
        {
            none(1),        --DLDP exchanges are not authenticated.
            simple(2),      --DLDP exchanges are authenticated by a clear text password.
            md5(3)          --DLDP exchanges are authenticated by a MD5 digest.

        }
    MAX-ACCESS  read-write
    STATUS      current
    DESCRIPTION
        "Type of authentication mode."
    DEFVAL          { none }
    ::= { ibDLDPConfigGroup 5 }

ibDLDPAuthenticationPassword OBJECT-TYPE
    SYNTAX      OCTET STRING(SIZE(1..53))
    MAX-ACCESS  read-write
    STATUS      current
    DESCRIPTION
        "This is the password for authentication.
        If the value of ibDLDPAuthenticationMode is null,
        the user cannot set this node.
        If the value of ibDLDPAuthenticationMode is simple or MD5,
        the user must set this node with a string.

        When the user gets or walks this node,
        it displays a cipher password if ibDLDPAuthenticationMode is MD5 or
        simple or a zero-length string if ibDLDPAuthenticationMode is null.
        "
    ::= { ibDLDPConfigGroup 6 }

ibDLDPUnidirectionalShutdown OBJECT-TYPE
    SYNTAX      INTEGER
        {
            auto(1),
            manual(2),
            hybird(3)
        }
    MAX-ACCESS  read-write
    STATUS      current
    DESCRIPTION
        "The mode of unidirectional shutdown and bidirectional startup.
        It indicates the port shutdown mode when a link becomes unidirectional
        and port startup mode when the link becomes bidirectional.
        In auto mode, DLDP shuts down a port when detecting a unidirectional
        link and brings up the port when the link becomes bidirectional.
        In manual mode, a port requires manual shutdown when DLDP detects a
        unidirectional link and the port requires manual startup when the
        link becomes bidirectional.In hybrid mode, DLDP shuts down a port when
        detecting a unidirectional link and the port requires manual startup
        when the link becomes bidirectional.
        "
    DEFVAL  { auto }
    ::= { ibDLDPConfigGroup 7 }

--ibDLDPPortStateTable--
ibDLDPPortStateTable OBJECT-TYPE
    SYNTAX      SEQUENCE OF IbDLDPPortStateEntry
    MAX-ACCESS  not-accessible
    STATUS      current
    DESCRIPTION
        "The table of the Ethernet ports of a LAN switch."
    ::= { ibDLDPMibObject 2 }

ibDLDPPortStateEntry OBJECT-TYPE
    SYNTAX      IbDLDPPortStateEntry
    MAX-ACCESS  not-accessible
    STATUS      current
    DESCRIPTION
        "Information about a ibDLDPPortDLDPTable entity."
    INDEX
        {
            ifIndex
        }
    ::= { ibDLDPPortStateTable 1 }

IbDLDPPortStateEntry ::= SEQUENCE
    {
        ibDLDPPortState    EnabledStatus
    }

ibDLDPPortState OBJECT-TYPE
    SYNTAX      EnabledStatus
    MAX-ACCESS  read-write
    STATUS      current
    DESCRIPTION
        "State of a port.
        If setting it to enabled, the port will enable DLDP and a new row
        will be added in ibDLDPPortDLDPTable for this port.
        If setting it to disabled, the port will disable DLDP and the
        corresponding row will be destroyed in ibDLDPPortDLDPTable."
    DEFVAL          { disabled }
    ::= { ibDLDPPortStateEntry 1 }

--ibDLDPPortDLDPTable--
ibDLDPPortDLDPTable OBJECT-TYPE
    SYNTAX      SEQUENCE OF IbDLDPPortDLDPEntry
    MAX-ACCESS  not-accessible
    STATUS      current
    DESCRIPTION
        "Table of a LAN switch's ports, which enable DLDP."
    ::= { ibDLDPMibObject  3 }

ibDLDPPortDLDPEntry OBJECT-TYPE
    SYNTAX      IbDLDPPortDLDPEntry
    MAX-ACCESS  not-accessible
    STATUS      current
    DESCRIPTION
        "The information of a port, which enable DLDP."
    INDEX
        {
            ifIndex
        }
    ::= { ibDLDPPortDLDPTable 1 }

IbDLDPPortDLDPEntry ::= SEQUENCE
    {
        ibDLDPPortDLDPState    DLDPStatus,
        ibDLDPLinkState        INTEGER,
        ibDLDPPortDLDPReset    TruthValue
    }

ibDLDPPortDLDPState OBJECT-TYPE
    SYNTAX      DLDPStatus
    MAX-ACCESS  read-only
    STATUS      current
    DESCRIPTION
        "Operating state of DLDP on the port.
        It is relational with ibDLDPPortState and ibDLDPLinkState."
    ::= { ibDLDPPortDLDPEntry 1 }

ibDLDPLinkState OBJECT-TYPE
    SYNTAX      INTEGER
        {
            down(1),
            up(2),
            unknown(3)
        }
    MAX-ACCESS  read-only
    STATUS      current
    DESCRIPTION
        "The link state of the port."
    ::= { ibDLDPPortDLDPEntry 2 }

ibDLDPPortDLDPReset OBJECT-TYPE
    SYNTAX      TruthValue
    MAX-ACCESS  read-write
    STATUS      current
    DESCRIPTION
        "DLDP reset systematically.
        This node only supports set operation.
        If the value of ibDLDPPortDLDPReset is true,
        and the current state is disable,
        it will change to inactive while the port is down
        or active while the port is up.
        "
    ::= { ibDLDPPortDLDPEntry 3 }



--ibDLDPNeighborTable--
ibDLDPNeighborTable OBJECT-TYPE
    SYNTAX      SEQUENCE OF IbDLDPNeighborEntry
    MAX-ACCESS  not-accessible
    STATUS      current
    DESCRIPTION
        "Table of a port's neighbors."
    ::= { ibDLDPMibObject  4 }

ibDLDPNeighborEntry OBJECT-TYPE
    SYNTAX      IbDLDPNeighborEntry
    MAX-ACCESS  not-accessible
    STATUS      current
    DESCRIPTION
        "The information of a neighbor."
    INDEX
        {
            ifIndex,
            ibDLDPNeighborBridgeMac,
            ibDLDPNeighborPortIndex
        }
    ::= { ibDLDPNeighborTable 1 }

IbDLDPNeighborEntry ::= SEQUENCE
    {
        ibDLDPNeighborBridgeMac    MacAddress,
        ibDLDPNeighborPortIndex    Integer32,
        ibDLDPNeighborState        DLDPNeighborStatus,
        ibDLDPNeighborAgingTime    Integer32
    }
ibDLDPNeighborBridgeMac OBJECT-TYPE
    SYNTAX      MacAddress
    MAX-ACCESS  not-accessible
    STATUS      current
    DESCRIPTION
        "The bridge MAC address of a neighbor."
    ::= { ibDLDPNeighborEntry 1 }

ibDLDPNeighborPortIndex OBJECT-TYPE
    SYNTAX      Integer32(0..2147483647)
    MAX-ACCESS  not-accessible
    STATUS      current
    DESCRIPTION
        "The port index of a neighbor."
    ::= { ibDLDPNeighborEntry 2 }

ibDLDPNeighborState OBJECT-TYPE
    SYNTAX      DLDPNeighborStatus
    MAX-ACCESS  read-only
    STATUS      current
    DESCRIPTION
        "The state of a neighbor."
    ::= { ibDLDPNeighborEntry 3 }

ibDLDPNeighborAgingTime OBJECT-TYPE
    SYNTAX      Integer32
    MAX-ACCESS  read-only
    STATUS      current
    DESCRIPTION
        "The aging time of a neighbor. unit: second."
    ::= { ibDLDPNeighborEntry 4 }

--trap--
ibDLDPTrapObject OBJECT IDENTIFIER ::= {  ibDldp 2  }

ibDLDPNotification OBJECT IDENTIFIER ::= { ibDLDPTrapObject 1 }

ibDLDPUnidirectionalPort NOTIFICATION-TYPE
    OBJECTS
        {
            ifIndex
        }
    STATUS      current
    DESCRIPTION
        "It will send a SNMP trap when the state of a port
        has changed to unidirectional-link."
    ::= { ibDLDPNotification 1 }

END
