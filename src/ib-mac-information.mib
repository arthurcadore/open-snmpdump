-- ============================================================================
-- Copyright (C) 2023 Intelbras S.A. All rights reserved.
--
-- Description: The purpose of this MIB file is to provide the definition of
--              the MAC Information general configuration.
-- Reference:
-- Version: V1.3
-- History:
-- V1.0 2007-12-28
--   Initial version, created by gejianzhuang
-- V1.1 2009-08-13
--   Add 'ibMACInformationTrapObjectsExt' by gejianzhuang
-- V1.2 2013-05-02
--   Add 'ibMACInformationMovedTrap' by yangjie
-- V1.3 2022-08-08
--   Add 'ibMACInformationMovedRsmTrap'
--   And 'ibMACInfoVsiMovedTrap'
--   And 'ibMACInfoVsiMovedRsmTrap'
--   And 'ibMACInfoTrapMsgMovedVsi'
--   And 'ibMACInfoTrapMsgMovedFmIfName'
--   And 'ibMACInfoTrapMsgMovedToIfName' by wangyuqing
-- ============================================================================
IB-MAC-INFORMATION-MIB DEFINITIONS ::= BEGIN

IMPORTS
        ibCommon
    FROM IB-OID-MIB
        Unsigned32, Counter32, OBJECT-TYPE, MODULE-IDENTITY, NOTIFICATION-TYPE, Integer32
    FROM SNMPv2-SMI
        TEXTUAL-CONVENTION, MacAddress
    FROM SNMPv2-TC
        ifIndex
    FROM IF-MIB;

-- Node definitions
ibMACInformation MODULE-IDENTITY
    LAST-UPDATED "202208081800Z"        -- AUG 08, 2022 at 18:00 GMT
    ORGANIZATION
        "Intelbras S.A. Industria de Telecomunicacao Eletronica Brasileria."
    CONTACT-INFO
        ""
    DESCRIPTION
        "This MIB file is to provide the definition of the MAC Information
        general configuration.  MAC Information feature is used to
        make that the changed MAC information in the monitored device is
        knowable in remote monitoring device."
    REVISION "202208081800Z"
    DESCRIPTION
        "Add the objects of ibMACInformationMovedRsmTrap, ibMACInfoVsiMovedTrap,
        ibMACInfoVsiMovedRsmTrap, ibMACInfoTrapMsgMovedVsi, ibMACInfoTrapMsgMovedFmIfName
        and ibMACInfoTrapMsgMovedToIfName."
    REVISION "200712281912Z"
    DESCRIPTION
        "The initial version of this MIB file."
    ::= { ibCommon 87 }

IbMACInfoWorkMode ::=  TEXTUAL-CONVENTION
    STATUS      current
    DESCRIPTION
        "The working mode of the MAC Information feature."
    SYNTAX      INTEGER
        {
            trap(1),
            syslog(2)
        }

ibMACInformationObjects OBJECT IDENTIFIER ::= { ibMACInformation 1 }

ibMACInformationMibGlobal OBJECT IDENTIFIER  ::= { ibMACInformationObjects 1 }

ibMACInformationMIBTableTroop OBJECT IDENTIFIER  ::= { ibMACInformationObjects 2 }

ibMACInformationMibTrap OBJECT IDENTIFIER  ::= { ibMACInformationObjects 3 }

ibMACInformationMibTrapExt OBJECT IDENTIFIER  ::= { ibMACInformationObjects 4 }


ibMACInformationEnabled OBJECT-TYPE
    SYNTAX      INTEGER
        {
            enabled(1),
            disabled(2)
        }
    MAX-ACCESS  read-write
    STATUS      current
    DESCRIPTION
        "The value is a global setting.  The feature will not work until the
        value is set to enabled(1).  If the value is set to disabled(2),
        the feature will stop working even there are interfaces that have
        been enabled the feature."
    DEFVAL { disabled }
    ::= { ibMACInformationMibGlobal 1 }

ibMACInformationcSendInterval OBJECT-TYPE
    SYNTAX      Unsigned32(1..20000)
    MAX-ACCESS  read-write
    STATUS      current
    DESCRIPTION
        "The maximum interval that the device generate syslogs or traps.
        The unit is second."
    DEFVAL { 1 }
    ::= { ibMACInformationMibGlobal 2 }


ibMACInformationLearntMACNum OBJECT-TYPE
    SYNTAX      Counter32
    MAX-ACCESS  read-only
    STATUS      current
    DESCRIPTION
        "The number of MAC addresses that learnt by the device since the
        ibMACInformationEnabled is set to enabled(1) and ibMACLearntEnable
        is set to enabled(1) at least on one interface. If the ibMACInformationEnabled
        is set to disabled(2), the object will always return 0."
    ::= { ibMACInformationMibGlobal 3 }

ibMACInformationRemovedMACNum OBJECT-TYPE
    SYNTAX      Counter32
    MAX-ACCESS  read-only
    STATUS      current
    DESCRIPTION
        "The number of MAC addresses that removed by the device since the
        ibMACInformationEnabled is set to enabled(1) and ibMACRemovedEnable
        is set to enabled(1) at least on one interface. If the ibMACInformationEnabled
        is set to disabled(2), the object will always return 0."
    ::= { ibMACInformationMibGlobal 4 }

ibMACInformationTrapSendNum OBJECT-TYPE
    SYNTAX      Counter32
    MAX-ACCESS  read-only
    STATUS      current
    DESCRIPTION
        "The number of traps that have been generated. This object is valid
        only when the ibMACInfomationWorkMode is set to trap(1). If the
        ibMACInfomationWorkMode is set to syslog(2), the object will always return 0."
    ::= { ibMACInformationMibGlobal 5 }


ibMACInformationSyslogSendNum OBJECT-TYPE
    SYNTAX      Counter32
    MAX-ACCESS  read-only
    STATUS      current
    DESCRIPTION
        "The number of syslogs that have been generated. This object is valid only
        when the ibMACInfomationWorkMode is set to syslog(2). If the
        ibMACInfomationWorkMode is set to trap(1), the object will always return 0."
    ::= { ibMACInformationMibGlobal 6 }


ibMACInformationCacheLen OBJECT-TYPE
    SYNTAX      Unsigned32(0..1000)
    MAX-ACCESS  read-write
    STATUS      current
    DESCRIPTION
        "The maximum queue lenth used to cache the changed MAC addresses information
        in the monitored device. If the value is set to 0, syslog or trap will generate
        as soon as there is a MAC address learnt or removed."
    DEFVAL { 50 }
    ::= { ibMACInformationMibGlobal 7 }

ibMACInfomationWorkMode OBJECT-TYPE
    SYNTAX      IbMACInfoWorkMode
    MAX-ACCESS  read-write
    STATUS      current
    DESCRIPTION
        "The working mode of MAC Information feature.  If the object is
        set to trap(1), the device will use trap mode to notify the MAC
        address information and all properties of trap interrelated is
        valid.  If the object is set to syslog(2), the device will use
        syslog mode to notify the MAC address information and all
        properties of trap interrelated is invalid."
    ::= { ibMACInformationMibGlobal 8}


--ibMACInfomationIfTable

ibMACInfomationIfTable OBJECT-TYPE
    SYNTAX      SEQUENCE OF IbMACInfomationIfEntry
    MAX-ACCESS  not-accessible
    STATUS      current
    DESCRIPTION
        "The table is used to enable or disable the MAC Information feature
        on interfaces."
    ::= { ibMACInformationMIBTableTroop 1 }

ibMACInfomationIfEntry OBJECT-TYPE
    SYNTAX      IbMACInfomationIfEntry
    MAX-ACCESS  not-accessible
    STATUS      current
    DESCRIPTION
        "The entry of ibMACInfomationIfTable."
    INDEX
        {
            ifIndex
        }
    ::= { ibMACInfomationIfTable 1 }

IbMACInfomationIfEntry ::= SEQUENCE
    {
        ibMACLearntEnable     INTEGER,
        ibMACRemovedEnable    INTEGER
    }

ibMACLearntEnable OBJECT-TYPE
    SYNTAX      INTEGER
        {
            enabled(1),
            disabled(2)
        }
    MAX-ACCESS  read-write
    STATUS      current
    DESCRIPTION
        "If the object is set to enabled(1) on interface, the device
        will cache the MAC address information that learnt on the interface."
    DEFVAL { disabled }
    ::= { ibMACInfomationIfEntry 1 }

ibMACRemovedEnable OBJECT-TYPE
    SYNTAX      INTEGER
        {
            enabled(1),
            disabled(2)
        }
    MAX-ACCESS  read-write
    STATUS      current
    DESCRIPTION
        "If the object is set to enable(1) on interface, the device
        will cache the MAC address information that removed on the interface."
    DEFVAL { disabled }
    ::= { ibMACInfomationIfEntry 2 }


-- ibMACNotificationTrap

ibMACInformationTraps OBJECT IDENTIFIER ::= { ibMACInformationMibTrap 0 }

ibMACInformationChangedTrap NOTIFICATION-TYPE
    OBJECTS
        {
            ibMACInfoTrapIndex,
            ibMACInfoTrapCount,
            ibMACInfoTrapMsg
        }
    STATUS      current
    DESCRIPTION
        "When the cached number of MAC address information is reached the
        value specified by ibMACInformationCacheLen, trap is generated
        and is sent to the remote monitoring device.  The trap is also
        generated when the amount of time elapsed since the previous
        notification is greater than the interval value specified by
        ibMACInformationcSendInterval and there is at least one cached
        MAC address information learnt or removed. The object is valid
        only when ibMACInfomationWorkMode is set to trap(1).  When the
        ibMACInfomationWorkMode is set to syslog(2), No trap will be
        generated even ibMACInformationEnabled is set to enabled(1) and
        the feature is enabled on interface."
    ::= { ibMACInformationTraps 1 }

ibMACInformationTrapObjects OBJECT IDENTIFIER  ::= { ibMACInformationMibTrap 2 }

ibMACInfoTrapIndex OBJECT-TYPE
    SYNTAX      Unsigned32(1..4294967295)
    MAX-ACCESS  accessible-for-notify
    STATUS      current
    DESCRIPTION
        "The sequence number of trap information. When it reaches the
        maximum value, it should be set to 1."
    ::= { ibMACInformationTrapObjects 1 }

ibMACInfoTrapCount OBJECT-TYPE
    SYNTAX      Unsigned32
    MAX-ACCESS  accessible-for-notify
    STATUS      current
    DESCRIPTION
        "The cell number of the current trap information.  The trap
        message may consists of more than one MAC address information.
        Each of the one MAC address information in one trap is called cell."
    ::= { ibMACInformationTrapObjects 2 }

ibMACInfoTrapMsg OBJECT-TYPE
    SYNTAX      OCTET STRING(SIZE(1..254))
    MAX-ACCESS  accessible-for-notify
    STATUS      current
    DESCRIPTION
        "This object is the MAC information that learnt or removed
        in the monitored device. It can consists of more than
        one MAC information in the object.
        This object is in the format of '<cell1><cell2>...'. Each
        cell consists of 12 octets in the format of
        '<operationType><VLAN><MAC><MACtype><ifIndex>'.

        <operationType> is the reason type of MAC address changed and have
        size of 1 octet. It only supports the following values.
        1 - MAC learnt.
        2 - MAC removed.

        <VLAN> is the vlan number that correspond to the MAC address in
        MAC address table and has size of 2 octet.

        <MAC> is the MAC address and has size of 6 octets.

        <MACtype> is the MAC address type and has size of 1 octet. It only
        supports the following values.
        0 - Unknown
        1 - Learnt
        2 - Config dynamic
        3 - Config static
        4 - Blackhole
        5 - Security
        6 - 802.1x
        7 - MAC authentication
        8 - Voice VLAN
        9 - Reserved

        <ifIndex> is the index of the interface where the MAC
        address is learnt or removed and has size of 2 octets."
    ::= { ibMACInformationTrapObjects 3 }

-- ibMACNotificationTrapExt

ibMACInformationTrapsExt OBJECT IDENTIFIER ::= { ibMACInformationMibTrapExt 0 }

ibMACInformationChangedTrapExt NOTIFICATION-TYPE
    OBJECTS
        {
            ibMACInfoTrapVerExt,
            ibMACInfoTrapIndexExt,
            ibMACInfoTrapCountExt,
            ibMACInfoTrapMsgExt
        }
    STATUS      current
    DESCRIPTION
        "When the cached number of MAC address information is reached the
        value specified by ibMACInformationCacheLen, trap is generated
        and is sent to the remote monitoring device.  The trap is also
        generated when the amount of time elapsed since the previous
        notification is greater than the interval value specified by
        ibMACInformationcSendInterval and there is at least one cached
        MAC address information learnt or removed.  The object is valid
        only when ibMACInfomationWorkMode is set to trap(1).  When the
        ibMACInfomationWorkMode is set to syslog(2), No trap will be
        generated even ibMACInformationEnabled is set to enabled(1) and
        the feature is enabled on interface."
    ::= { ibMACInformationTrapsExt 1 }

ibMACInformationMovedTrap NOTIFICATION-TYPE
    OBJECTS
        {
            ibMACInfoTrapMsgMovedAddress,
            ibMACInfoTrapMsgMovedVlan,
            ibMACInfoTrapMsgMovedFromIf,
            ibMACInfoTrapMsgMovedToIf,
            ibMACInfoTrapMsgMovedCount,
            ibMACInfoTrapMsgChassis,
            ibMACInfoTrapMsgSlot
        }
    STATUS      current
    DESCRIPTION
        "When the MAC address has been moved to another interface, trap
        is generated and is sent to the remote monitoring device."
    ::= { ibMACInformationTrapsExt 2 }

ibMACInformationMovedRsmTrap NOTIFICATION-TYPE
    OBJECTS
        {
            ibMACInfoTrapMsgMovedVlan,
            ibMACInfoTrapMsgChassis,
            ibMACInfoTrapMsgSlot
        }
    STATUS      current
    DESCRIPTION
        "In this cycle, this trap information is reported when the MAC address in the VLAN no longer migrates."
    ::= { ibMACInformationTrapsExt 3 }

ibMACInfoVsiMovedTrap NOTIFICATION-TYPE
    OBJECTS
        {
            ibMACInfoTrapMsgMovedAddress,
            ibMACInfoTrapMsgMovedVsi,
            ibMACInfoTrapMsgMovedFmIfName,
            ibMACInfoTrapMsgMovedToIfName,
            ibMACInfoTrapMsgMovedCount,
            ibMACInfoTrapMsgChassis,
            ibMACInfoTrapMsgSlot
        }
    STATUS      current
    DESCRIPTION
        "When the MAC address has been moved to another interface in the VSI, trap
        is generated and is sent to the remote monitoring device."
    ::= { ibMACInformationTrapsExt 4 }

ibMACInfoVsiMovedRsmTrap NOTIFICATION-TYPE
    OBJECTS
        {
            ibMACInfoTrapMsgMovedVsi,
            ibMACInfoTrapMsgChassis,
            ibMACInfoTrapMsgSlot
        }
    STATUS      current
    DESCRIPTION
        "In this cycle, this trap information is reported when the MAC address in the VSI no longer migrates."
    ::= { ibMACInformationTrapsExt 5 }

ibMACInfoMovedIfBlockTrap NOTIFICATION-TYPE
    OBJECTS
        {
            ibMACInfoTrapMsgBlockIfName,
            ibMACInfoTrapMsgBlockTime,
            ibMACInfoTrapMsgMovedAddress,
            ibMACInfoTrapMsgMovedVlan
        }
    STATUS      current
    DESCRIPTION
        "When the MAC migration suppression function is enabled, the interface is down for a
        certain time due to frequent migration, and this trap information is reported."
    ::= { ibMACInformationTrapsExt 6 }

ibMACInfoMovedIfResumeTrap NOTIFICATION-TYPE
    OBJECTS
        {
            ibMACInfoTrapMsgBlockIfName,
            ibMACInfoTrapMsgBlockTime,
            ibMACInfoTrapMsgMovedVlan
        }
    STATUS      current
    DESCRIPTION
        "When the MAC migration suppression function is enabled, the interface is up after
        the interface is down for a certain time due to frequent migration, and this trap
        information is reported."
    ::= { ibMACInformationTrapsExt 7 }

ibMACInformationTrapObjectsExt OBJECT IDENTIFIER  ::= { ibMACInformationMibTrapExt 2 }

ibMACInfoTrapVerExt OBJECT-TYPE
    SYNTAX      Unsigned32
    MAX-ACCESS  accessible-for-notify
    STATUS      current
    DESCRIPTION
        "The version of trap information."
    ::= { ibMACInformationTrapObjectsExt 1 }

ibMACInfoTrapIndexExt OBJECT-TYPE
    SYNTAX      Unsigned32(1..4294967295)
    MAX-ACCESS  accessible-for-notify
    STATUS      current
    DESCRIPTION
        "The sequence number of trap information.  When it reaches the
        maximum value, it should be set to 1."
    ::= { ibMACInformationTrapObjectsExt 2 }

ibMACInfoTrapCountExt OBJECT-TYPE
    SYNTAX      Unsigned32
    MAX-ACCESS  accessible-for-notify
    STATUS      current
    DESCRIPTION
        "The cell number of the current trap information.  The trap
        message may consists of more than one MAC address information.
        Each of the one MAC address information in one trap is called cell."
    ::= { ibMACInformationTrapObjectsExt 3 }

ibMACInfoTrapMsgExt OBJECT-TYPE
    SYNTAX      OCTET STRING(SIZE(1..254))
    MAX-ACCESS  accessible-for-notify
    STATUS      current
    DESCRIPTION
        "This object is the MAC information that learnt or removed
        in the monitored device.  It can consists of more than
        one MAC information in the object.
        This object is in the format of '<cell1><cell2>...'.  Each
        cell consists of 14 octets in the format of
        '<operationType><VLAN><MAC><MACtype><ifIndex>'.

        <operationType> is the reason type of MAC address changed and have
        size of 1 octet.  It only supports the following values.
        1 - MAC learnt.
        2 - MAC removed.

        <VLAN> is the vlan number that correspond to the MAC address in
        MAC address table and has size of 2 octet.

        <MAC> is the MAC address and has size of 6 octets.

        <MACtype> is the MAC address type and has size of 1 octet.  It only
        supports the following values.
        0 - Unknown
        1 - Learnt
        2 - Config dynamic
        3 - Config static
        4 - Blackhole
        5 - Security
        6 - 802.1x
        7 - MAC authentication
        8 - Voice VLAN
        9 - Reserved

        <ifIndex> is the index of the interface where the MAC
        address is learnt or removed and has size of 4 octets."
    ::= { ibMACInformationTrapObjectsExt 4 }

ibMACInfoTrapMsgMovedAddress   OBJECT-TYPE
    SYNTAX  MacAddress
    MAX-ACCESS  accessible-for-notify
    STATUS  current
    DESCRIPTION
        "The MAC address that is moved between interfaces."
        ::= { ibMACInformationTrapObjectsExt  5 }

ibMACInfoTrapMsgMovedVlan OBJECT-TYPE
    SYNTAX      Integer32 (1..4094)
    MAX-ACCESS  accessible-for-notify
    STATUS      current
    DESCRIPTION
        "The VLAN number in which the MAC address is moved."
        ::= { ibMACInformationTrapObjectsExt  6}

ibMACInfoTrapMsgMovedFromIf OBJECT-TYPE
    SYNTAX      Integer32 (1..2147483647)
    MAX-ACCESS  accessible-for-notify
    STATUS      current
    DESCRIPTION
        "The index of the interface from which the MAC address is moved."
        ::= { ibMACInformationTrapObjectsExt  7 }

ibMACInfoTrapMsgMovedToIf OBJECT-TYPE
    SYNTAX      Integer32 (1..2147483647)
    MAX-ACCESS  accessible-for-notify
    STATUS      current
    DESCRIPTION
        "The index of the interface to which the MAC address is moved."
        ::= { ibMACInformationTrapObjectsExt  8 }

ibMACInfoTrapMsgMovedCount OBJECT-TYPE
    SYNTAX      Counter32
    MAX-ACCESS  accessible-for-notify
    STATUS      current
    DESCRIPTION
        "The times for which the MAC address has been moved between the
        interfaces."
        ::= { ibMACInformationTrapObjectsExt  9 }

ibMACInfoTrapMsgMovedVsi OBJECT-TYPE
    SYNTAX      OCTET STRING(SIZE(1..31))
    MAX-ACCESS  accessible-for-notify
    STATUS      current
    DESCRIPTION
        "The name of VSI in which the MAC address is moved."
        ::= { ibMACInformationTrapObjectsExt  10 }

ibMACInfoTrapMsgMovedFmIfName OBJECT-TYPE
    SYNTAX      OCTET STRING(SIZE (0..255))
    MAX-ACCESS  accessible-for-notify
    STATUS      current
    DESCRIPTION
        "The name of the interface from which the MAC address is moved."
        ::= { ibMACInformationTrapObjectsExt  11 }

ibMACInfoTrapMsgMovedToIfName OBJECT-TYPE
    SYNTAX      OCTET STRING(SIZE (0..255))
    MAX-ACCESS  accessible-for-notify
    STATUS      current
    DESCRIPTION
        "The name of the interface to which the MAC address is moved."
        ::= { ibMACInformationTrapObjectsExt  12 }

ibMACInfoTrapMsgChassis OBJECT-TYPE
    SYNTAX      Unsigned32
    MAX-ACCESS  accessible-for-notify
    STATUS      current
    DESCRIPTION
        "The information of chassis ID. If the value is 65535, the device is
        not a stacked device ."
    ::= { ibMACInformationTrapObjectsExt 13 }

ibMACInfoTrapMsgSlot OBJECT-TYPE
    SYNTAX      Unsigned32
    MAX-ACCESS  accessible-for-notify
    STATUS      current
    DESCRIPTION
        "The information of slot."
    ::= { ibMACInformationTrapObjectsExt 14 }

ibMACInfoTrapMsgBlockIfName OBJECT-TYPE
    SYNTAX      OCTET STRING(SIZE (0..255))
    MAX-ACCESS  accessible-for-notify
    STATUS      current
    DESCRIPTION
        "The name of the interface."
        ::= { ibMACInformationTrapObjectsExt  15 }

ibMACInfoTrapMsgBlockTime OBJECT-TYPE
    SYNTAX      Unsigned32(30..86400)
    MAX-ACCESS  accessible-for-notify
    STATUS      current
    DESCRIPTION
        "The time of MAC migration suppression, and the unit of time is seconds."
        ::= { ibMACInformationTrapObjectsExt  16 }

END
