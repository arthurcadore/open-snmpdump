-- ==================================================================
-- Copyright (C) 2023 Intelbras S.A. All rights reserved.
--
-- Description:
-- Reference:
-- Version: V1.4
-- History:
-- V1.0 Created by luoqiang01280, 2004.06.08
-- V1.1 2004-10-12 updated by gaolong
--      Import TEXTUAL-CONVENTION.
-- V1.2 2004-12-7 add ibvoiceVlanPortTable by liaoyuxia.
-- V1.3 2009-5-15 add ibVoiceVlanPortLegacy and ibVoiceVlanPortQosTrust
--                by zhangqingjun.
-- V1.4 2016-12-1 add value 0 to ibVoiceVlanAgingTime by yuhaiyan.
-- ==================================================================
-- ==================================================================
--
-- Varibles and types be imported
--
-- ==================================================================
IB-VOICE-VLAN-MIB DEFINITIONS ::= BEGIN

IMPORTS
    ibCommon
        FROM IB-OID-MIB
    RowStatus, TruthValue, MacAddress, TEXTUAL-CONVENTION
        FROM SNMPv2-TC
    MODULE-IDENTITY, OBJECT-TYPE, Integer32
        FROM SNMPv2-SMI;

    ibVoiceVlan MODULE-IDENTITY

    LAST-UPDATED     "201612010000Z"        -- Dec 01, 2016 at 00:00 GMT
    ORGANIZATION
        "Intelbras S.A. Industria de Telecomunicacao Eletronica Brasileria."
    CONTACT-INFO
        ""
    DESCRIPTION
            "This MIB contains objects to manage the voice vlan operations, which is used on
            lanswitch products. "
    REVISION "201612010000Z"
    DESCRIPTION
        "add value 0 to ibVoiceVlanAgingTime."
    REVISION "200905150000Z"
    DESCRIPTION
        "To fix bugs in the MIB file."
    REVISION "200207010000Z"
    DESCRIPTION
    "The initial revision of this MIB module."
        ::= { ibCommon 9 }

-- =============================================================
-- Textual Conventions
-- =============================================================

PortList ::= TEXTUAL-CONVENTION
    STATUS      current
    DESCRIPTION
        "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
    SYNTAX      OCTET STRING

-- ==================================================================
--
-- ======================= definition begin =========================
--
-- ==================================================================

    ibvoiceVlanOuiTable OBJECT-TYPE
        SYNTAX  SEQUENCE OF IbVoiceVlanOuiEntry
        MAX-ACCESS not-accessible
        STATUS   current
        DESCRIPTION " A table containing the mac address which can be identified by voice vlan "
        ::= { ibVoiceVlan  1  }

    ibvoiceVlanOuiEntry OBJECT-TYPE
        SYNTAX  IbVoiceVlanOuiEntry
        MAX-ACCESS not-accessible
        STATUS current
        DESCRIPTION " A table containing the mac address which can be identified by voice vlan "
                INDEX   { ibVoiceVlanOuiAddress }
                ::= {ibvoiceVlanOuiTable 1}

    IbVoiceVlanOuiEntry    ::=
    SEQUENCE {
        ibVoiceVlanOuiAddress    MacAddress  ,
        ibVoiceVlanOuiMask    MacAddress  ,
        ibVoiceVlanOuiDescription    OCTET STRING  ,
        ibVoiceVlanOuiRowStatus      RowStatus
        }

    ibVoiceVlanOuiAddress OBJECT-TYPE
        SYNTAX  MacAddress
        MAX-ACCESS read-only
        STATUS current
        DESCRIPTION " Mac address can be identified by voice vlan "
        ::= { ibvoiceVlanOuiEntry 1 }

    ibVoiceVlanOuiMask OBJECT-TYPE
        SYNTAX  MacAddress
        MAX-ACCESS read-write
        STATUS current
        DESCRIPTION " The mask of mac address "
        ::= { ibvoiceVlanOuiEntry 2 }

    ibVoiceVlanOuiDescription OBJECT-TYPE
        SYNTAX  OCTET STRING (SIZE(0..30))
        MAX-ACCESS read-write
        STATUS current
        DESCRIPTION " The description of oui "
        ::= { ibvoiceVlanOuiEntry 3 }

    ibVoiceVlanOuiRowStatus OBJECT-TYPE
        SYNTAX  RowStatus
        MAX-ACCESS read-create
        STATUS current
        DESCRIPTION " Current operation status of the row  "
        ::= { ibvoiceVlanOuiEntry 4 }

    ibVoiceVlanEnabledId  OBJECT-TYPE
        SYNTAX  Integer32
        MAX-ACCESS read-write
        STATUS current
        DESCRIPTION " Voice vlan enable status: enabled (2..4095), disabled (0xffffffff) "
        ::= { ibVoiceVlan 2 }

    ibVoiceVlanPortEnableList  OBJECT-TYPE
        SYNTAX  PortList
        MAX-ACCESS read-write
        STATUS current
        DESCRIPTION " Portlist of voice vlan enabled ports "
        ::= { ibVoiceVlan 3 }

    ibVoiceVlanAgingTime  OBJECT-TYPE
        SYNTAX  Integer32 (0|5..43200)
        MAX-ACCESS read-write
        STATUS current
        DESCRIPTION " Voice vlan aging time, the unit of which is minute.  0 means no aging."
        DEFVAL { 1440 }
        ::= { ibVoiceVlan  4 }

    ibVoiceVlanConfigState  OBJECT-TYPE
        SYNTAX  INTEGER
        {
        auto (1),
        manual (2)
        }
        MAX-ACCESS read-write
        STATUS current
        DESCRIPTION " Voice vlan configuration mode status "
        ::= { ibVoiceVlan 5 }

    ibVoiceVlanSecurityState  OBJECT-TYPE
        SYNTAX  INTEGER
        {
        security (1),
        normal (2)
        }
        MAX-ACCESS read-write
        STATUS current
        DESCRIPTION " Voice vlan security mode status "
        ::= { ibVoiceVlan 6 }

    ibvoiceVlanPortTable OBJECT-TYPE
        SYNTAX  SEQUENCE OF IbVoiceVlanPortEntry
        MAX-ACCESS not-accessible
        STATUS   current
        DESCRIPTION " A list of voice vlan mode entries."
        ::= { ibVoiceVlan  7  }

    ibvoiceVlanPortEntry OBJECT-TYPE
        SYNTAX  IbVoiceVlanPortEntry
        MAX-ACCESS not-accessible
        STATUS current
        DESCRIPTION " An entry containing voice vlan mode information,
            which is applicable to a voice vlan enabled interface."
        INDEX   { ibVoiceVlanPortifIndex }
        ::= {ibvoiceVlanPortTable 1}

    IbVoiceVlanPortEntry ::=
        SEQUENCE {
            ibVoiceVlanPortifIndex    Integer32,
            ibVoiceVlanPortMode       INTEGER,
            ibVoiceVlanPortLegacy     TruthValue,
            ibVoiceVlanPortQosTrust   TruthValue
        }

    ibVoiceVlanPortifIndex OBJECT-TYPE
        SYNTAX Integer32(1..2147483647)
        MAX-ACCESS not-accessible
        STATUS current
        DESCRIPTION " The index of interface on which voice vlan function
            is enabled."
        REFERENCE "ifIndex in RFC1213"
    ::= { ibvoiceVlanPortEntry 1 }

    ibVoiceVlanPortMode OBJECT-TYPE
        SYNTAX  INTEGER
            {
            auto (1),
            manual (2)
            }
        MAX-ACCESS read-write
        STATUS current
        DESCRIPTION " Voice vlan configuration mode status, which is
            applicable to a voice vlan enabled interface."
        ::= { ibvoiceVlanPortEntry 2 }

    ibVoiceVlanPortLegacy OBJECT-TYPE
        SYNTAX  TruthValue
        MAX-ACCESS read-write
        STATUS current
        DESCRIPTION " Voice vlan configuration legacy status, which is
            applicable to a voice vlan enabled interface."
        ::= { ibvoiceVlanPortEntry 3 }

    ibVoiceVlanPortQosTrust OBJECT-TYPE
        SYNTAX  TruthValue
        MAX-ACCESS read-write
        STATUS current
        DESCRIPTION " Voice vlan configuration qos trust status, which is
            applicable to a voice vlan enabled interface."
        ::= { ibvoiceVlanPortEntry 4 }
END
