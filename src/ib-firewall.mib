-- =========================================================================
-- Copyright (C) 2023 Intelbras S.A. All rights reserved.
--
-- Description: The MIB is designed to get Firewall' statistic information.
-- Reference:
-- Version: V1.1
-- History:
--  V1.0 2008-01-17 created by ZhangBo 05309
--       Initial version.
--  V1.1 2012/12/01 Modified by y05947
--       Add ibFWConnRate node.
-- =========================================================================
IB-FIREWALL-MIB DEFINITIONS ::= BEGIN

IMPORTS
        ibCommon
    FROM IB-OID-MIB
        Unsigned32, Gauge32, OBJECT-TYPE, MODULE-IDENTITY
    FROM SNMPv2-SMI;


ibFireWall MODULE-IDENTITY
    LAST-UPDATED "200801171450Z"
    ORGANIZATION
        "Intelbras S.A. Industria de Telecomunicacao Eletronica Brasileria."
    CONTACT-INFO
        ""
    DESCRIPTION
        "The MIB is designed to manage Firewall products."
    ::= { ibCommon 88 }


--
-- Node definitions
--

ibFirewallobject OBJECT IDENTIFIER ::= { ibFireWall 1 }

ibFirewallSpecs OBJECT IDENTIFIER ::= { ibFirewallobject 1 }

ibFWMaxConnNum OBJECT-TYPE
    SYNTAX      Unsigned32
    MAX-ACCESS  read-only
    STATUS      current
    DESCRIPTION
        "Max connection number of system."
    ::= { ibFirewallSpecs 1 }

ibFirewallGlobalStats OBJECT IDENTIFIER ::= { ibFirewallobject 2 }

ibFWConnNumCurr OBJECT-TYPE
    SYNTAX      Gauge32
    MAX-ACCESS  read-only
    STATUS      current
    DESCRIPTION
        "The number of connections that currently exist."
    ::= { ibFirewallGlobalStats 1 }

ibFWConnRate OBJECT-TYPE
    SYNTAX Gauge32
    MAX-ACCESS read-only
    STATUS current
    DESCRIPTION
        "Connection establishment rate."
    ::= { ibFirewallGlobalStats 2 }

END
