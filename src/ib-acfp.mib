-- ==================================================================
-- Copyright (C) 2023 Intelbras S.A. All rights reserved.
--
-- Description: ACFP MIB
-- Reference:
-- Version: V1.5
-- History:
--   V1.0 2006-07-04 Created by Wang Haidong
--   V1.1 2007-03-23 Modified by Hao Chunbo
--        Delete the default value of ibAcfpPolicyAdminStatus.
--   V1.2 2007-07-03 Modified by Hao Chunbo
--        Add a new trap node for ibAcfpPolicyLifetime.
--   V1.3 2007-11-07 Modified by Li Yugang
--        Modify the value of ibAcfpServerCurContextType.
--        Destroy the node of ibAcfpRuleEstablish.
--        Add a new node for IbAcfpPolicyDestIfFailAction.
--        Add a new node for IbAcfpPolicyPriority.
--        Add a new node for ibAcfpRuleTCPFlag.
--   V1.4 2007-12-19 Modified by Li Yugang
--        Modify the description of ibAcfpPolicyRowStatus.
--        Modify the description of ibAcfpRuleRowStatus.
--        Modify the status of ibAcfpRuleEstablish.
--        Modify the value of ibAcfpRuleTCPFlag.
--   V1.5 2009-11-30 Modified by Zhu Dengfeng
--        Add a new node for ibAcfpRuleSrcIPV6Address
--        Add a new node for ibAcfpRuleSrcPrefixLen
--        Add a new node for ibAcfpRuleDstIPV6Address
--        Add a new node for ibAcfpRuleDstPrefixLen
--        Add a new node for ibAcfpRuleTrafficType
--        Add a new node for ibAcfpRuleTypeOrLen
-- ==================================================================
IB-ACFP-MIB DEFINITIONS ::= BEGIN

IMPORTS
    IpAddress, Integer32, OBJECT-TYPE, MODULE-IDENTITY, NOTIFICATION-TYPE
        FROM SNMPv2-SMI
    RowStatus, TruthValue, MacAddress, DisplayString
        FROM SNMPv2-TC
    Ipv6Address
        FROM IPV6-TC
    InetAddressPrefixLength
        FROM INET-ADDRESS-MIB
    ibCommon
        FROM IB-OID-MIB;

--
-- Node definitions
--

ibAcfp MODULE-IDENTITY
    LAST-UPDATED "200607041936Z"
    ORGANIZATION
        "Intelbras S.A. Industria de Telecomunicacao Eletronica Brasileria."
    CONTACT-INFO
        ""
    DESCRIPTION
        "This MIB module defines a set of basic objects for
        configuring switches and routers to enable ACFP."
    REVISION    "200607041936Z"
    DESCRIPTION
        "Initial version"
    ::= { ibCommon 74 }

ibAcfpObjects OBJECT IDENTIFIER  ::= { ibAcfp 1 }

ibAcfpOAP  OBJECT IDENTIFIER ::= { ibAcfpObjects 1 }

--  ACFP server information
--      ACFP server should create this object and
--      advertise its capability

ibAcfpServer OBJECT IDENTIFIER ::= { ibAcfpOAP 1 }

ibAcfpServerInfo OBJECT-TYPE
    SYNTAX      BITS
        {
            ipserver(0),
            redirect(1),
            mirror(2),
            passThrough(3)
        }
    MAX-ACCESS  read-only
    STATUS      current
    DESCRIPTION
        "When retrieved, this object returns a set of bits
        indicating the capabilities (or configuration) of the
        switch or router.  The set bit is indication that a
        router or switch can support the action for
        security rule."
    ::= { ibAcfpServer 1 }

ibAcfpServerMaxLifetime OBJECT-TYPE
    SYNTAX      Integer32(0..2147483647)
    UNITS       "seconds"
    MAX-ACCESS  read-only
    STATUS      current
    DESCRIPTION
        "When retrieved, this object returns the maximum
        lifetime in seconds, that this router or switch allows
        policy rules to have."
    ::= { ibAcfpServer 2 }

ibAcfpServerPersistentRules OBJECT-TYPE
    SYNTAX      TruthValue
    MAX-ACCESS  read-only
    STATUS      current
    DESCRIPTION
        "When retrieved, this object returns true(1) if the
        ACFP MIB implementation can store policy rules
        persistently.  Otherwise, it returns false(2)."
    ::= { ibAcfpServer 3 }

ibAcfpServerCurContextType OBJECT-TYPE
    SYNTAX      INTEGER
        {
            no-context(1),
            context-VLANID(2),
            context-HG(3),
            context-FlowID(4),
            context-HGPlus(5)
        }
    MAX-ACCESS  read-only
    STATUS      current
    DESCRIPTION
        "In some circumstances, it's necessary that packets go to
        ACFP client with context from ACFP server.  However, the context
        perhaps is different.  ibAcfpServerCurContextType is
        used to distinguish this difference, ACFP client may
        process distinctively."
    ::= { ibAcfpServer 4 }

-- ACFP client Information.
--     This object is used for network management purpose.

ibAcfpClientInfo OBJECT IDENTIFIER ::= { ibAcfpOAP 2 }

ibAcfpClientInfoTable OBJECT-TYPE
    SYNTAX      SEQUENCE OF IbAcfpClientInfoEntry
    MAX-ACCESS  not-accessible
    STATUS      current
    DESCRIPTION
        "This table contains the basic information about ACFP client."
    ::= { ibAcfpClientInfo 1 }

ibAcfpClientInfoEntry OBJECT-TYPE
    SYNTAX      IbAcfpClientInfoEntry
    MAX-ACCESS  not-accessible
    STATUS      current
    DESCRIPTION
        "This list contains the basic information about ACFP client."
    INDEX
        {
            ibAcfpClientID
        }
    ::= { ibAcfpClientInfoTable 1 }

IbAcfpClientInfoEntry ::= SEQUENCE
    {
        ibAcfpClientID             Integer32,
        ibAcfpClientDescription    DisplayString,
        ibAcfpClientHwVersion      DisplayString,
        ibAcfpClientOSVersion      DisplayString,
        ibAcfpClientAppVersion     DisplayString,
        ibAcfpClientIP             IpAddress,
        ibAcfpClientMode           BITS,
        ibAcfpClientRowStatus      RowStatus
    }

ibAcfpClientID OBJECT-TYPE
    SYNTAX      Integer32(1..2147483647)
    MAX-ACCESS  accessible-for-notify
    STATUS      current
    DESCRIPTION
        "The identifier of ACFP client."
    ::= { ibAcfpClientInfoEntry 1 }

ibAcfpClientDescription OBJECT-TYPE
    SYNTAX      DisplayString(SIZE(0..64))
    MAX-ACCESS  read-create
    STATUS      current
    DESCRIPTION
        "Description of the application that is running on ACFP
        client, eg. IPS, VCX."
    ::= { ibAcfpClientInfoEntry 2 }

ibAcfpClientHwVersion OBJECT-TYPE
    SYNTAX      DisplayString(SIZE(0..64))
    MAX-ACCESS  read-create
    STATUS      current
    DESCRIPTION
        "The hardware revision of ACFP client."
    ::= { ibAcfpClientInfoEntry 3 }

ibAcfpClientOSVersion OBJECT-TYPE
    SYNTAX      DisplayString(SIZE(0..64))
    MAX-ACCESS  read-create
    STATUS      current
    DESCRIPTION
        "The operating system version running ACFP client."
    ::= { ibAcfpClientInfoEntry 4 }

ibAcfpClientAppVersion OBJECT-TYPE
    SYNTAX      DisplayString(SIZE(0..64))
    MAX-ACCESS  read-create
    STATUS      current
    DESCRIPTION
        "The application version running on ACFP client"
    ::= { ibAcfpClientInfoEntry 5 }

ibAcfpClientIP OBJECT-TYPE
    SYNTAX      IpAddress
    MAX-ACCESS  read-create
    STATUS      current
    DESCRIPTION
        "IP address of ACFP client."
    ::= { ibAcfpClientInfoEntry 6 }

ibAcfpClientMode OBJECT-TYPE
    SYNTAX      BITS
        {
            ipserver(0),
            redirect(1),
            mirror(2),
            passThrough(3)
        }
    MAX-ACCESS  read-create
    STATUS      current
    DESCRIPTION
        "ACFP client informs Router or switch which mode it is operating.
        Router or switch checks ibAcfpServerInfo to see whether it is
        capable of fulfilling this function.  If not, router or switch
        generates a trap informing ACFP client such OAP mode is not
        supported."
    DEFVAL { 0 }
    ::= { ibAcfpClientInfoEntry 7 }

ibAcfpClientRowStatus OBJECT-TYPE
    SYNTAX      RowStatus
    MAX-ACCESS  read-create
    STATUS      current
    DESCRIPTION
        "RowStatus, supports three states: createAndGo, active, destroy.
        Creation Operation Restriction:
        Node ibAcfpClientMode must be bound while creating a row. It is
        optional for other nodes.
        ACFP module must be enabled for the server while creating a row.
        The number of rows created must not exceed upper limit.

        Modification Operation Restriction:
        Nodes that do not support modification: ibAcfpClientMode.
        Nodes that support modification: ibAcfpClientDescription,
        ibAcfpClientHwVersion, ibAcfpClientOSVersion,
        ibAcfpClientAppVersion and ibAcfpClientIP.
        If the row to be modified does not exist, error returns directly.

        Deletion Operation Restriction:
        If the row to be deleted does not exist, success returns directly.
        "
    ::= { ibAcfpClientInfoEntry 8 }

-- Policy Information applied to Router or switch

ibAcfpPolicy OBJECT IDENTIFIER ::= { ibAcfpOAP 3 }

ibAcfpPolicyTable OBJECT-TYPE
    SYNTAX      SEQUENCE OF IbAcfpPolicyEntry
    MAX-ACCESS  not-accessible
    STATUS      current
    DESCRIPTION
        "This table lists all current policies for ACFP
        client(s).  Entries in this table are created or removed
        implicitly when entries in the ibAcfpRuleTable are
        created or removed, respectively.  A policy entry in this
        table only exists as long as there is rule of this policy
        in the ibAcfpRuleTable.  The table serves for listing the
        existing policies and their remaining lifetimes and for
        changing lifetimes of policies and implicitly of all policy
        members and all their member policy rules can be
        deleted by setting ibAcfpPolicyLifetime to 0."
    ::= { ibAcfpPolicy 1 }

ibAcfpPolicyEntry OBJECT-TYPE
    SYNTAX      IbAcfpPolicyEntry
    MAX-ACCESS  not-accessible
    STATUS      current
    DESCRIPTION
        "The list contains basic information of ACFP Policy."
    INDEX
        {
            ibAcfpClientID,
            ibAcfpPolicyIndex
        }
    ::= { ibAcfpPolicyTable 1 }

IbAcfpPolicyEntry ::= SEQUENCE
    {
        ibAcfpPolicyIndex              Integer32,
        ibAcfpPolicyInIfIndex          Integer32,
        ibAcfpPolicyOutIfIndex         Integer32,
        ibAcfpPolicyDestIfIndex        Integer32,
        ibAcfpPolicyContextID          Integer32,
        ibAcfpPolicyAdminStatus        INTEGER,
        ibAcfpPolicyLifetime           Integer32,
        ibAcfpPolicyTimeStart          OCTET STRING,
        ibAcfpPolicyTimeEnd            OCTET STRING,
        ibAcfpPolicyRowStatus          RowStatus,
        ibAcfpPolicyDestIfFailAction   INTEGER,
        ibAcfpPolicyPriority           INTEGER
    }

ibAcfpPolicyIndex OBJECT-TYPE
    SYNTAX      Integer32(1..2147483647)
    MAX-ACCESS  accessible-for-notify
    STATUS      current
    DESCRIPTION
        "The identifier of the Policy of ACFP client"
    ::= { ibAcfpPolicyEntry 1 }

ibAcfpPolicyInIfIndex OBJECT-TYPE
    SYNTAX      Integer32(0..2147483647)
    MAX-ACCESS  read-create
    STATUS      current
    DESCRIPTION
        "Packet is received from this interface.  The value of this object
        contains the same value of ifIndex of ifTable."
    DEFVAL {0}
    ::= { ibAcfpPolicyEntry 2}


ibAcfpPolicyOutIfIndex OBJECT-TYPE
    SYNTAX      Integer32(0..2147483647)
    MAX-ACCESS  read-create
    STATUS      current
    DESCRIPTION
        "Packet is sent to this interface.  The value of this object
        contains the same value of ifIndex of ifTable."
    DEFVAL {0}
    ::= { ibAcfpPolicyEntry 3 }

ibAcfpPolicyDestIfIndex OBJECT-TYPE
    SYNTAX      Integer32
    MAX-ACCESS  read-create
    STATUS      current
    DESCRIPTION
        "Through this interface, packet go to ACFP client from
        ACFP server.  The value of this object contains the same
        value of ifIndex of ifTable."
    DEFVAL {0}
    ::= { ibAcfpPolicyEntry 4 }

ibAcfpPolicyContextID OBJECT-TYPE
    SYNTAX      Integer32(0..2147483647)
    MAX-ACCESS  read-only
    STATUS      current
    DESCRIPTION
        "Internal id ACFP server allocated used to map to the interface.
        ACFP server may send packet with this ibAcfpPolicyContextID to
        ACFP client, ACFP client can make use of this ibAcfpPolicyContextID
        and find the policy. "
    ::= { ibAcfpPolicyEntry 5 }

ibAcfpPolicyAdminStatus OBJECT-TYPE
    SYNTAX      INTEGER
        {
            enable(1), -- policy is applied
            disable(2)   -- policy is not applied

        }
    MAX-ACCESS  read-create
    STATUS      current
    DESCRIPTION
        "The value of this object indicates the desired status of the
        policy."
    ::= { ibAcfpPolicyEntry 6 }

ibAcfpPolicyLifetime OBJECT-TYPE
    SYNTAX      Integer32(0..2147483647)
    UNITS       "seconds"
    MAX-ACCESS  read-create
    STATUS      current
    DESCRIPTION
        "When retrieved, this object delivers the maximum lifetime (seconds)
        of all the rules of this, i.e., of all the rows in ibAcfpRuleTable
        that have the same values of ibAcfpRulePolicyIndex and
        ibAcfpClientID.  Successfully writing to this object modifies the
        lifetime of all the rules of this.  Successfully writing a value
        of 0 terminates all the rules and implicitly deletes this as soon as
        all member entries are removed from the ibAcfpRuleTable. Note that
        after a lifetime expired, all the corresponding entry in the
        ibAcfpRuleTable will be removed and this will be deleted
        implicitly.  Writing to this object is processed by the ACFP MIB
        implementation by choosing a lifetime value that is greater than
        or equal to zero and less than or equal to the minimum of the requested
        value and the value specified by object ibAcfpServerMaxLifetime:

            0 <= lt_granted <= MINIMUM(lt_requested, lt_maximum)

        whereas:
        lt_granted is the actually granted lifetime by the ACFP MIB
        implementation.
        lt_requested is the requested lifetime of the ACFP client.
        lt_maximum is the value of object ibAcfpServerMaxLifetime.
        SNMP set requests to this object may be rejected or the value of
        the object after an accepted set operation may be less than the
        value that was contained in the SNMP set request."
    DEFVAL{ ibAcfpServerMaxLifetime }
    ::= { ibAcfpPolicyEntry 7 }

ibAcfpPolicyTimeStart OBJECT-TYPE
    SYNTAX      OCTET STRING(SIZE(8))
    MAX-ACCESS  read-create
    STATUS      current
    DESCRIPTION
        "Beginning time of this policy every day.  Eg. HH:MM:SS"
    ::= { ibAcfpPolicyEntry 8 }

ibAcfpPolicyTimeEnd OBJECT-TYPE
    SYNTAX      OCTET STRING(SIZE(8))
    MAX-ACCESS  read-create
    STATUS      current
    DESCRIPTION
        "Ending time of this policy every day.  Eg. HH:MM:SS"
    ::= { ibAcfpPolicyEntry 9 }

ibAcfpPolicyRowStatus OBJECT-TYPE
    SYNTAX      RowStatus
    MAX-ACCESS  read-create
    STATUS      current
    DESCRIPTION
        "RowStatus, supports three states: createAndGo, active, destroy.
        Creation Operation Restriction:
        The client corresponding to the index ibAcfpClientID must exist
        while creating a row.
        Nodes ibAcfpPolicyTimeStart and ibAcfpPolicyTimeEnd are
        bound together, and ibAcfpPolicyTimeEnd must be greater than
        ibAcfpPolicyTimeStart.
        The number of rows created on an incoming/outgoing interface
        cannot exceed the upper limit.
        The number of rows created cannot exceed the upper limit for each client.
        A packet matches a policy in the following order:
        - It first matches the policy with the highest priority.
        - For two policies with the same priority,
          it matches the one with the smallest client index.
        - For two policies with the same client index,
          it matches the one with the smallest policy index.

        Modification Operation Restriction:
        Nodes that do not support modification: ibAcfpPolicyInIfIndex,
        ibAcfpPolicyOutIfIndex, ibAcfpPolicyDestIfIndex,
        ibAcfpPolicyDestIfFailAction, ibAcfpPolicyPriority.
        Nodes that support modification: ibAcfpPolicyAdminStatus,
        ibAcfpPolicyLifetime, ibAcfpPolicyTimeStart and ibAcfpPolicyTimeEnd.
        While modifying a row, if the row corresponding to the index configured
        does not exist, error returns directly.
        While modifying a node, the restriction over ibAcfpPolicyTimeStart
        and ibAcfpPolicyTimeEnd is the same as creating a node.

        Deletion Operation Restriction:
        If the row to be deleted does not exist, success returns directly.
        "
    ::= { ibAcfpPolicyEntry 10 }

ibAcfpPolicyDestIfFailAction OBJECT-TYPE
    SYNTAX      INTEGER
        {
            delete(1),   -- delete all rules of the policy from driver
            reserve(2)   -- reserve all rules of the policy in driver
        }
    MAX-ACCESS  read-create
    STATUS      current
    DESCRIPTION
        "The value of this object indicates the action of the
        policy when the destination interface failed."
    DEFVAL { 1 }
    ::= { ibAcfpPolicyEntry 11 }

ibAcfpPolicyPriority OBJECT-TYPE
    SYNTAX      INTEGER
        {
            priority1(1), -- Priority 1 (MIN)
            priority2(2), -- Priority 2
            priority3(3), -- Priority 3
            priority4(4), -- Priority 4
            priority5(5), -- Priority 5
            priority6(6), -- Priority 6
            priority7(7), -- Priority 7
            priority8(8)  -- Priority 8 (MAX)
        }
    MAX-ACCESS  read-create
    STATUS      current
    DESCRIPTION
        "The value of this object indicates the priority of the
        policy.
        Priority8 is maximal priority.
        Priority1 is minimal priority."
    DEFVAL { 4 }
    ::= { ibAcfpPolicyEntry 12 }

-- Individual Rule policy Information applied to Router or switch

ibAcfpRule OBJECT IDENTIFIER ::= { ibAcfpOAP 4 }

ibAcfpRuleTable OBJECT-TYPE
    SYNTAX      SEQUENCE OF IbAcfpRuleEntry
    MAX-ACCESS  not-accessible
    STATUS      current
    DESCRIPTION
        "This table lists all the rules.  It is indexed by
        ibAcfpClientID, ibAcfpRulePolicyIndex and ibAcfpRuleIndex.
        Entries can be deleted by writing ibAcfpPolicyLifetime to 0."
    ::= { ibAcfpRule 1 }

ibAcfpRuleEntry OBJECT-TYPE
    SYNTAX      IbAcfpRuleEntry
    MAX-ACCESS  not-accessible
    STATUS      current
    DESCRIPTION
        "The list contains basic information of the rule."
    INDEX
        {
            ibAcfpClientID,
            ibAcfpPolicyIndex,
            ibAcfpRuleIndex
        }
    ::= { ibAcfpRuleTable 1 }

IbAcfpRuleEntry ::= SEQUENCE
    {
        ibAcfpRuleIndex           Integer32,
        ibAcfpRuleOperStatus      INTEGER,
        ibAcfpRuleAction          INTEGER,
        ibAcfpRuleAll             TruthValue,
        ibAcfpRuleSrcMAC          MacAddress,
        ibAcfpRuleDstMAC          MacAddress,
        ibAcfpRuleVlanStart       Integer32,
        ibAcfpRuleVlanEnd         Integer32,
        ibAcfpRuleProtocol        Integer32,
        ibAcfpRuleSrcIP           IpAddress,
        ibAcfpRuleSrcIPMask       IpAddress,
        ibAcfpRuleSrcOp           INTEGER,
        ibAcfpRuleSrcStartPort    Integer32,
        ibAcfpRuleSrcEndPort      Integer32,
        ibAcfpRuleDstIP           IpAddress,
        ibAcfpRuleDstIPMask       IpAddress,
        ibAcfpRuleDstOp           INTEGER,
        ibAcfpRuleDstStartPort    Integer32,
        ibAcfpRuleDstEndPort      Integer32,
        ibAcfpRulePrecedence      Integer32,
        ibAcfpRuleTos             Integer32,
        ibAcfpRuleDscp            Integer32,
        ibAcfpRuleEstablish       TruthValue,
        ibAcfpRuleFragment        TruthValue,
        ibAcfpRulePacketRate      Integer32,
        ibAcfpRuleRowStatus       RowStatus,
        ibAcfpRuleTCPFlag         Integer32,
        ibAcfpRuleSrcIPV6Address  Ipv6Address,
        ibAcfpRuleSrcPrefixLen    InetAddressPrefixLength,
        ibAcfpRuleDstIPV6Address  Ipv6Address,
        ibAcfpRuleDstPrefixLen    InetAddressPrefixLength,
        ibAcfpRuleTrafficType     BITS,
        ibAcfpRuleTypeOrLen       Integer32
    }

ibAcfpRuleIndex OBJECT-TYPE
    SYNTAX      Integer32(1..2147483647)
    MAX-ACCESS  accessible-for-notify
    STATUS      current
    DESCRIPTION
        "The identifier of the rules which have the same ibAcfpPolicyIndex
        and ibAcfpClientID.ibAcfpRuleIndex indicates rule sequence in the
        same policy."
    ::= { ibAcfpRuleEntry 1 }

ibAcfpRuleOperStatus OBJECT-TYPE
    SYNTAX      INTEGER
        {
            success(1), -- rule applied successfully to interface
            fail(2)     -- rule failed to apply to interface

        }
    MAX-ACCESS  read-only
    STATUS      current
    DESCRIPTION
        "The value of this object indicates the status of a rule.
        success : Applied rule to interface successfully.
        fail : Failed to apply rule to interface.
        "
    DEFVAL { fail }
    ::= { ibAcfpRuleEntry 2 }

ibAcfpRuleAction OBJECT-TYPE
    SYNTAX      INTEGER
        {
            permit(1),
            deny(2),
            redirect(3),
            mirror(4),
            rate(5)
        }
    MAX-ACCESS  read-create
    STATUS      current
    DESCRIPTION
        "The action of this rule."
    ::= { ibAcfpRuleEntry 3 }

ibAcfpRuleAll OBJECT-TYPE
    SYNTAX      TruthValue
    MAX-ACCESS  read-create
    STATUS      current
    DESCRIPTION
        "The rule match all packet or does not.
        true : all
        false : not all
        "
    DEFVAL { false }
    ::= { ibAcfpRuleEntry 4 }

ibAcfpRuleSrcMAC OBJECT-TYPE
    SYNTAX      MacAddress
    MAX-ACCESS  read-create
    STATUS      current
    DESCRIPTION
        "Source MAC of this rule."
    ::= { ibAcfpRuleEntry 5 }

ibAcfpRuleDstMAC OBJECT-TYPE
    SYNTAX      MacAddress
    MAX-ACCESS  read-create
    STATUS      current
    DESCRIPTION
        "Destination MAC of this rule."
    ::= { ibAcfpRuleEntry 6 }

ibAcfpRuleVlanStart OBJECT-TYPE
    SYNTAX      Integer32(0..4094)
    MAX-ACCESS  read-create
    STATUS      current
    DESCRIPTION
        "Starting VLAN id of this rule.
        0 : Invalid value"
    DEFVAL { 0 }
    ::= { ibAcfpRuleEntry 7 }

ibAcfpRuleVlanEnd OBJECT-TYPE
    SYNTAX      Integer32(0..4094)
    MAX-ACCESS  read-create
    STATUS      current
    DESCRIPTION
        "Ending VLAN id of this rule.
        0 : Invalid value"
    DEFVAL { 0 }
    ::= { ibAcfpRuleEntry 8 }

ibAcfpRuleProtocol OBJECT-TYPE
    SYNTAX      Integer32(0..255)
    MAX-ACCESS  read-create
    STATUS      current
    DESCRIPTION
        "The protocol-type of this rule.
        <0-255>  Protocol number
        gre      GRE tunneling(47)
        icmp     Internet Control Message Protocol(1)
        igmp     Internet Management Protocol(2)
        ip       Any IP protocol(0)
        ipinip   IP in IP tunneling(4)
        ospf     OSPF routing protocol(89)
        tcp      Transmission Control Protocol (6)
        udp      User Datagram Protocol (17)
        "
    DEFVAL { 0 }
    ::= { ibAcfpRuleEntry 9 }

ibAcfpRuleSrcIP OBJECT-TYPE
    SYNTAX      IpAddress
    MAX-ACCESS  read-create
    STATUS      current
    DESCRIPTION
        "Source IP address of this rule."
    ::= { ibAcfpRuleEntry 10 }

ibAcfpRuleSrcIPMask OBJECT-TYPE
    SYNTAX      IpAddress
    MAX-ACCESS  read-create
    STATUS      current
    DESCRIPTION
        "Source IP-address wild of this rule.  Eg. 0.0.0.255."
    ::= { ibAcfpRuleEntry 11 }

ibAcfpRuleSrcOp OBJECT-TYPE
    SYNTAX      INTEGER
        {
            equal(1),
            notEqual(2),
            lessThan(3),
            greaterThan(4),
            range(5),
            invalid(6)
        }
    MAX-ACCESS  read-create
    STATUS      current
    DESCRIPTION
        "Source Port operation for this rule"
    DEFVAL { invalid }
    ::= { ibAcfpRuleEntry 12 }

ibAcfpRuleSrcStartPort OBJECT-TYPE
    SYNTAX      Integer32(0..65535)
    MAX-ACCESS  read-create
    STATUS      current
    DESCRIPTION
        "Starting UDP/TCP Source Port number of this rule."
    ::= { ibAcfpRuleEntry 13 }

ibAcfpRuleSrcEndPort OBJECT-TYPE
    SYNTAX      Integer32(0..65535)
    MAX-ACCESS  read-create
    STATUS      current
    DESCRIPTION
        "Ending UDP/TCP Source Port of this rule."
    ::= { ibAcfpRuleEntry 14 }

ibAcfpRuleDstIP OBJECT-TYPE
    SYNTAX      IpAddress
    MAX-ACCESS  read-create
    STATUS      current
    DESCRIPTION
        "Destination IP address of this rule."
    ::= { ibAcfpRuleEntry 15 }

ibAcfpRuleDstIPMask OBJECT-TYPE
    SYNTAX      IpAddress
    MAX-ACCESS  read-create
    STATUS      current
    DESCRIPTION
        "Destination IP-address wild of this rule.  Eg. 0.0.0.255"
    ::= { ibAcfpRuleEntry 16 }

ibAcfpRuleDstOp OBJECT-TYPE
    SYNTAX      INTEGER
        {
            equal(1),
            nonEqual(2),
            lessThan(3),
            greaterThan(4),
            range(5),
            invalid(6)
        }
    MAX-ACCESS  read-create
    STATUS      current
    DESCRIPTION
        "Destination Port operation for this rule"
    DEFVAL { invalid }
    ::= { ibAcfpRuleEntry 17 }

ibAcfpRuleDstStartPort OBJECT-TYPE
    SYNTAX      Integer32(0..65535)
    MAX-ACCESS  read-create
    STATUS      current
    DESCRIPTION
        "Starting UDP/TCP Destination Port number of this rule."
    ::= { ibAcfpRuleEntry 18 }

ibAcfpRuleDstEndPort OBJECT-TYPE
    SYNTAX      Integer32(0..65535)
    MAX-ACCESS  read-create
    STATUS      current
    DESCRIPTION
        "Ending UDP/TCP Destination Port of this rule."
    ::= { ibAcfpRuleEntry 19 }

ibAcfpRulePrecedence OBJECT-TYPE
    SYNTAX      Integer32(0..7|255)
    MAX-ACCESS  read-create
    STATUS      current
    DESCRIPTION
        "The value of precedence field in IP header.
        <255>                  Invalid value
        <0-7>                  value of precedence
        routine(0)             Routine precedence
        priority(1)            Priority precedence
        immediate(2)           Immediate precedence
        flash(3)               Flash precedence
        flash-override(4)      Flash Override precedence
        critical(5)            Critical precedence
        internet(6)            Network Control precedence
        network(7)             Internetwork Control precedence
        "
    DEFVAL { 255 }
    ::= { ibAcfpRuleEntry 20 }

ibAcfpRuleTos OBJECT-TYPE
    SYNTAX      Integer32(0..15|255)
    MAX-ACCESS  read-create
    STATUS      current
    DESCRIPTION
        "The value of TOS field in IP header.
        <255>                  Invalid value
        <0-15>                 value of ToS (Type of Service)
        Normal(0)              normal service
        min-monetary-cost(1)   minimum monetary cost
        max-reliability(2)     maximum reliability
        max-throughput(4)      maximum throughput
        min-delay(8)           minimum delay
        "
    DEFVAL { 255 }
    ::= { ibAcfpRuleEntry 21 }

ibAcfpRuleDscp OBJECT-TYPE
    SYNTAX      Integer32(0..63|255)
    MAX-ACCESS  read-create
    STATUS      current
    DESCRIPTION
        "The value of DSCP.
        <255>                  Invalid value
        <0-63>                 value of DSCP
        Be(0)                  best effort
        af11(10)               assured forwarding 11 service
        af12(12)               assured forwarding 12 service
        af13(14)               assured forwarding 13 service
        af21(18)               assured forwarding 18 service
        af22(20)               assured forwarding 20 service
        af23(22)               assured forwarding 22 service
        af31(26)               assured forwarding 31 service
        af32(28)               assured forwarding 32 service
        af33(30)               assured forwarding 33 service
        af41(34)               assured forwarding 41 service
        af42(36)               assured forwarding 42 service
        af43(38)               assured forwarding 43 service
        cs1(8)                 class selector 1 service
        cs2(16)                class selector 2 service
        cs3(24)                class selector 3 service
        cs4(32)                class selector 4 service
        cs5(40)                class selector 5 service
        cs6(48)                class selector 6 service
        cs7(56)                class selector 7 service
        ef(46)                 expedited forwarding service
        "
    DEFVAL { 255 }
    ::= { ibAcfpRuleEntry 22 }

ibAcfpRuleEstablish OBJECT-TYPE
    SYNTAX      TruthValue
    MAX-ACCESS  read-create
    STATUS      deprecated
    DESCRIPTION
        "Establish Flag.  Matches the TCP packets with the ACK
        and/or RST flag, including the TCP packets of these
        types: SYN+ACK, ACK, FIN+ACK, RST, RST+ACK."
    DEFVAL { false }
    ::= { ibAcfpRuleEntry 23 }

ibAcfpRuleFragment OBJECT-TYPE
    SYNTAX      TruthValue
    MAX-ACCESS  read-create
    STATUS      current
    DESCRIPTION
        "The flag of matching fragmented packet."
    DEFVAL { false }
    ::= { ibAcfpRuleEntry 24 }

ibAcfpRulePacketRate OBJECT-TYPE
    SYNTAX      Integer32
    MAX-ACCESS  read-create
    STATUS      current
    DESCRIPTION
        "Packet rate (Kbps) of this rule."
    ::= { ibAcfpRuleEntry 25 }

ibAcfpRuleRowStatus OBJECT-TYPE
    SYNTAX      RowStatus
    MAX-ACCESS  read-create
    STATUS      current
    DESCRIPTION
        "RowStatus, supports three states: createAndGo, active, destroy.
        Creation Operation Restriction:
        Node ibAcfpRuleAction must be bound while creating a line.
        Nodes ibAcfpRuleAll and ibAcfpRuleProtocol, ibAcfpRuleSrcIP,
        ibAcfpRuleSrcIPMask, ibAcfpRuleDstIP, ibAcfpRuleSrcOp,
        ibAcfpRuleSrcStartPort, ibAcfpRuleSrcEndPort, ibAcfpRuleDstIP,
        ibAcfpRuleDstIPMask, ibAcfpRuleDstOp, ibAcfpRuleDstStartPort,
        ibAcfpRuleDstEndPort, ibAcfpRulePrecedence, ibAcfpRuleTos,
        ibAcfpRuleDscp, ibAcfpRuleTCPFlag, ibAcfpRuleFragment are
        mutually exclusive.
        Nodes ibAcfpRuleSrcIP and ibAcfpRuleSrcIPMask are bound together,
        otherwise, the source IP address is neglected.
        The restriction over ibAcfpRuleDstIP and ibAcfpRuleDstIPMask is the
        same as ibAcfpRuleSrcIP and ibAcfpRuleSrcIPMask.
        Nodes ibAcfpRuleDscp and ibAcfpRulePrecedence, ibAcfpRuleTos are
        mutually exclusive.
        If the node ibAcfpRuleSrcOp is bound to range(5),
        ibAcfpRuleSrcStartPort and ibAcfpRuleSrcEndPort must be bound together,
        and ibAcfpRuleSrcEndPort must be greater than ibAcfpRuleSrcStartPort.
        If the node ibAcfpRuleSrcOp is bound to equal(1), notEqual(2),
        lessThan(3) or greaterThan(4), ibAcfpRuleSrcStartPort must be bound
        together, and ibAcfpRuleSrcEndPort is neglected.
        The restriction over ibAcfpRuleDstOp, ibAcfpRuleDstStartPort and
        ibAcfpRuleDstEndPort is the same as ibAcfpRuleSrcOp,
        ibAcfpRuleSrcStartPort and ibAcfpRuleSrcEndPort.
        If the node ibAcfpRuleAction is bound to redirect(3) or mirror(4),
        the destination interfaces of the policy the rule belonging to must exist;
        The number of rows created cannot exceed the upper limit for each policy,
        each inbound interface and each outbound interface.

        Modification Operation Restriction:
        The row does not support modification.

        Deletion Operation Restriction
        If the row to be deleted does not exist, success returns directly.
        "
    ::= { ibAcfpRuleEntry 26 }

ibAcfpRuleTCPFlag OBJECT-TYPE
    SYNTAX      Integer32(0..65535)
    MAX-ACCESS  read-create
    STATUS      current
    DESCRIPTION
        "TCP Flag.
        <0>       don't care for TCP flag to match packets
        <1-65535> care for TCP flag to match packets,
                  the value is combination of next list.
                  URG_VALID (1 << 13)
                  URG_SET   (1 << 5)
                  ACK_VALID (1 << 12)
                  ACK_SET   (1 << 4)
                  PSH_VALID (1 << 11)
                  PSH_SET   (1 << 3)
                  RST_VALID (1 << 10)
                  RST_SET   (1 << 2)
                  SYN_VALID (1 << 9)
                  SYN_SET   (1 << 1)
                  FIN_VALID (1 << 8)
                  FIN_SET   1

        Matches the TCP packets with the URG and/or
        ACK and/or PSH and/or RST and/or SYN and/or FIN flag,
        including the TCP packets of these
        types: SYN+ACK, ACK, FIN+ACK, RST, RST+ACK."
    DEFVAL { 0 }
    ::= { ibAcfpRuleEntry 27 }

ibAcfpRuleSrcIPV6Address OBJECT-TYPE
    SYNTAX      Ipv6Address
    MAX-ACCESS  read-create
    STATUS      current
    DESCRIPTION
        "Source IPv6 address of this rule."
    ::= { ibAcfpRuleEntry 28 }

ibAcfpRuleSrcPrefixLen OBJECT-TYPE
    SYNTAX      InetAddressPrefixLength
    MAX-ACCESS  read-create
    STATUS      current
    DESCRIPTION
        "Source IPv6 address prefix length of this rule. Eg. 64."
    ::= { ibAcfpRuleEntry 29 }

ibAcfpRuleDstIPV6Address OBJECT-TYPE
    SYNTAX      Ipv6Address
    MAX-ACCESS  read-create
    STATUS      current
    DESCRIPTION
        "Destination IPv6 address of this rule."
    ::= { ibAcfpRuleEntry 30 }

ibAcfpRuleDstPrefixLen OBJECT-TYPE
    SYNTAX      InetAddressPrefixLength
    MAX-ACCESS  read-create
    STATUS      current
    DESCRIPTION
        "Destination IPv6 address prefix length of this rule. Eg. 64."
    ::= { ibAcfpRuleEntry 31 }

ibAcfpRuleTrafficType OBJECT-TYPE
    SYNTAX      BITS
        {
            unicast(0),
            multicast(1),
            broadcast(2)
        }
    MAX-ACCESS  read-create
    STATUS      current
    DESCRIPTION
        "Traffic type of this rule. When retrieved, this object
        returns a set of bits indicating the traffic type."
    ::= { ibAcfpRuleEntry 32 }

ibAcfpRuleTypeOrLen OBJECT-TYPE
    SYNTAX      Integer32(0..65535)
    MAX-ACCESS  read-create
    STATUS      current
    DESCRIPTION
        "The type or length of ethernet packet.
        For Ethernet II encapsulation, it stands for packet type.
        For 802.3 encapsulation, it stands for packet length."
    ::= { ibAcfpRuleEntry 33 }

-- Notifications.  The definition of ibAcfpNotifications makes notification
-- registrations reversible (see STD 58, RFC 2578, section 8.5).

ibAcfpNotifications OBJECT IDENTIFIER  ::= { ibAcfpOAP 5 }

ibAcfpCurContextChanged NOTIFICATION-TYPE
    OBJECTS
        {
            ibAcfpServerCurContextType
        }
    STATUS      current
    DESCRIPTION
        "This notification is sent when router or switch changed
        ibAcfpServerCurContextType."
    ::= { ibAcfpNotifications 1 }

ibAcfpClientRegister NOTIFICATION-TYPE
    OBJECTS
        {
            ibAcfpClientID
        }
    STATUS      current
    DESCRIPTION
        "This notification is sent when the ACFP client is registered."
    ::= { ibAcfpNotifications 2 }

ibAcfpClientUnRegister NOTIFICATION-TYPE
    OBJECTS
        {
            ibAcfpClientID
        }
    STATUS      current
    DESCRIPTION
        "This notification is sent when the ACFP client is unregistered."
    ::= { ibAcfpNotifications 3 }

ibAcfpClientDead NOTIFICATION-TYPE
    OBJECTS
        {
            ibAcfpClientID
        }
    STATUS      current
    DESCRIPTION
        "This notification is sent when the ACFP client is not responding."
    ::= { ibAcfpNotifications 4 }

ibAcfpNotSupportedOAPMode NOTIFICATION-TYPE
    OBJECTS
        {
            ibAcfpClientID,
            ibAcfpClientMode,
            ibAcfpServerInfo
        }
    STATUS      current
    DESCRIPTION
        "This notification is sent when router or switch cannot support OAP
        mode that ACFP client wants to operate on."
    ::= { ibAcfpNotifications 5 }

ibAcfpLifetimeChangeEvent NOTIFICATION-TYPE
    OBJECTS
        {
            ibAcfpPolicyLifetime
        }
    STATUS      current
    DESCRIPTION
        "This notification can be generated for indicating that
        The lifetime of all member rules of the was
        changed by successfully writing to object
        ibAcfpPolicyLifetime.  Note that this notification
        is only sent if the lifetime of a policy was changed by
        successfully writing to object ibAcfpPolicyLifetime."
    ::= { ibAcfpNotifications 6 }

ibAcfpRuleCreatedEvent NOTIFICATION-TYPE
    OBJECTS
        {
            ibAcfpRuleIndex
        }
    STATUS      current
    DESCRIPTION
        "This notification is sent when a new rule is created."
    ::= { ibAcfpNotifications 7 }

ibAcfpRuleDeletedEvent NOTIFICATION-TYPE
    OBJECTS
        {
            ibAcfpRuleIndex
        }
    STATUS      current
    DESCRIPTION
        "This notification is sent when a rule is deleted."
    ::= { ibAcfpNotifications 8 }

ibAcfpRuleErrorEvent NOTIFICATION-TYPE
    OBJECTS
        {
            ibAcfpRuleIndex
        }
    STATUS      current
    DESCRIPTION
        "This notification is sent when rule cannot be applied."
    ::= { ibAcfpNotifications 9 }

ibAcfpLifetimeExpireEvent NOTIFICATION-TYPE
    OBJECTS
        {
            ibAcfpPolicyLifetime
        }
    STATUS      current
    DESCRIPTION
        "This notification is sent
         when the time of the policy existed exceeds its lifetime."
    ::= { ibAcfpNotifications 10 }

END
