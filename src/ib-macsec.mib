-- ==========================================================================
-- Copyright (C) 2023 Intelbras S.A. All rights reserved.
--
-- Description: The file defines a MIB to provide MACSEC configuration
-- Reference:
-- Version: V1.1
-- History:
--   V1.0 2015-09-01 created by liubo
--   V1.1 2022-05-11 Add ibMACsecTrap by zhengjun
-- ==========================================================================
IB-MACSEC-MIB DEFINITIONS ::= BEGIN

IMPORTS
    MODULE-IDENTITY, OBJECT-TYPE, NOTIFICATION-TYPE
        FROM SNMPv2-SMI
    InterfaceIndex, ifDescr, ifIndex
        FROM IF-MIB
    ibCommon
        FROM IB-OID-MIB;

ibMACsec MODULE-IDENTITY
    LAST-UPDATED "202205111427Z"
    ORGANIZATION
        "Intelbras S.A. Industria de Telecomunicacao Eletronica Brasileria."
    CONTACT-INFO
        ""
    DESCRIPTION
        "This MIB provides information for MACSEC configuration.
        MACSEC presents secure communication method."
    REVISION "202205111427Z"
    DESCRIPTION
        "This version added the MKA session lifetime expired notification and
        its recovery notification."
    REVISION "201509011615Z"
    DESCRIPTION
        "Initial version."
    ::= { ibCommon 163 }

ibMACsecCFGObjects OBJECT IDENTIFIER ::= { ibMACsec 1 }

-- ==========================================================================
-- ibMACsecCFGPortTable OBJECT
-- ==========================================================================
ibMACsecCFGPortTable OBJECT-TYPE
    SYNTAX SEQUENCE OF IbMACsecCFGPortEntry
    MAX-ACCESS not-accessible
    STATUS current
    DESCRIPTION
    "The MACsec port table."
::= { ibMACsecCFGObjects 1 }

ibMACsecCFGPortEntry OBJECT-TYPE
    SYNTAX IbMACsecCFGPortEntry
    MAX-ACCESS not-accessible
    STATUS current
    DESCRIPTION
    "The MACsec port entry."
    INDEX { ibMACsecCFGPortIndex }
::= { ibMACsecCFGPortTable 1 }

IbMACsecCFGPortEntry ::= SEQUENCE {
    ibMACsecCFGPortIndex         InterfaceIndex,
    ibMACsecCFGPortPSKCKNName    OCTET STRING,
    ibMACsecCFGPortPSKCAKValue   OCTET STRING }

ibMACsecCFGPortIndex OBJECT-TYPE
    SYNTAX      InterfaceIndex
    MAX-ACCESS  not-accessible
    STATUS      current
    DESCRIPTION
    "An interface index indicates the port number associated with this port."
::= { ibMACsecCFGPortEntry 1 }

ibMACsecCFGPortPSKCKNName OBJECT-TYPE
    SYNTAX      OCTET STRING (SIZE(0..128))
    MAX-ACCESS  read-write
    STATUS      current
    DESCRIPTION
    "The connectivity asociation key name."
::= { ibMACsecCFGPortEntry 2 }

ibMACsecCFGPortPSKCAKValue OBJECT-TYPE
    SYNTAX      OCTET STRING (SIZE(0..128))
    MAX-ACCESS  read-write
    STATUS      current
    DESCRIPTION
    "The connectivity asociation key value."
::= { ibMACsecCFGPortEntry 3 }

-- trap --
ibMACsecTrap      OBJECT IDENTIFIER ::= { ibMACsec 2 }

ibMACsecTrapPrex OBJECT IDENTIFIER ::= { ibMACsecTrap 0 }

ibMACsecTimeout NOTIFICATION-TYPE
    OBJECTS
        {
            ifIndex,
            ifDescr,
            ibMACsecDeviceRole
        }
    STATUS       current
    DESCRIPTION
        "The lifetime of the MKA session on the specified local interface expired."
    ::= { ibMACsecTrapPrex 1 }

ibMACsecTimeoutResume NOTIFICATION-TYPE
    OBJECTS
        {
            ifIndex,
            ifDescr,
            ibMACsecDeviceRole
        }
    STATUS       current
    DESCRIPTION
        "The MKA session on the specified local interface restored."
    ::= { ibMACsecTrapPrex 2 }

ibMACsecTrapOjbects OBJECT IDENTIFIER ::= { ibMACsecTrap 1 }

ibMACsecDeviceRole OBJECT-TYPE
    SYNTAX INTEGER
        {
        unknown(1),
        server(2),
        client(3)
        }
    MAX-ACCESS accessible-for-notify
    STATUS current
    DESCRIPTION
        "The role of the local device role in MKA.
        unknown : The device role is unknown.
        server  : The device is the key server.
        client  : The device is the client.
        "
    ::= { ibMACsecTrapOjbects 1 }

END
