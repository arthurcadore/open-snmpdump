-- ====================================================================
-- Copyright (C) 2023 Intelbras S.A. All rights reserved.
--
-- Description: The MIB is designed to get IKE tunnels' statistic information.
--
-- Reference:
-- Version: 1.5
-- History:
--     V1.0: The initial version created by Caixiansen, Renweichun and Maoyu.
--     V1.1: modified by liguanmin.2005.1.19
--           In order to describe DPD work parameters if a tunnel enable
--           DPD function, two nodes have added in IbIKETunnelEntry .those nodes are
--           ibIKETunDpdIntervalTime and ibIKETunDpdTimeOut.
--     V1.2: Modified by Caixiansen Mar.3 2005
--           Two values 'modp1536(5)' and 'modp2048(14)'are added for data type
--           'IbDiffHellmanGrp' .
--     V1.3: Modified by Liukan Dec.8 2008
--           Three values 'aesCbc128(8)', 'aesCbc192(9)' and 'aesCbc256(10)' are added
--           to data type 'IbEncryptAlgo'.
--           Value description of data type 'IbIKENegoMode' is changed from 'aggressive(4)' to
--           'aggressiveMode(4)'.
--     V1.4: Modified by Weiyanheng Jun.28 2012
--           1) 'dsaSignatures(2)' is added to data type 'IbIKEAuthMethod'.
--           2) 'none(0)' 'invalidGroup(2147483647)' and 'dhGroup24(24)' are added
--               to data type 'IbDiffHellmanGrp'.
--           3) Value description of data type 'IbDiffHellmanGrp' is changed
--              from 'modp768(1)' 'modp1024(2)' 'modp1536(5)' 'modp2048(14)'
--              to 'dhGroup1(1)' 'dhGroup2(2)' 'dhGroup5(5)' 'dhGroup14(14)'.
--           4) 'aesCtr(11)', 'aesCamelliaCbc(12)', 'rc4(13)' and 'invalidAlg(2147483647)'
--               are added to data type 'IbEncryptAlgo'.
--           5) Value description of data type 'IbAuthAlgo' is changed from
--              'sha(2)' to 'sha1(2)'.
--           6) 'sha256(3)', 'sha384(4)', 'sha512(5)' and 'invalidAlg(2147483647)'
--              are added to data type 'IbAuthAlgo'.
--           7) In order to describe the IPV4 and IPV6 address of a tunnel, four
--              nodes have added in IbIKETunnelEntry.
--              These nodes are ibIKETunLocalInetAddrType, ibIKETunLocalInetAddr,
--              ibIKETunRemoteInetAddrType and ibIKETunRemoteInetAddr.
--           8) 'ibIKETunLocalAddr' and 'ibIKETunRemoteAddr' are deprecated.
--     V1.5: Modified by Yangbaotao and Zhaoming Apr.25 2021
--           1) One value 'gmMainMode(128)' is added to data type 'IbIKENegoMode'.
--           2) Two values 'rsaDigitalEnvelope(5)' and 'sm2DigitalEnvelope(6)' are added
--              to data type 'IbIKEAuthMethod'.
--           3) Four values 'sm1Cbc128(128)','sm1Cbc192(129)','sm1Cbc256(130)' and 'sm4Cbc(131)'
--              are added to data type 'IbEncryptAlgo'.
--           4) One value 'sm3(128)' is added to data type 'IbAuthAlgo'.
--              Deprecated ibIKETunLocalValue1 and ibIKETunRemoteValue1,
--              added ibIKETunLocalValue3 and ibIKETunRemoteValue3.
-- =====================================================================
IB-IKE-MONITOR-MIB DEFINITIONS ::= BEGIN

    IMPORTS
        DisplayString,TEXTUAL-CONVENTION
            FROM SNMPv2-TC
        IpAddress, Integer32, Counter32, Counter64, OBJECT-TYPE, MODULE-IDENTITY,
        Gauge32, NOTIFICATION-TYPE
            FROM SNMPv2-SMI
        InetAddressType, InetAddress
            FROM INET-ADDRESS-MIB
        MODULE-COMPLIANCE, OBJECT-GROUP, NOTIFICATION-GROUP
            FROM SNMPv2-CONF
        ibCommon
            FROM IB-OID-MIB;

    ibIKEMonitor MODULE-IDENTITY
        LAST-UPDATED "202104241858Z"            -- Apr. 25, 2021  GMT
        ORGANIZATION
            "Intelbras S.A. Industria de Telecomunicacao Eletronica Brasileria."
        CONTACT-INFO
            ""
        DESCRIPTION
            "The MIB is designed to get statistic information of
            IKE tunnels. With this MIB, we can get information of a certain IKE tunnel
            or all IKE tunnels"
        REVISION "202104241858Z"
         DESCRIPTION
            "Data type IbIKENegoMode,IbIKEAuthMethod,IbEncryptAlgo and IbAuthAlgo are added.
             Deprecate ibIKETunLocalValue1 and ibIKETunRemoteValue1,
             add ibIKETunLocalValue3 and ibIKETunRemoteValue3."
        ::= { ibCommon 30 }

        IbIKENegoMode   ::= TEXTUAL-CONVENTION
                   STATUS     current
                   DESCRIPTION
                       "The IKE negotiation mode."
                   SYNTAX INTEGER {
                             mainMode(2),
                             aggressiveMode(4),
                             quickMode(32),
                             gmMainMode(128)

                          }

    IbIKEAuthMethod   ::= TEXTUAL-CONVENTION
        STATUS     current
        DESCRIPTION
        "The authentication method used in IKE negotiations."
        SYNTAX INTEGER {
            preSharedKey(1),
            dsaSignatures(2),
            rsaSignatures(3),
            rsaDigitalEnvelope(5),
            sm2DigitalEnvelope(6)
        }

    IbDiffHellmanGrp   ::= TEXTUAL-CONVENTION
        STATUS     current
        DESCRIPTION
           "The Diffie Hellman Group used in IKE and IPsec negotiations."
        SYNTAX INTEGER {
            none(0),
            dhGroup1(1),
            dhGroup2(2),
            dhGroup5(5),
            dhGroup14(14),
            dhGroup24(24),
            invalidGroup(2147483647)
        }

    IbEncryptAlgo   ::= TEXTUAL-CONVENTION
        STATUS     current
        DESCRIPTION
            "The encryption algorithm used in IKE and IPsec negotiations."
        SYNTAX INTEGER {
            none(0),
            desCbc(1),
            ideaCbc(2),
            blowfishCbc(3),
            rc5R16B64Cbc(4),
            tripleDesCbc(5),
            castCbc(6),
            aesCbc(7),
            aesCbc128(8),
            aesCbc192(9),
            aesCbc256(10),
            aesCtr(11),
            aesCamelliaCbc(12),
            rc4(13),
            sm1Cbc128(128),
            sm1Cbc192(129),
            sm1Cbc256(130),
            sm4Cbc(131),
            invalidAlg(2147483647)
        }

    IbAuthAlgo   ::= TEXTUAL-CONVENTION
        STATUS     current
        DESCRIPTION
            "The authentication algorithm used in IKE negotiations."
        SYNTAX INTEGER {
            none(0),
            md5(1),
            sha1(2),
            sha256(3),
            sha384(4),
            sha512(5),
            sm3(128),
            invalidAlg(2147483647)
        }

        IbTrapStatus   ::= TEXTUAL-CONVENTION
                   STATUS     current
                   DESCRIPTION
                       "The switch which determines whether send a trap or not."
                   SYNTAX INTEGER {
                             enabled(1),
                             disabled(2)
                          }

        IbIKEIDType   ::= TEXTUAL-CONVENTION
                   STATUS     current
                   DESCRIPTION
                       "The type of IKE Identity."
                   SYNTAX INTEGER {
                             reserved(0),
                             ipv4Addr(1),
                             fqdn(2),             -- fully-qualified domain name
                             userFqdn(3),         -- fully-qualified username
                             ipv4AddrSubnet(4),
                             ipv6Addr(5),
                             ipv6AddrSubnet(6),
                             ipv4AddrRange(7),
                             ipv6AddrRange(8),
                             derAsn1Dn(9),        -- the binary DER encoding of an ASN.1 X.500 Distinguished Name
                                                  -- [X.501] of the principal whose certificates are being exchanged
                                                  -- to establish the SA.

                             derAsn1Gn(10),       -- the binary DER encoding of an ASN.1 X.500 GeneralName [X.509]
                                                  -- of the principal whose certificates are being exchanged to
                                                  -- establish the SA.

                             keyId(11)            -- specifies an opaque byte stream which may be used to pass
                                                  -- vendor-specific information necessary to identify which
                                                  -- pre-shared key should be used to authenticate Aggressive
                                                  -- mode negotiations.
                          }

        IbIKETunnelState   ::= TEXTUAL-CONVENTION
                   STATUS     current
                   DESCRIPTION
                       "The state of the IKE tunnel."
                   SYNTAX INTEGER {
                             active(1),
                             timeout(2)
                          }


-- ========================================================================
-- Node definitions
-- ========================================================================
--Begin the node of ibIKEObjects.

        ibIKEObjects OBJECT IDENTIFIER ::= { ibIKEMonitor 1 }
-- ================================================
-- Begin the table of ibIKETunnelTable.
-- ================================================

        ibIKETunnelTable OBJECT-TYPE
            SYNTAX SEQUENCE OF IbIKETunnelEntry
            MAX-ACCESS not-accessible
            STATUS current
            DESCRIPTION
                "The IPsec Phase-1 Internet Key Exchange Tunnel Table.
                 There is one entry in this table for each active IPsec Phase-1 IKE Tunnel."
            ::= { ibIKEObjects 1 }

        ibIKETunnelEntry OBJECT-TYPE
            SYNTAX IbIKETunnelEntry
            MAX-ACCESS not-accessible
            STATUS current
            DESCRIPTION
                "The entry contains the information about ibIKETunnelTable, such as negotiate mode,
                 encryption algorithm and authentication algorithm, etc."
            INDEX { ibIKETunIndex }
            ::= { ibIKETunnelTable 1 }

    IbIKETunnelEntry ::=
        SEQUENCE {
            ibIKETunIndex
                Integer32,
            ibIKETunLocalType
                IbIKEIDType,
            ibIKETunLocalValue1
                DisplayString,
            ibIKETunLocalValue2
                DisplayString,
            ibIKETunLocalAddr
                IpAddress,
            ibIKETunRemoteType
                IbIKEIDType,
            ibIKETunRemoteValue1
                DisplayString,
            ibIKETunRemoteValue2
                DisplayString,
            ibIKETunRemoteAddr
                IpAddress,
            ibIKETunInitiator
                INTEGER,
            ibIKETunNegoMode
                IbIKENegoMode,
            ibIKETunDiffHellmanGrp
                IbDiffHellmanGrp,
            ibIKETunEncryptAlgo
                IbEncryptAlgo,
            ibIKETunHashAlgo
                IbAuthAlgo,
            ibIKETunAuthMethod
                IbIKEAuthMethod,
            ibIKETunLifeTime
                Integer32,
            ibIKETunActiveTime
                Integer32,
            ibIKETunRemainTime
                Integer32,
            ibIKETunTotalRefreshes
                Counter32,
            ibIKETunState
                IbIKETunnelState,
            ibIKETunDpdIntervalTime
                Integer32,
            ibIKETunDpdTimeOut
                Integer32,
            ibIKETunLocalInetAddrType
                InetAddressType,
            ibIKETunLocalInetAddr
                InetAddress,
            ibIKETunRemoteInetAddrType
                InetAddressType,
            ibIKETunRemoteInetAddr
                InetAddress,
            ibIKETunLocalValue3
                OCTET STRING,
            ibIKETunRemoteValue3
                OCTET STRING
        }

        ibIKETunIndex OBJECT-TYPE
            SYNTAX Integer32 (1..2147483647)
            MAX-ACCESS accessible-for-notify
            STATUS current
            DESCRIPTION
                "The index of the IPsec Phase-1 IKE Tunnel Table.
                 The value of the index is a number which begins
                 at one and is incremented with each tunnel that
                 is created. The value of this object will wrap
                 at 2147483647."
            ::= { ibIKETunnelEntry 1 }

        ibIKETunLocalType OBJECT-TYPE
            SYNTAX IbIKEIDType
            MAX-ACCESS read-only
            STATUS current
            DESCRIPTION
                "The type of local peer identity."
            ::= { ibIKETunnelEntry 2 }

        ibIKETunLocalValue1 OBJECT-TYPE
            SYNTAX DisplayString(SIZE(0..255))
            MAX-ACCESS read-only
            STATUS deprecated
            DESCRIPTION
                "The value of the local peer identity.

                If the local peer type is ipv4Addr/ipv6Addr, this is the IP address
                used to identify the local peer.

                If the local peer type is ipv4AddrSubnet/ipv6AddrSubnet, this is
                the subnet address.

                If the local peer type is ipv4AddrRange/ipv6AddrRange, this is
                the beginning IP address of the range.

                If the local peer type is fqdn/userFqdn, this is the host name
                used to identify the local peer.

                If the local peer type is derAsn1Dn, this is the binary DER
                encoding of an ASN.1 X.500 Distinguished Name [X.501] of the
                principal whose certificates are being exchanged to establish
                the SA.

                If the local peer type is derAsn1Gn, this is the binary DER
                encoding of an ASN.1 X.500 GeneralName [X.509] of the principal
                whose certificates are being exchanged to establish the SA.

                If the local peer type is keyId, this is an opaque byte
                stream which may be used to pass vendor-specific information
                necessary to identify which pre-shared key should be used to
                authenticate Aggressive mode negotiations.

                The local peer identity may not exceed 255 characters in length.
                The complete value will be displayed by ibIKETunLocalValue3"
            ::= { ibIKETunnelEntry 3 }

        ibIKETunLocalValue2 OBJECT-TYPE
            SYNTAX DisplayString(SIZE(0..255))
            MAX-ACCESS read-only
            STATUS current
            DESCRIPTION
                "The second specification of the local peer's IP address.

                 If the local peer type is ipv4AddrSubnet/ipv6AddrSubnet, this
                 is the subnet mask.

                 If the local peer type is ipv4AddrRange/ipv6AddrRange, this is
                 the ending IP address of the range.

                 If the local peer type are others, this is a zero-length string."
            ::= { ibIKETunnelEntry 4 }

        ibIKETunLocalAddr OBJECT-TYPE
            SYNTAX IpAddress
            MAX-ACCESS read-only
            STATUS deprecated
            DESCRIPTION
                "The IP address of the local endpoint for the IPsec
                 Phase-1 IKE Tunnel."
            ::= { ibIKETunnelEntry 5 }

        ibIKETunRemoteType OBJECT-TYPE
            SYNTAX IbIKEIDType
            MAX-ACCESS read-only
            STATUS current
            DESCRIPTION
                "The type of remote peer identity."
            ::= { ibIKETunnelEntry 6 }

        ibIKETunRemoteValue1 OBJECT-TYPE
            SYNTAX DisplayString(SIZE(0..255))
            MAX-ACCESS read-only
            STATUS deprecated
            DESCRIPTION
                "The value of the remote peer identity.

                If the remote peer type is ipv4Addr/ipv6Addr, this is the IP address
                used to identify the remote peer.

                If the remote peer type is ipv4AddrSubnet/ipv6AddrSubnet, this is
                the subnet address.

                If the remote peer type is ipv4AddrRange/ipv6AddrRange, this is
                the beginning IP address of the range.

                If the remote peer type is fqdn/userFqdn, this is the host name
                used to identify the remote peer.

                If the remote peer type is derAsn1Dn, this is the binary DER
                encoding of an ASN.1 X.500 Distinguished Name [X.501] of the
                principal whose certificates are being exchanged to establish
                the SA.

                If the remote peer type is derAsn1Gn, this is the binary DER
                encoding of an ASN.1 X.500 GeneralName [X.509] of the principal
                whose certificates are being exchanged to establish the SA.

                If the remote peer type is keyId, this is an opaque byte
                stream which may be used to pass vendor-specific information
                necessary to identify which pre-shared key should be used to
                authenticate Aggressive mode negotiations.

                The remote peer identity may not exceed 255 characters in length.
                The complete value will be displayed by ibIKETunRemoteValue3"
            ::= { ibIKETunnelEntry 7 }

        ibIKETunRemoteValue2 OBJECT-TYPE
            SYNTAX DisplayString(SIZE(0..255))
            MAX-ACCESS read-only
            STATUS current
            DESCRIPTION
                "The second specification of the remote peer's IP address.

                 If the remote peer type is ipv4AddrSubnet/ipv6AddrSubnet, this
                 is the subnet mask.

                 If the remote peer type is ipv4AddrRange/ipv6AddrRange, this is
                 the ending IP address of the range.

                 If the remote peer type are others, this is a zero-length string."
            ::= { ibIKETunnelEntry 8 }

        ibIKETunRemoteAddr OBJECT-TYPE
            SYNTAX IpAddress
            MAX-ACCESS read-only
            STATUS deprecated
            DESCRIPTION
                "The IP address of the remote peer for the IPsec
                Phase-1 IKE Tunnel."
            ::= { ibIKETunnelEntry 9 }

        ibIKETunInitiator OBJECT-TYPE
            SYNTAX INTEGER  {
                                local(1),
                                remote(2)
                            }
            MAX-ACCESS read-only
            STATUS current
            DESCRIPTION
                "The initiator of this tunnel."
            ::= { ibIKETunnelEntry 10 }

        ibIKETunNegoMode OBJECT-TYPE
            SYNTAX IbIKENegoMode
            MAX-ACCESS read-only
            STATUS current
            DESCRIPTION
                "The negotiation mode of the IPsec Phase-1 IKE Tunnel."
            ::= { ibIKETunnelEntry 11 }

        ibIKETunDiffHellmanGrp OBJECT-TYPE
            SYNTAX IbDiffHellmanGrp
            MAX-ACCESS read-only
            STATUS current
            DESCRIPTION
                "The Diffie Hellman Group used in the IPsec Phase-1 IKE
                 negotiations."
            ::= { ibIKETunnelEntry 12 }

        ibIKETunEncryptAlgo OBJECT-TYPE
            SYNTAX IbEncryptAlgo
            MAX-ACCESS read-only
            STATUS current
            DESCRIPTION
                "The encryption algorithm used in the IPsec Phase-1 IKE
                 negotiations."
            ::= { ibIKETunnelEntry 13 }

        ibIKETunHashAlgo OBJECT-TYPE
            SYNTAX IbAuthAlgo
            MAX-ACCESS read-only
            STATUS current
            DESCRIPTION
                "The hash algorithm used in the IPsec Phase-1 IKE
                 negotiations."
            ::= { ibIKETunnelEntry 14 }

        ibIKETunAuthMethod OBJECT-TYPE
            SYNTAX IbIKEAuthMethod
            MAX-ACCESS read-only
            STATUS current
            DESCRIPTION
                "The authentication method used in the IPsec Phase-1
                 IKE negotiations."
            ::= { ibIKETunnelEntry 15 }

        ibIKETunLifeTime OBJECT-TYPE
            SYNTAX Integer32 (1..2147483647)
            MAX-ACCESS read-only
            STATUS current
            DESCRIPTION
                "The negotiated LifeTime of the IPsec Phase-1
                 IKE Tunnel in seconds."
            ::= { ibIKETunnelEntry 16 }

        ibIKETunActiveTime OBJECT-TYPE
            SYNTAX Integer32 (1..2147483647)
            MAX-ACCESS read-only
            STATUS current
            DESCRIPTION
                "The duration the IPsec Phase-1 IKE tunnel
                 has been active in seconds."
            ::= { ibIKETunnelEntry 17 }

        ibIKETunRemainTime OBJECT-TYPE
            SYNTAX Integer32 (1..2147483647)
            MAX-ACCESS read-only
            STATUS current
            DESCRIPTION
                "The security association remaining time in
                 seconds."
            ::= { ibIKETunnelEntry 18 }

        ibIKETunTotalRefreshes OBJECT-TYPE
            SYNTAX Counter32
            MAX-ACCESS read-only
            STATUS current
            DESCRIPTION
                "The total number of security association
                 refreshing performed."
            ::= { ibIKETunnelEntry 19 }

        ibIKETunState OBJECT-TYPE
            SYNTAX IbIKETunnelState
            MAX-ACCESS read-only
            STATUS current
            DESCRIPTION
                "The State of IKE Tunnel."
            ::= { ibIKETunnelEntry 20 }

        ibIKETunDpdIntervalTime OBJECT-TYPE
            SYNTAX Integer32
            UNITS "second"
            MAX-ACCESS read-only
            STATUS current
            DESCRIPTION
                "The time that trigger DPD request.
                If ipsec message is expected to be sent out
                and the interval time between current time
                and the last time receiving peer's IPsec
                message is bigger than this time, DPD request
                would be triggered."
            DEFVAL { 10 }
            ::= { ibIKETunnelEntry 21 }

        ibIKETunDpdTimeOut OBJECT-TYPE
            SYNTAX Integer32
            UNITS "second"
            MAX-ACCESS read-only
            STATUS current
            DESCRIPTION
                "The overtime of single DPD request.
                If DPD requests are refused three times, all
                security associations related would be deleted."
            DEFVAL { 5 }
            ::= { ibIKETunnelEntry 22 }

    ibIKETunLocalInetAddrType OBJECT-TYPE
        SYNTAX InetAddressType
        MAX-ACCESS read-only
        STATUS current
        DESCRIPTION
            "The type of the local peer's IP address."
        ::= { ibIKETunnelEntry 23 }

    ibIKETunLocalInetAddr OBJECT-TYPE
        SYNTAX InetAddress
        MAX-ACCESS read-only
        STATUS current
        DESCRIPTION
            "The IP address of the local peer for the IPsec Phase-1 IKE Tunnel."
        ::= { ibIKETunnelEntry 24 }

    ibIKETunRemoteInetAddrType OBJECT-TYPE
        SYNTAX InetAddressType
        MAX-ACCESS read-only
        STATUS current
        DESCRIPTION
            "The type of the remote peer's IP address."
        ::= { ibIKETunnelEntry 25 }

    ibIKETunRemoteInetAddr OBJECT-TYPE
        SYNTAX InetAddress
        MAX-ACCESS read-only
        STATUS current
        DESCRIPTION
            "The IP address of the remote peer for the IPsec Phase-1 IKE Tunnel."
        ::= { ibIKETunnelEntry 26 }

     ibIKETunLocalValue3 OBJECT-TYPE
        SYNTAX OCTET STRING (SIZE(0..2047))
        MAX-ACCESS read-only
        STATUS current
        DESCRIPTION
            "The value of the local peer identity.

            If the local peer type is ipv4Addr/ipv6Addr, this is the IP address
            used to identify the local peer.

            If the local peer type is ipv4AddrSubnet/ipv6AddrSubnet, this is
            the subnet address.

            If the local peer type is ipv4AddrRange/ipv6AddrRange, this is
            the beginning IP address of the range.

            If the local peer type is fqdn/userFqdn, this is the host name
            used to identify the local peer.

            If the local peer type is derAsn1Dn, this is the binary DER
            encoding of an ASN.1 X.500 Distinguished Name [X.501] of the
            principal whose certificates are being exchanged to establish
            the SA.

            If the local peer type is derAsn1Gn, this is the binary DER
            encoding of an ASN.1 X.500 GeneralName [X.509] of the principal
            whose certificates are being exchanged to establish the SA.

            If the local peer type is keyId, this is an opaque byte
            stream which may be used to pass vendor-specific information
            necessary to identify which pre-shared key should be used to
            authenticate Aggressive mode negotiations."
        ::= { ibIKETunnelEntry 27 }

    ibIKETunRemoteValue3 OBJECT-TYPE
        SYNTAX OCTET STRING (SIZE(0..2047))
        MAX-ACCESS read-only
        STATUS current
        DESCRIPTION
            "The value of the remote peer identity.

            If the remote peer type is ipv4Addr/ipv6Addr, this is the IP address
            used to identify the remote peer.

            If the remote peer type is ipv4AddrSubnet/ipv6AddrSubnet, this is
            the subnet address.

            If the remote peer type is ipv4AddrRange/ipv6AddrRange, this is
            the beginning IP address of the range.

            If the remote peer type is fqdn/userFqdn, this is the host name
            used to identify the remote peer.

            If the remote peer type is derAsn1Dn, this is the binary DER
            encoding of an ASN.1 X.500 Distinguished Name [X.501] of the
            principal whose certificates are being exchanged to establish
            the SA.

            If the remote peer type is derAsn1Gn, this is the binary DER
            encoding of an ASN.1 X.500 GeneralName [X.509] of the principal
            whose certificates are being exchanged to establish the SA.

            If the remote peer type is keyId, this is an opaque byte
            stream which may be used to pass vendor-specific information
            necessary to identify which pre-shared key should be used to
            authenticate Aggressive mode negotiations."
        ::= { ibIKETunnelEntry 28 }
-- =======================================
-- begin the table of ibIKETunnelStatTable.
-- =======================================

        ibIKETunnelStatTable OBJECT-TYPE
            SYNTAX SEQUENCE OF IbIKETunnelStatEntry
            MAX-ACCESS not-accessible
            STATUS current
            DESCRIPTION
                "The IPsec Phase-1 IKE Tunnel Statistic Table."
            ::= { ibIKEObjects 2 }


        ibIKETunnelStatEntry OBJECT-TYPE
            SYNTAX IbIKETunnelStatEntry
            MAX-ACCESS not-accessible
            STATUS current
            DESCRIPTION
                "The entry contains the information of ibIKETunnelStatTable,
                 such as the number of packets sent and received by the
                 IKE tunnel, etc."
            INDEX { ibIKETunIndex }
            ::= { ibIKETunnelStatTable 1 }

        IbIKETunnelStatEntry ::=
            SEQUENCE {
                                ibIKETunInOctets
                                    Counter64,
                                ibIKETunInPkts
                                    Counter64,
                                ibIKETunInDropPkts
                                    Counter64,
                                ibIKETunInP2Exchgs
                                    Counter64,
                                ibIKETunInP2ExchgRejets
                                    Counter64,
                                ibIKETunInP2SaDelRequests
                                    Counter64,
                                ibIKETunInP1SaDelRequests
                                    Counter64,
                                ibIKETunInNotifys
                                    Counter32,
                                ibIKETunOutOctets
                                    Counter64,
                                ibIKETunOutPkts
                                    Counter64,
                                ibIKETunOutDropPkts
                                    Counter64,
                                ibIKETunOutP2Exchgs
                                    Counter64,
                                ibIKETunOutP2ExchgRejects
                                    Counter64,
                                ibIKETunOutP2SaDelRequests
                                    Counter64,
                                ibIKETunOutP1SaDelRequests
                                    Counter64,
                                ibIKETunOutNotifys
                                    Counter32
             }

        ibIKETunInOctets OBJECT-TYPE
            SYNTAX Counter64
            MAX-ACCESS read-only
            STATUS current
            DESCRIPTION
                "The total number of octets received by
                 this IPsec Phase-1 IKE Tunnel."
            ::= { ibIKETunnelStatEntry 1 }

        ibIKETunInPkts OBJECT-TYPE
            SYNTAX Counter64
            MAX-ACCESS read-only
            STATUS current
            DESCRIPTION
                "The total number of packets received by
                 this IPsec Phase-1 IKE Tunnel."
            ::= { ibIKETunnelStatEntry 2 }

        ibIKETunInDropPkts OBJECT-TYPE
            SYNTAX Counter64
            MAX-ACCESS read-only
            STATUS current
            DESCRIPTION
                "The total number of packets dropped  by this
                 IPsec Phase-1 IKE Tunnel during receiving process."
            ::= { ibIKETunnelStatEntry 3 }

        ibIKETunInP2Exchgs OBJECT-TYPE
            SYNTAX Counter64
            MAX-ACCESS read-only
            STATUS current
            DESCRIPTION
                "The total number of IPsec Phase-2 exchanges
                 received by this IPsec Phase-1 IKE Tunnel."
            ::= { ibIKETunnelStatEntry 4 }

        ibIKETunInP2ExchgRejets OBJECT-TYPE
            SYNTAX Counter64
            MAX-ACCESS read-only
            STATUS current
            DESCRIPTION
                "The total number of IPsec Phase-2 exchanges
                 received and rejected by this IPsec Phase-1 Tunnel."
            ::= { ibIKETunnelStatEntry 5 }

        ibIKETunInP2SaDelRequests OBJECT-TYPE
            SYNTAX Counter64
            MAX-ACCESS read-only
            STATUS current
            DESCRIPTION
                "The total number of IPsec Phase-2 security association
                 deleting requests received by this IPsec Phase-1 IKE Tunnel."
            ::= { ibIKETunnelStatEntry 6 }

        ibIKETunInP1SaDelRequests OBJECT-TYPE
            SYNTAX Counter64
            MAX-ACCESS read-only
            STATUS current
            DESCRIPTION
                "The total number of IPsec Phase-1
                 security association deleting requests."
            ::= { ibIKETunnelStatEntry 7 }

        ibIKETunInNotifys OBJECT-TYPE
            SYNTAX Counter32
            MAX-ACCESS read-only
            STATUS current
            DESCRIPTION
                "The total number of notifications received by this
                 IPsec Phase-1 IKE Tunnel."
            ::= { ibIKETunnelStatEntry 8 }

        ibIKETunOutOctets OBJECT-TYPE
            SYNTAX Counter64
            MAX-ACCESS read-only
            STATUS current
            DESCRIPTION
                "The total number of octets sent by this IPsec
                 Phase-1 IKE Tunnel."
            ::= { ibIKETunnelStatEntry 9 }

        ibIKETunOutPkts OBJECT-TYPE
            SYNTAX Counter64
            MAX-ACCESS read-only
            STATUS current
            DESCRIPTION
                "The total number of packets sent by this IPsec
                 Phase-1 IKE Tunnel."
            ::= { ibIKETunnelStatEntry 10 }

        ibIKETunOutDropPkts OBJECT-TYPE
            SYNTAX Counter64
            MAX-ACCESS read-only
            STATUS current
            DESCRIPTION
                "The total number of packets dropped by this
                 IPsec Phase-1 IKE Tunnel during sending process."
            ::= { ibIKETunnelStatEntry 11 }

        ibIKETunOutP2Exchgs OBJECT-TYPE
            SYNTAX Counter64
            MAX-ACCESS read-only
            STATUS current
            DESCRIPTION
                "The total number of IPsec Phase-2 exchanges sent
                 by this IPsec Phase-1 IKE Tunnel."
            ::= { ibIKETunnelStatEntry 12 }

        ibIKETunOutP2ExchgRejects OBJECT-TYPE
            SYNTAX Counter64
            MAX-ACCESS read-only
            STATUS current
            DESCRIPTION
                "The total number of IPsec Phase-2 exchanges sent
                 and rejected by this IPsec Phase-1 IKE Tunnel."
            ::= { ibIKETunnelStatEntry 13 }

        ibIKETunOutP2SaDelRequests OBJECT-TYPE
            SYNTAX Counter64
            MAX-ACCESS read-only
            STATUS current
            DESCRIPTION
                "The total number of IPsec Phase-2 security
                 association deleting requests sent by this
                 IPsec Phase-1 IKE Tunnel."
            ::= { ibIKETunnelStatEntry 14 }

        ibIKETunOutP1SaDelRequests OBJECT-TYPE
            SYNTAX Counter64
            MAX-ACCESS read-only
            STATUS current
            DESCRIPTION
                "The total number of IPsec Phase-1 security
                 association deleting requests sent by this
                 IPsec Phase-1 IKE Tunnel."
            ::= { ibIKETunnelStatEntry 15 }

        ibIKETunOutNotifys OBJECT-TYPE
            SYNTAX Counter32
            MAX-ACCESS read-only
            STATUS current
            DESCRIPTION
                "The total number of notifications sent by this IPsec
                 Phase-1 Tunnel."
            ::= { ibIKETunnelStatEntry 16 }

-- =======================================
-- Begin the ibIKEGlobalStats.
-- =======================================

        ibIKEGlobalStats OBJECT IDENTIFIER ::= { ibIKEObjects 3 }

        ibIKEGlobalActiveTunnels OBJECT-TYPE
            SYNTAX Gauge32
            MAX-ACCESS read-only
            STATUS current
            DESCRIPTION
                "The number of currently active IPsec Phase-1 IKE Tunnels."
            ::= { ibIKEGlobalStats 1 }

        ibIKEGlobalInOctets OBJECT-TYPE
            SYNTAX Counter64
            MAX-ACCESS read-only
            STATUS current
            DESCRIPTION
                "The total number of octets received by all currently and
                 previously active IPsec Phase-1 IKE Tunnels."
            ::= { ibIKEGlobalStats 2 }

        ibIKEGlobalInPkts OBJECT-TYPE
            SYNTAX Counter64
            MAX-ACCESS read-only
            STATUS current
            DESCRIPTION
                "The total number of packets received by all
                 currently and previously active IPsec Phase-1 IKE Tunnels."
            ::= { ibIKEGlobalStats 3 }

        ibIKEGlobalInDropPkts OBJECT-TYPE
            SYNTAX Counter64
            MAX-ACCESS read-only
            STATUS current
            DESCRIPTION
                "The total number of packets which were dropped during receiving
                 process by all currently and previously active IPsec Phase-1
                 IKE Tunnels."
            ::= { ibIKEGlobalStats 4 }

        ibIKEGlobalInP2Exchgs OBJECT-TYPE
            SYNTAX Counter64
            MAX-ACCESS read-only
            STATUS current
            DESCRIPTION
                "The total number of IPsec Phase-2 exchanges received by all
                 currently and previously active IPsec Phase-1 IKE Tunnels."
            ::= { ibIKEGlobalStats 5 }

        ibIKEGlobalInP2ExchgRejects OBJECT-TYPE
            SYNTAX Counter64
            MAX-ACCESS read-only
            STATUS current
            DESCRIPTION
                "The total number of IPsec Phase-2 exchanges which were
                 received and rejected by all currently and previously
                 active IPsec Phase-1 IKE Tunnels."
            ::= { ibIKEGlobalStats 6 }

        ibIKEGlobalInP2SaDelRequests OBJECT-TYPE
            SYNTAX Counter64
            MAX-ACCESS read-only
            STATUS current
            DESCRIPTION
                "The total number of IPsec Phase-2 security association
                 deleting requests received by all currently and previously
                 active IPsec Phase-1 IKE Tunnels."
            ::= { ibIKEGlobalStats 7 }

        ibIKEGlobalInNotifys OBJECT-TYPE
            SYNTAX Counter32
            MAX-ACCESS read-only
            STATUS current
            DESCRIPTION
                "The total number of notifications received by all IPsec
                 Phase-1 IKE Tunnels."
            ::= { ibIKEGlobalStats 8 }

        ibIKEGlobalOutOctets OBJECT-TYPE
            SYNTAX Counter64
            MAX-ACCESS read-only
            STATUS current
            DESCRIPTION
                "The total number of octets sent by all currently
                 and previously active and IPsec Phase-1 IKE Tunnels. "
            ::= { ibIKEGlobalStats 9 }

        ibIKEGlobalOutPkts OBJECT-TYPE
            SYNTAX Counter64
            MAX-ACCESS read-only
            STATUS current
            DESCRIPTION
                "The total number of packets sent by all currently
                 and previously active and IPsec Phase-1 Tunnels."
            ::= { ibIKEGlobalStats 10 }

        ibIKEGlobalOutDropPkts OBJECT-TYPE
            SYNTAX Counter64
            MAX-ACCESS read-only
            STATUS current
            DESCRIPTION
                "The total number of packets which were dropped during
                 sending process by all currently and previously active
                 IPsec Phase-1 IKE Tunnels."
            ::= { ibIKEGlobalStats 11 }

        ibIKEGlobalOutP2Exchgs OBJECT-TYPE
            SYNTAX Counter64
            MAX-ACCESS read-only
            STATUS current
            DESCRIPTION
                "The total number of IPsec Phase-2 exchanges which were
                 sent by all currently and previously active IPsec
                 Phase-1 IKE Tunnels."
            ::= { ibIKEGlobalStats 12 }

        ibIKEGlobalOutP2ExchgRejects OBJECT-TYPE
            SYNTAX Counter64
            MAX-ACCESS read-only
            STATUS current
            DESCRIPTION
                "The total number of IPsec Phase-2 exchanges which
                 were sent and rejected by all currently and previously
                 active IPsec Phase-1 IKE Tunnels."
            ::= { ibIKEGlobalStats 13 }

        ibIKEGlobalOutP2SaDelRequests OBJECT-TYPE
            SYNTAX Counter64
            MAX-ACCESS read-only
            STATUS current
            DESCRIPTION
                "The total number of IPsec Phase-2 SA deleting requests sent
                 by all currently and previously active IPsec Phase-1 IKE Tunnels."
            ::= { ibIKEGlobalStats 14 }

        ibIKEGlobalOutNotifys OBJECT-TYPE
            SYNTAX Counter32
            MAX-ACCESS read-only
            STATUS current
            DESCRIPTION
                "The total number of notifications sent by all active IPsec
                 Phase-1 IKE Tunnels."
            ::= { ibIKEGlobalStats 15 }

        ibIKEGlobalInitTunnels OBJECT-TYPE
            SYNTAX Counter32
            MAX-ACCESS read-only
            STATUS current
            DESCRIPTION
                "The total number of IPsec Phase-1 IKE Tunnels which
                 were locally initiated."
            ::= { ibIKEGlobalStats 16 }

        ibIKEGlobalInitTunnelFails OBJECT-TYPE
            SYNTAX Counter32
            MAX-ACCESS read-only
            STATUS current
            DESCRIPTION
                "The total number of IPsec Phase-1 IKE Tunnels which
                 were locally initiated and failed to activate."
            ::= { ibIKEGlobalStats 17 }

        ibIKEGlobalRespTunnels OBJECT-TYPE
            SYNTAX Counter32
            MAX-ACCESS read-only
            STATUS current
            DESCRIPTION
                "The total number of IPsec Phase-1 IKE Tunnels which
                 were remotely initiated."
            ::= { ibIKEGlobalStats 18 }

        ibIKEGlobalRespTunnelFails OBJECT-TYPE
            SYNTAX Counter32
            MAX-ACCESS read-only
            STATUS current
            DESCRIPTION
                "The total number of IPsec Phase-1 IKE Tunnels which
                 were remotely initiated and failed to activate."
            ::= { ibIKEGlobalStats 19 }

        ibIKEGlobalAuthFails OBJECT-TYPE
            SYNTAX Counter32
            MAX-ACCESS read-only
            STATUS current
            DESCRIPTION
                "The total number of authentications which ended in
                 failure by all current and previous IPsec Phase-1 IKE Tunnels."
            ::= { ibIKEGlobalStats 20 }

        ibIKEGlobalNoSaFails OBJECT-TYPE
            SYNTAX Counter32
            MAX-ACCESS read-only
            STATUS current
            DESCRIPTION
                "The total number of non-existent Security Association
                 in failures which occurred during processing of all
                 current and previous IPsec Phase-1 IKE Tunnels."
            ::= { ibIKEGlobalStats 21 }

        ibIKEGlobalInvalidCookieFails OBJECT-TYPE
            SYNTAX Counter32
            MAX-ACCESS read-only
            STATUS current
            DESCRIPTION
                "The total number of invalid cookie in failures which
                 occurred during processing of all current and previous
                 IPsec Phase-1 IKE Tunnels."
            ::= { ibIKEGlobalStats 22 }

        ibIKEGlobalAttrNotSuppFails OBJECT-TYPE
            SYNTAX Counter32
            MAX-ACCESS read-only
            STATUS current
            DESCRIPTION
                "The total number of attributes not supported in failures
                 which occurred during processing of all current and previous
                 IPsec Phase-1 IKE Tunnels."
            ::= { ibIKEGlobalStats 23 }

        ibIKEGlobalNoProposalChosenFails OBJECT-TYPE
            SYNTAX Counter32
            MAX-ACCESS read-only
            STATUS current
            DESCRIPTION
                "The total number of no proposal chosen in failures which
                 occurred during processing of all current and previous
                 IPsec Phase-1 IKE Tunnels."
            ::= { ibIKEGlobalStats 24 }

        ibIKEGlobalUnsportExchTypeFails OBJECT-TYPE
            SYNTAX Counter32
            MAX-ACCESS read-only
            STATUS current
            DESCRIPTION
                "The total number of unsupported exchange type in failures
                 which occurred during processing of all current and
                 previous IPsec Phase-1 IKE Tunnels."
            ::= { ibIKEGlobalStats 25 }

        ibIKEGlobalInvalidIdFails OBJECT-TYPE
            SYNTAX Counter32
            MAX-ACCESS read-only
            STATUS current
            DESCRIPTION
                "The total number of invalid id Information in failures
                 which occurred during processing of all current and
                 previous IPsec Phase-1 IKE Tunnels."
            ::= { ibIKEGlobalStats 26 }

            ibIKEGlobalInvalidProFails OBJECT-TYPE
            SYNTAX Counter32
            MAX-ACCESS read-only
            STATUS current
            DESCRIPTION
                "The total number of invalid protocol id in failures which
                 occurred during processing of all current and previous
                 IPsec Phase-1 IKE Tunnels."
            ::= { ibIKEGlobalStats 27 }

            ibIKEGlobalCertTypeUnsuppFails OBJECT-TYPE
            SYNTAX Counter32
            MAX-ACCESS read-only
            STATUS current
            DESCRIPTION
                "The total number of certificate type unsupported in failures
                 which occurred during processing of all current and
                 previous IPsec Phase-1 IKE Tunnels."
            ::= { ibIKEGlobalStats 28 }

        ibIKEGlobalInvalidCertAuthFails OBJECT-TYPE
            SYNTAX Counter32
            MAX-ACCESS read-only
            STATUS current
            DESCRIPTION
                   "The total number of failures because of invalid certificate authority
                 which occurred during processing of all current and
                 previous IPsec Phase-1 IKE Tunnels."
            ::= { ibIKEGlobalStats 29 }

        ibIKEGlobalInvalidSignFails OBJECT-TYPE
            SYNTAX Counter32
            MAX-ACCESS read-only
            STATUS current
            DESCRIPTION
                "The total number of failures because of the invalid signature which
                 occurred during processing of all current and previous
                 IPsec Phase-1 IKE Tunnels."
            ::= { ibIKEGlobalStats 30 }

        ibIKEGlobalCertUnavailableFails OBJECT-TYPE
            SYNTAX Counter32
            MAX-ACCESS read-only
            STATUS current
            DESCRIPTION
                "The total number of certificate unavailable in failures
                 which occurred during processing of all current and
                 previous IPsec Phase-1 IKE Tunnels."
            ::= { ibIKEGlobalStats 31 }

-- =======================================
-- Begin the ibIKETrapObject.
-- =======================================

        ibIKETrapObject OBJECT IDENTIFIER ::= { ibIKEObjects 4 }

        ibIKEProposalNumber OBJECT-TYPE
            SYNTAX Integer32
            MAX-ACCESS accessible-for-notify
            STATUS current
            DESCRIPTION
                "The IKE proposal's number with a trap."
            ::= { ibIKETrapObject 1 }

        ibIKEProposalSize OBJECT-TYPE
            SYNTAX Integer32
            MAX-ACCESS accessible-for-notify
            STATUS current
            DESCRIPTION
                "The number of IKE proposals with a trap."
            ::= { ibIKETrapObject 2 }

        ibIKEIdInformation OBJECT-TYPE
            SYNTAX DisplayString(SIZE(0..255))
            MAX-ACCESS accessible-for-notify
            STATUS current
            DESCRIPTION
                "The id information with a trap."
            ::= { ibIKETrapObject 3 }

        ibIKEProtocolNum OBJECT-TYPE
            SYNTAX Integer32
            MAX-ACCESS accessible-for-notify
            STATUS current
            DESCRIPTION
                "The protocol number with a trap"
            ::= { ibIKETrapObject 4 }

        ibIKECertInformation OBJECT-TYPE
            SYNTAX DisplayString(SIZE(0..255))
            MAX-ACCESS accessible-for-notify
            STATUS current
            DESCRIPTION
                "The certificate information with a trap."
            ::= { ibIKETrapObject 5 }


-- =======================================
-- Begin the ibIKETrapCntl.
-- =======================================

        ibIKETrapCntl OBJECT IDENTIFIER ::= { ibIKEObjects 5 }

        ibIKETrapGlobalCntl OBJECT-TYPE
            SYNTAX IbTrapStatus
            MAX-ACCESS read-write
            STATUS current
            DESCRIPTION
                "Indicates whether all IKE traps should be generated."
            ::= { ibIKETrapCntl 1 }


        ibIKETunnelStartTrapCntl OBJECT-TYPE
            SYNTAX IbTrapStatus
            MAX-ACCESS read-write
            STATUS current
            DESCRIPTION
                "Indicates whether ibIKETunnelStart traps should be generated."
            ::= { ibIKETrapCntl 2 }

        ibIKETunnelStopTrapCntl OBJECT-TYPE
            SYNTAX IbTrapStatus
            MAX-ACCESS read-write
            STATUS current
            DESCRIPTION
                        "Indicates whether ibIKETunnelStop traps should be generated."
            ::= { ibIKETrapCntl 3 }

        ibIKENoSaTrapCntl OBJECT-TYPE
            SYNTAX IbTrapStatus
            MAX-ACCESS read-write
            STATUS current
            DESCRIPTION
                "Indicates whether ibIKENoSaFailure traps should be generated."
            ::= { ibIKETrapCntl 4 }

        ibIKEEncryFailureTrapCntl OBJECT-TYPE
            SYNTAX IbTrapStatus
            MAX-ACCESS read-write
            STATUS current
            DESCRIPTION
                "Indicates whether ibIKEEncryFailFailure traps should be generated."
            ::= { ibIKETrapCntl 5 }

        ibIKEDecryFailureTrapCntl OBJECT-TYPE
            SYNTAX IbTrapStatus
            MAX-ACCESS read-write
            STATUS current
            DESCRIPTION
                "Indicates whether ibIKEDecryFailFailure traps should be generated."
            ::= { ibIKETrapCntl 6 }

        ibIKEInvalidProposalTrapCntl OBJECT-TYPE
            SYNTAX IbTrapStatus
            MAX-ACCESS read-write
            STATUS current
            DESCRIPTION
                "Indicates whether ibIKEInvalidProposalFailure traps should be generated."
            ::= { ibIKETrapCntl 7 }

        ibIKEAuthFailTrapCntl OBJECT-TYPE
            SYNTAX IbTrapStatus
            MAX-ACCESS read-write
            STATUS current
            DESCRIPTION
                "Indicates whether ibIKEAuthFailFailure traps should be generated."
            ::= { ibIKETrapCntl 8 }

        ibIKEInvalidCookieTrapCntl OBJECT-TYPE
            SYNTAX IbTrapStatus
            MAX-ACCESS read-write
            STATUS current
            DESCRIPTION
                "Indicates whether ibIKEInvalidCookieFailure traps should be generated."
            ::= { ibIKETrapCntl 9 }

        ibIKEInvalidSpiTrapCntl OBJECT-TYPE
            SYNTAX IbTrapStatus
            MAX-ACCESS read-write
            STATUS current
            DESCRIPTION
                "Indicates whether ibIKEInvalidSpiFailure traps should be generated."
            ::= { ibIKETrapCntl 10 }

        ibIKEAttrNotSuppTrapCntl OBJECT-TYPE
            SYNTAX IbTrapStatus
            MAX-ACCESS read-write
            STATUS current
            DESCRIPTION
                "Indicates whether ibIKEAttrNotSuppFailure traps should be generated."
            ::= { ibIKETrapCntl 11 }

        ibIKEUnsportExchTypeTrapCntl OBJECT-TYPE
            SYNTAX IbTrapStatus
            MAX-ACCESS read-write
            STATUS current
            DESCRIPTION
                "Indicates whether ibIKEUnsportExchTypeFailure traps should be generated."
            ::= { ibIKETrapCntl 12 }

        ibIKEInvalidIdTrapCntl OBJECT-TYPE
            SYNTAX IbTrapStatus
            MAX-ACCESS read-write
            STATUS current
            DESCRIPTION
                "Indicates whether ibIKEInvalidIdFailure traps should be generated."
            ::= { ibIKETrapCntl 13 }

        ibIKEInvalidProtocolTrapCntl OBJECT-TYPE
            SYNTAX IbTrapStatus
            MAX-ACCESS read-write
            STATUS current
            DESCRIPTION
                "Indicates whether ibIKEInvalidProtocolFailure traps should be generated."
            ::= { ibIKETrapCntl 14 }

        ibIKECertTypeUnsuppTrapCntl OBJECT-TYPE
            SYNTAX IbTrapStatus
            MAX-ACCESS read-write
            STATUS current
            DESCRIPTION
                "Indicates whether ibIKECertTypeUnsuppFailure traps should be generated."
            ::= { ibIKETrapCntl 15 }

        ibIKEInvalidCertAuthTrapCntl OBJECT-TYPE
            SYNTAX IbTrapStatus
            MAX-ACCESS read-write
            STATUS current
            DESCRIPTION
                "Indicates whether ibIKEInvalidCertAuthFailure traps should be generated."
            ::= { ibIKETrapCntl 16 }

        ibIKEInvalidSignTrapCntl OBJECT-TYPE
            SYNTAX IbTrapStatus
            MAX-ACCESS read-write
            STATUS current
            DESCRIPTION
                "Indicates whether ibIKEInvalidSignFailure traps should be generated."
            ::= { ibIKETrapCntl 17 }

        ibIKECertUnavailableTrapCntl OBJECT-TYPE
            SYNTAX IbTrapStatus
            MAX-ACCESS read-write
            STATUS current
            DESCRIPTION
                "Indicates whether ibIKECertUnavailableFailure traps should be generated."
            ::= { ibIKETrapCntl 18 }

        ibIKEProposalAddTrapCntl OBJECT-TYPE
            SYNTAX IbTrapStatus
            MAX-ACCESS read-write
            STATUS current
            DESCRIPTION
                "Indicates whether ibIKEProposalAdd traps should be generated."
            ::= { ibIKETrapCntl 19 }

        ibIKEProposalDelTrapCntl OBJECT-TYPE
            SYNTAX IbTrapStatus
            MAX-ACCESS read-write
            STATUS current
            DESCRIPTION
                "Indicates whether ibIKEProposalDel traps should be generated."
            ::= { ibIKETrapCntl 20 }

-- ================================================
-- definition of traps.
-- ================================================

        ibIKETrap OBJECT IDENTIFIER ::= { ibIKEObjects 6 }
        ibIKENotifications OBJECT IDENTIFIER ::= { ibIKETrap 1 }

        ibIKETunnelStart NOTIFICATION-TYPE
            OBJECTS {
                        ibIKETunLocalAddr,
                        ibIKETunRemoteAddr,
                        ibIKETunLifeTime,
                        ibIKETunIndex,
                        ibIKETunLocalInetAddrType,
                        ibIKETunLocalInetAddr,
                        ibIKETunRemoteInetAddrType,
                        ibIKETunRemoteInetAddr
                    }
            STATUS     current
            DESCRIPTION
                 "This notification is generated when an IPsec Phase-1
                  IKE Tunnel is created."
                    ::= { ibIKENotifications 1 }

        ibIKETunnelStop NOTIFICATION-TYPE
            OBJECTS {
                        ibIKETunLocalAddr,
                        ibIKETunRemoteAddr,
                        ibIKETunActiveTime,
                        ibIKETunIndex,
                        ibIKETunLocalInetAddrType,
                        ibIKETunLocalInetAddr,
                        ibIKETunRemoteInetAddrType,
                        ibIKETunRemoteInetAddr
                    }
            STATUS     current
            DESCRIPTION
                "This notification is generated when an IPsec Phase-1
                IKE Tunnel is deleted."
                    ::= { ibIKENotifications 2 }

        ibIKENoSaFailure NOTIFICATION-TYPE
            OBJECTS {
                        ibIKETunLocalAddr,
                        ibIKETunRemoteAddr,
                        ibIKETunIndex,
                        ibIKETunLocalInetAddrType,
                        ibIKETunLocalInetAddr,
                        ibIKETunRemoteInetAddrType,
                        ibIKETunRemoteInetAddr
                    }
            STATUS     current
            DESCRIPTION
                "This notification is generated when the IKE tunnel
                 has a non-existent SA error."
        ::= { ibIKENotifications 3 }

        ibIKEEncryFailFailure NOTIFICATION-TYPE
            OBJECTS {
                        ibIKETunLocalAddr,
                        ibIKETunRemoteAddr,
                        ibIKETunIndex,
                        ibIKETunLocalInetAddrType,
                        ibIKETunLocalInetAddr,
                        ibIKETunRemoteInetAddrType,
                        ibIKETunRemoteInetAddr
                    }
            STATUS     current
            DESCRIPTION
                "This notification is generated when the IKE tunnel
                 has an encrypting failure."
                    ::= { ibIKENotifications 4 }

        ibIKEDecryFailFailure NOTIFICATION-TYPE
            OBJECTS {
                        ibIKETunLocalAddr,
                        ibIKETunRemoteAddr,
                        ibIKETunIndex,
                        ibIKETunLocalInetAddrType,
                        ibIKETunLocalInetAddr,
                        ibIKETunRemoteInetAddrType,
                        ibIKETunRemoteInetAddr
                    }
            STATUS     current
                    DESCRIPTION
                "This notification is generated when the IKE tunnel
                has a decrypting failure."
                    ::= { ibIKENotifications 5 }

        ibIKEInvalidProposalFailure NOTIFICATION-TYPE
            OBJECTS {
                        ibIKETunLocalAddr,
                        ibIKETunRemoteAddr,
                        ibIKETunIndex,
                        ibIKETunLocalInetAddrType,
                        ibIKETunLocalInetAddr,
                        ibIKETunRemoteInetAddrType,
                        ibIKETunRemoteInetAddr
                    }
            STATUS     current
            DESCRIPTION
                "This notification is generated when the IPsec phase-1
                invalid proposal occurs."
                    ::= { ibIKENotifications 6 }

        ibIKEAuthFailFailure NOTIFICATION-TYPE
            OBJECTS {
                        ibIKETunLocalAddr,
                        ibIKETunRemoteAddr,
                        ibIKETunIndex,
                        ibIKETunLocalInetAddrType,
                        ibIKETunLocalInetAddr,
                        ibIKETunRemoteInetAddrType,
                        ibIKETunRemoteInetAddr
                    }
            STATUS     current
            DESCRIPTION
                "This notification is generated when the IPsec phase-1
                authentication failure occurs."
            ::= { ibIKENotifications 7 }

        ibIKEInvalidCookieFailure NOTIFICATION-TYPE
            OBJECTS {
                        ibIKETunLocalAddr,
                        ibIKETunRemoteAddr,
                        ibIKETunIndex,
                        ibIKETunLocalInetAddrType,
                        ibIKETunLocalInetAddr,
                        ibIKETunRemoteInetAddrType,
                        ibIKETunRemoteInetAddr
                    }
            STATUS     current
            DESCRIPTION
                "This notification is generated when the IPsec phase-1
                invalid cookie failure occurs."
            ::= { ibIKENotifications 8 }

        ibIKEAttrNotSuppFailure NOTIFICATION-TYPE
            OBJECTS {
                        ibIKETunLocalAddr,
                        ibIKETunRemoteAddr,
                        ibIKETunIndex,
                        ibIKETunLocalInetAddrType,
                        ibIKETunLocalInetAddr,
                        ibIKETunRemoteInetAddrType,
                        ibIKETunRemoteInetAddr
                    }
            STATUS     current
            DESCRIPTION
                "This notification is generated when the IPsec phase-1 unsupported
                attribute failure occurs."
            ::= { ibIKENotifications 9 }

        ibIKEUnsportExchTypeFailure NOTIFICATION-TYPE
            OBJECTS {
                        ibIKETunLocalAddr,
                        ibIKETunRemoteAddr,
                        ibIKETunIndex,
                        ibIKETunLocalInetAddrType,
                        ibIKETunLocalInetAddr,
                        ibIKETunRemoteInetAddrType,
                        ibIKETunRemoteInetAddr
                    }
            STATUS     current
            DESCRIPTION
                "This notification is generated when the IPsec phase-1
                unsupported exchange type failure occurs."
            ::= { ibIKENotifications 10 }

        ibIKEInvalidIdFailure NOTIFICATION-TYPE
            OBJECTS {
                        ibIKETunLocalAddr,
                        ibIKETunRemoteAddr,
                        ibIKEIdInformation,
                        ibIKETunIndex,
                        ibIKETunLocalInetAddrType,
                        ibIKETunLocalInetAddr,
                        ibIKETunRemoteInetAddrType,
                        ibIKETunRemoteInetAddr
                    }
            STATUS     current
            DESCRIPTION
                "This notification is generated when the IPsec phase-1
                invalid id failure occurs."
            ::= { ibIKENotifications 11 }

        ibIKEInvalidProtocolFailure NOTIFICATION-TYPE
            OBJECTS {
                        ibIKETunLocalAddr,
                        ibIKETunRemoteAddr,
                        ibIKEProtocolNum,
                        ibIKETunIndex,
                        ibIKETunLocalInetAddrType,
                        ibIKETunLocalInetAddr,
                        ibIKETunRemoteInetAddrType,
                        ibIKETunRemoteInetAddr
                        }
            STATUS     current
            DESCRIPTION
                "This notification is generated when the processing for
                an IPsec Phase-1 IKE Tunnel has a protocol related errors."
            ::= { ibIKENotifications 12 }

        ibIKECertTypeUnsuppFailure NOTIFICATION-TYPE
            OBJECTS {
                        ibIKETunLocalAddr,
                        ibIKETunRemoteAddr,
                        ibIKECertInformation,
                        ibIKETunIndex,
                        ibIKETunLocalInetAddrType,
                        ibIKETunLocalInetAddr,
                        ibIKETunRemoteInetAddrType,
                        ibIKETunRemoteInetAddr
                    }
            STATUS     current
            DESCRIPTION
                "This notification is generated when the IPsec phase-1
                unsupported certificate type failure occurs."
            ::= { ibIKENotifications 13 }

        ibIKEInvalidCertAuthFailure NOTIFICATION-TYPE
            OBJECTS {
                        ibIKETunLocalAddr,
                        ibIKETunRemoteAddr,
                        ibIKECertInformation,
                        ibIKETunIndex,
                        ibIKETunLocalInetAddrType,
                        ibIKETunLocalInetAddr,
                        ibIKETunRemoteInetAddrType,
                        ibIKETunRemoteInetAddr
                    }
            STATUS     current
            DESCRIPTION
                "This notification is generated when the IPsec phase-1
                invalid certificate authorization failure occurs."
            ::= { ibIKENotifications 14 }

        ibIKElInvalidSignFailure NOTIFICATION-TYPE
            OBJECTS {
                        ibIKETunLocalAddr,
                        ibIKETunRemoteAddr,
                        ibIKECertInformation,
                        ibIKETunIndex,
                        ibIKETunLocalInetAddrType,
                        ibIKETunLocalInetAddr,
                        ibIKETunRemoteInetAddrType,
                        ibIKETunRemoteInetAddr
                    }
            STATUS     current
            DESCRIPTION
                "This notification is generated when the IPsec phase-1
                invalid signature failure occurs."
            ::= { ibIKENotifications 15 }

        ibIKECertUnavailableFailure NOTIFICATION-TYPE
            OBJECTS {
                        ibIKETunLocalAddr,
                        ibIKETunRemoteAddr,
                        ibIKECertInformation,
                        ibIKETunIndex,
                        ibIKETunLocalInetAddrType,
                        ibIKETunLocalInetAddr,
                        ibIKETunRemoteInetAddrType,
                        ibIKETunRemoteInetAddr
                    }
            STATUS     current
            DESCRIPTION
                "This notification is generated when the IPsec phase-1
                certificate unavailable failure occurs."
            ::= { ibIKENotifications 16 }

        ibIKEProposalAdd NOTIFICATION-TYPE
                    OBJECTS { ibIKEProposalNumber,
                              ibIKEProposalSize
                            }
                    STATUS     current
                    DESCRIPTION
                "This notification is generated when an IKE proposal is added."
                    ::= { ibIKENotifications 17 }

        ibIKEProposalDel NOTIFICATION-TYPE
                    OBJECTS { ibIKEProposalNumber,
                              ibIKEProposalSize
                            }
                    STATUS     current
                    DESCRIPTION
                "This notification is generated when an IKE proposal is deleted."
                    ::= { ibIKENotifications 18 }

-- =======================================
-- Begin the ibIKEScalarObjects.
-- =======================================
    ibIKEScalarObjects OBJECT IDENTIFIER ::= { ibIKEObjects 7 }

    ibIKEMIBVersion OBJECT-TYPE
        SYNTAX DisplayString(SIZE(0..255))
        MAX-ACCESS read-only
        STATUS current
        DESCRIPTION
            "Version string of this MIB."
        ::= { ibIKEScalarObjects 1 }

-- =======================================
-- Conformance Information
-- =======================================
        ibIKEConformance   OBJECT IDENTIFIER
                                 ::= { ibIKEMonitor 2 }
        ibIKECompliances   OBJECT IDENTIFIER
                                 ::= { ibIKEConformance 1 }
        ibIKEGroups        OBJECT IDENTIFIER
                                 ::= { ibIKEConformance 2 }

-- =======================================
-- Compliance Statements
-- =======================================
        ibIKECompliance MODULE-COMPLIANCE
            STATUS current
            DESCRIPTION
                " "
            MODULE -- this module
            MANDATORY-GROUPS
                {
                    ibIKETunnelTableGroup,
                    ibIKETunnelStatTableGroup,
                    ibIKEGlobalStatsGroup,
                    ibIKETrapObjectGroup,
                    ibIKETrapCntlGroup,
                    ibIKETrapGroup,
                    ibIKEScalarObjectsGroup
                }
            ::= { ibIKECompliances 1 }

    ibIKETunnelTableGroup OBJECT-GROUP
        OBJECTS {
            ibIKETunLocalType,
            ibIKETunLocalValue1,
            ibIKETunLocalValue2,
            ibIKETunLocalAddr,
            ibIKETunRemoteType,
            ibIKETunRemoteValue1,
            ibIKETunRemoteValue2,
            ibIKETunRemoteAddr,
            ibIKETunInitiator,
            ibIKETunNegoMode,
            ibIKETunDiffHellmanGrp,
            ibIKETunEncryptAlgo,
            ibIKETunHashAlgo,
            ibIKETunAuthMethod,
            ibIKETunLifeTime,
            ibIKETunActiveTime,
            ibIKETunRemainTime,
            ibIKETunTotalRefreshes,
            ibIKETunState,
            ibIKETunDpdIntervalTime,
            ibIKETunDpdTimeOut,
            ibIKETunLocalInetAddrType,
            ibIKETunLocalInetAddr,
            ibIKETunRemoteInetAddrType,
            ibIKETunRemoteInetAddr,
            ibIKETunLocalValue3,
            ibIKETunRemoteValue3
        }
        STATUS current
        DESCRIPTION
            "The group contains the IKE tunnel's property information."
        ::= { ibIKEGroups 1 }


        ibIKETunnelStatTableGroup OBJECT-GROUP
            OBJECTS {
                                ibIKETunInOctets ,
                                ibIKETunInPkts,
                                ibIKETunInDropPkts,
                                ibIKETunInP2Exchgs,
                                ibIKETunInP2ExchgRejets,
                                ibIKETunInP2SaDelRequests,
                                ibIKETunInP1SaDelRequests,
                                ibIKETunInNotifys,
                                ibIKETunOutOctets,
                                ibIKETunOutPkts,
                                ibIKETunOutDropPkts,
                                ibIKETunOutP2Exchgs,
                                ibIKETunOutP2ExchgRejects,
                                ibIKETunOutP2SaDelRequests,
                                ibIKETunOutP1SaDelRequests,
                                ibIKETunOutNotifys
                                }
            STATUS current
            DESCRIPTION
                "The group contains the IKE tunnel's statistic information."
            ::= { ibIKEGroups 2 }

        ibIKEGlobalStatsGroup OBJECT-GROUP
            OBJECTS {
                                ibIKEGlobalActiveTunnels,
                                ibIKEGlobalInOctets,
                                ibIKEGlobalInPkts,
                                ibIKEGlobalInDropPkts,
                                ibIKEGlobalInP2Exchgs,
                                ibIKEGlobalInP2ExchgRejects,
                                ibIKEGlobalInP2SaDelRequests,
                                ibIKEGlobalInNotifys,
                                ibIKEGlobalOutOctets,
                                ibIKEGlobalOutPkts,
                                ibIKEGlobalOutDropPkts,
                                ibIKEGlobalOutP2Exchgs,
                                ibIKEGlobalOutP2ExchgRejects,
                                ibIKEGlobalOutP2SaDelRequests,
                                ibIKEGlobalOutNotifys,
                                ibIKEGlobalInitTunnels,
                                ibIKEGlobalInitTunnelFails,
                                ibIKEGlobalRespTunnels,
                                ibIKEGlobalRespTunnelFails,
                                ibIKEGlobalAuthFails,
                                ibIKEGlobalNoSaFails,
                                ibIKEGlobalInvalidCookieFails,
                                ibIKEGlobalAttrNotSuppFails,
                                ibIKEGlobalNoProposalChosenFails,
                                ibIKEGlobalUnsportExchTypeFails,
                                ibIKEGlobalInvalidIdFails,
                                ibIKEGlobalInvalidProFails,
                                ibIKEGlobalCertTypeUnsuppFails,
                                ibIKEGlobalInvalidCertAuthFails,
                                ibIKEGlobalInvalidSignFails,
                                ibIKEGlobalCertUnavailableFails
                                }
            STATUS current
            DESCRIPTION
                "The group contains all of the IKE tunnel's statistic information."
            ::= { ibIKEGroups 3 }

        ibIKETrapObjectGroup OBJECT-GROUP
            OBJECTS {
                                ibIKEProposalNumber,
                                ibIKEProposalSize,
                                ibIKEIdInformation,
                                ibIKEProtocolNum,
                                ibIKECertInformation
                    }
            STATUS current
            DESCRIPTION
                "The group contains all of trap objects of IKE tunnels."
            ::= { ibIKEGroups 4 }

        ibIKETrapCntlGroup OBJECT-GROUP
            OBJECTS {
                                ibIKETrapGlobalCntl,
                                ibIKETunnelStartTrapCntl,
                                ibIKETunnelStopTrapCntl,
                                ibIKENoSaTrapCntl,
                                ibIKEEncryFailureTrapCntl,
                                ibIKEDecryFailureTrapCntl,
                                ibIKEInvalidProposalTrapCntl,
                                ibIKEAuthFailTrapCntl,
                                ibIKEInvalidCookieTrapCntl,
                                ibIKEInvalidSpiTrapCntl,
                                ibIKEAttrNotSuppTrapCntl,
                                ibIKEUnsportExchTypeTrapCntl,
                                ibIKEInvalidIdTrapCntl,
                                ibIKEInvalidProtocolTrapCntl,
                                ibIKECertTypeUnsuppTrapCntl,
                                ibIKEInvalidCertAuthTrapCntl,
                                ibIKEInvalidSignTrapCntl,
                                ibIKECertUnavailableTrapCntl,
                                ibIKEProposalAddTrapCntl,
                                ibIKEProposalDelTrapCntl
                                }
            STATUS current
            DESCRIPTION
                "The group contains all of trap switches of IKE tunnels."
            ::= { ibIKEGroups 5 }

        ibIKETrapGroup  NOTIFICATION-GROUP
            NOTIFICATIONS {
                                ibIKETunnelStart,
                                ibIKETunnelStop,
                                ibIKENoSaFailure,
                                ibIKEEncryFailFailure,
                                ibIKEDecryFailFailure,
                                ibIKEInvalidProposalFailure,
                                ibIKEAuthFailFailure,
                                ibIKEInvalidCookieFailure,
                                ibIKEAttrNotSuppFailure,
                                ibIKEUnsportExchTypeFailure,
                                ibIKEInvalidIdFailure,
                                ibIKEInvalidProtocolFailure,
                                ibIKECertTypeUnsuppFailure,
                                ibIKEInvalidCertAuthFailure,
                                ibIKElInvalidSignFailure,
                                ibIKECertUnavailableFailure,
                                ibIKEProposalAdd,
                                ibIKEProposalDel
                           }
            STATUS current
            DESCRIPTION
                "The group contains all of trap of IKE tunnels."
            ::= { ibIKEGroups 6 }

        ibIKEScalarObjectsGroup OBJECT-GROUP
            OBJECTS {
                        ibIKEMIBVersion
                    }
            STATUS current
            DESCRIPTION
                "The group contains all of scalar objects of the MIB."
            ::= { ibIKEGroups 7 }

    END
