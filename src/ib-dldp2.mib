-- =====================================================================
-- Copyright (C) 2023 Intelbras S.A. All rights reserved.
--
-- Description: Device Link Detection Protocol (DLDP) MIB.
-- Reference:
-- Version: V1.1
-- History:
-- V1.0 2011-12-26 created by Gu Ce
-- V1.1 2016-03-18 updated by LiYuGang
--      Modify ibDldp2UniShutdown
-- =====================================================================
IB-DLDP2-MIB DEFINITIONS ::= BEGIN
IMPORTS
    TruthValue, MacAddress
        FROM SNMPv2-TC
    MODULE-IDENTITY, OBJECT-TYPE, Integer32, NOTIFICATION-TYPE
        FROM SNMPv2-SMI
    ifIndex, ifDescr
        FROM IF-MIB
    ibCommon
        FROM IB-OID-MIB;

ibDldp2 MODULE-IDENTITY
    LAST-UPDATED
        "201603181530Z"
    ORGANIZATION
        "Intelbras S.A. Industria de Telecomunicacao Eletronica Brasileria."
    CONTACT-INFO
        ""
    DESCRIPTION
        "Device Link Detection Protocol (DLDP) MIB.
        Device Link Detection Protocol is a private Layer 2 protocol,
        which can be used to detect and shut down unidirectional links (fiber or
        copper links) to avoid network problems."
    REVISION
        "201603181530Z"
    DESCRIPTION
        "Modify ibDldp2UniShutdown."
    REVISION
        "201112261530Z"
    DESCRIPTION
        "Initial version of this MIB module."
    ::= { ibCommon 117 }

ibDldp2ScalarGroup        OBJECT IDENTIFIER ::= { ibDldp2 1 }

ibDldp2GlobalEnable OBJECT-TYPE
    SYNTAX      TruthValue
    MAX-ACCESS  read-write
    STATUS      current
    DESCRIPTION
        "Enable(true) or disable(false) DLDP on the device."
    ::= { ibDldp2ScalarGroup 1 }

ibDldp2Interval OBJECT-TYPE
    SYNTAX      Integer32(1..100)
    UNITS       "second"
    MAX-ACCESS  read-write
    STATUS      current
    DESCRIPTION
        "Indicates the advertisement packet sending interval."
    DEFVAL      { 5 }
    ::= { ibDldp2ScalarGroup 2 }

ibDldp2AuthMode OBJECT-TYPE
    SYNTAX      INTEGER
                {
                    unknown(1),
                    none(2),
                    simple(3),
                    md5(4)
                }
    MAX-ACCESS  read-write
    STATUS      current
    DESCRIPTION
        "Indicates the authentication mode.
        unknown:    cannot be determined for some reason.
        none:       not authenticated.
        simple:     authenticated by a clear text password.
        md5:        authenticated by MD5 digest."
    DEFVAL      { none }
    ::= { ibDldp2ScalarGroup 3 }

ibDldp2AuthPassword OBJECT-TYPE
    SYNTAX      OCTET STRING(SIZE(0..16))
    MAX-ACCESS  read-write
    STATUS      current
    DESCRIPTION
        "Indicates the authentication password.
        Setting the password to a zero-length octet string means
        deleting the password.
        When read, it always returns a zero-length octet string."
    ::= { ibDldp2ScalarGroup 4 }

ibDldp2UniShutdown OBJECT-TYPE
    SYNTAX      INTEGER
                {
                    unknown(1),
                    auto(2),
                    manual(3),
                    hybrid(4)
                }
    MAX-ACCESS  read-write
    STATUS      current
    DESCRIPTION
        "Indicates the shutdown mode when a unidirectional
        link has been detected.
        unknown:    cannot be determined for some reason.
        auto:       the port will be shut down automatically.
        manual:     the port must be shut down manually.
        hybrid:     the port will be shut down automatically,
                    but it must be brought up manually."
    DEFVAL  { auto }
    ::= { ibDldp2ScalarGroup 5 }

ibDldp2TableGroup         OBJECT IDENTIFIER ::= { ibDldp2 2 }

ibDldp2PortConfigTable OBJECT-TYPE
    SYNTAX      SEQUENCE OF IbDldp2PortConfigEntry
    MAX-ACCESS  not-accessible
    STATUS      current
    DESCRIPTION
        "This table contains all ports that support DLDP."
    ::= { ibDldp2TableGroup 1 }

ibDldp2PortConfigEntry OBJECT-TYPE
    SYNTAX      IbDldp2PortConfigEntry
    MAX-ACCESS  not-accessible
    STATUS      current
    DESCRIPTION
        "This entry describes a port that supports DLDP."
    INDEX
        {
            ifIndex
        }
    ::= { ibDldp2PortConfigTable 1 }

IbDldp2PortConfigEntry ::= SEQUENCE
    {
        ibDldp2PortEnable     TruthValue
    }

ibDldp2PortEnable OBJECT-TYPE
    SYNTAX      TruthValue
    MAX-ACCESS  read-write
    STATUS      current
    DESCRIPTION
        "Enable(true) or disable(false) DLDP on a port."
    ::= { ibDldp2PortConfigEntry 1 }

ibDldp2PortStatusTable OBJECT-TYPE
    SYNTAX      SEQUENCE OF IbDldp2PortStatusEntry
    MAX-ACCESS  not-accessible
    STATUS      current
    DESCRIPTION
        "This table contains all ports enabled with DLDP."
    ::= { ibDldp2TableGroup 2 }

ibDldp2PortStatusEntry OBJECT-TYPE
    SYNTAX      IbDldp2PortStatusEntry
    MAX-ACCESS  not-accessible
    STATUS      current
    DESCRIPTION
        "This entry describes a port enabled with DLDP."
    INDEX
        {
            ifIndex
        }
    ::= { ibDldp2PortStatusTable 1 }

IbDldp2PortStatusEntry ::= SEQUENCE
    {
        ibDldp2PortOperStatus     INTEGER,
        ibDldp2PortLinkStatus     INTEGER
    }

ibDldp2PortOperStatus OBJECT-TYPE
    SYNTAX      INTEGER
                {
                    unknown(1),
                    initial(2),
                    inactive(3),
                    unidirectional(4),
                    bidirectional(5)
                }
    MAX-ACCESS  read-only
    STATUS      current
    DESCRIPTION
        "Indicates the DLDP operating status on the port.
        unknown:        cannot be determined for some reason.
        initial:        DLDP is not globally enabled.
        inactive:       physical status of the port is down.
        unidirectional: all neighbors of the port are in 'unconfirmed' status.
        bidirectional:  more than one neighbor of the port is in 'confirmed'
                        status."
    ::= { ibDldp2PortStatusEntry 1 }

ibDldp2PortLinkStatus OBJECT-TYPE
    SYNTAX      INTEGER
                {
                    unknown(1),
                    down(2),
                    up(3)
                }
    MAX-ACCESS  read-only
    STATUS      current
    DESCRIPTION
        "Indicates the DLDP link status of the port.
        unknown:    cannot be determined for some reason.
        down:       the DLDP link status of the port is down.
        up:         the DLDP link status of the port is up.
        If the port operating status is not 'inactive',
        'unidirectional', or 'bidirectional', it always returns 'unknown'."
    ::= { ibDldp2PortStatusEntry 2 }

ibDldp2NeighborTable OBJECT-TYPE
    SYNTAX      SEQUENCE OF IbDldp2NeighborEntry
    MAX-ACCESS  not-accessible
    STATUS      current
    DESCRIPTION
        "This table contains all port's neighbors."
    ::= { ibDldp2TableGroup 3 }

ibDldp2NeighborEntry OBJECT-TYPE
    SYNTAX      IbDldp2NeighborEntry
    MAX-ACCESS  not-accessible
    STATUS      current
    DESCRIPTION
        "This entry describes a port's neighbors."
    INDEX
        {
            ifIndex,
            ibDldp2NeighborBridgeMac,
            ibDldp2NeighborPortIndex
        }
    ::= { ibDldp2NeighborTable 1 }

IbDldp2NeighborEntry ::= SEQUENCE
    {
        ibDldp2NeighborBridgeMac      MacAddress,
        ibDldp2NeighborPortIndex      Integer32,
        ibDldp2NeighborStatus         INTEGER,
        ibDldp2NeighborAgingTime      Integer32
    }

ibDldp2NeighborBridgeMac OBJECT-TYPE
    SYNTAX      MacAddress
    MAX-ACCESS  not-accessible
    STATUS      current
    DESCRIPTION
        "Indicates the bridge MAC address of a neighbor."
    ::= { ibDldp2NeighborEntry 1 }

ibDldp2NeighborPortIndex OBJECT-TYPE
    SYNTAX      Integer32(1..2147483647)
    MAX-ACCESS  not-accessible
    STATUS      current
    DESCRIPTION
        "Indicates the port index of a neighbor."
    ::= { ibDldp2NeighborEntry 2 }

ibDldp2NeighborStatus OBJECT-TYPE
    SYNTAX      INTEGER
                {
                    unknown(1),
                    unconfirmed(2),
                    confirmed(3)
                }
    MAX-ACCESS  read-only
    STATUS      current
    DESCRIPTION
        "Indicates the status of a neighbor.
        unknown:        cannot be determined for some reason.
        unconfirmed:    unidirectional communication between the port and
                        its neighbor.
        confirmed:      bidirectional communication between the port and
                        its neighbor."
    ::= { ibDldp2NeighborEntry 3 }

ibDldp2NeighborAgingTime OBJECT-TYPE
    SYNTAX      Integer32
    UNITS       "second"
    MAX-ACCESS  read-only
    STATUS      current
    DESCRIPTION
        "Indicates the aging time of a neighbor.
        If the neighbor status is not 'confirmed', it always returns 0."
    ::= { ibDldp2NeighborEntry 4 }

ibDldp2TrapBindObjects    OBJECT IDENTIFIER ::= { ibDldp2 3 }

ibDldp2Trap               OBJECT IDENTIFIER ::= { ibDldp2 4 }
ibDldp2TrapPrefix         OBJECT IDENTIFIER ::= { ibDldp2Trap 0 }
ibDldp2TrapUniLink NOTIFICATION-TYPE
    OBJECTS
        {
            ifIndex,
            ifDescr
        }
    STATUS      current
    DESCRIPTION
        "This trap is generated when DLDP detects a unidirectional link,
        ifIndex and ifDescr identify the port."
    ::= { ibDldp2TrapPrefix 1 }

ibDldp2TrapBidLink NOTIFICATION-TYPE
    OBJECTS
        {
            ifIndex,
            ifDescr
        }
    STATUS      current
    DESCRIPTION
        "This trap is generated when DLDP detects a bidirectional link,
        ifIndex and ifDescr identify the port."
    ::= { ibDldp2TrapPrefix 2 }

END
