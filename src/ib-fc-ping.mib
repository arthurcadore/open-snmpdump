-- =====================================================================
-- Copyright (C) 2023 Intelbras S.A. All rights reserved.
--
-- Description:
--      This MIB module is for the management of the Fibre Channel
--      Ping functionality.
-- Reference:
-- Version: V1.0
-- History:
--      V1.0 Initial version created by liuyanchao 2013-03-15
-- =====================================================================
IB-FC-PING-MIB DEFINITIONS ::= BEGIN

IMPORTS
    MODULE-IDENTITY, OBJECT-TYPE, NOTIFICATION-TYPE, Unsigned32, Integer32
        FROM SNMPv2-SMI
    RowStatus, TruthValue
        FROM SNMPv2-TC
    IbFcVsanIndex, IbFcAddressType, IbFcAddress,
    IbFcStartOper
        FROM IB-FC-TC-MIB
    ibSan
        FROM IB-VSAN-MIB;


ibFcPing  MODULE-IDENTITY
    LAST-UPDATED "201303150000Z"
    ORGANIZATION
        "Intelbras S.A. Industria de Telecomunicacao Eletronica Brasileria."
    CONTACT-INFO
        ""
    DESCRIPTION
        "This MIB module is for the management of the Fibre Channel
         Ping functionality."
    REVISION "201303150000Z"
    DESCRIPTION
        "Initial version of this MIB module."
    ::= { ibSan 5 }

ibFcPingObjects             OBJECT IDENTIFIER
    ::= { ibFcPing 1 }
ibFcPingConfigurations      OBJECT IDENTIFIER
    ::= { ibFcPingObjects 1 }
ibFcPingStatistics          OBJECT IDENTIFIER
    ::= { ibFcPingObjects 2 }
ibFcPingNotifications       OBJECT IDENTIFIER
    ::= { ibFcPingObjects 3 }
ibFcPingNotifyPrefix        OBJECT IDENTIFIER
    ::= { ibFcPingNotifications 0 }

-- FC Ping table

ibFcPingTable OBJECT-TYPE
    SYNTAX        SEQUENCE OF IbFcPingEntry
    MAX-ACCESS    not-accessible
    STATUS        current
    DESCRIPTION
        "A table of FC ping entries containing a group of
         FC ping requests that need to be executed at the
         agent."
    ::= { ibFcPingConfigurations 1 }

ibFcPingEntry OBJECT-TYPE
    SYNTAX        IbFcPingEntry
    MAX-ACCESS    not-accessible
    STATUS        current
    DESCRIPTION
        "A FC ping request entry that need to be executed
         at the agent."
    INDEX         { ibFcPingIndex }
    ::= { ibFcPingTable 1 }

IbFcPingEntry ::= SEQUENCE {
    ibFcPingIndex              Unsigned32,
    ibFcPingVsan               IbFcVsanIndex,
    ibFcPingAddressType        IbFcAddressType,
    ibFcPingAddress            IbFcAddress,
    ibFcPingPacketCount        Unsigned32,
    ibFcPingPayloadSize        Unsigned32,
    ibFcPingTimeout            Unsigned32,
    ibFcPingDelay              Unsigned32,
    ibFcPingAgeInterval        Unsigned32,
    ibFcPingAdminStatus        IbFcStartOper,
    ibFcPingOperStatus         INTEGER,
    ibFcPingTrapOnCompletion   TruthValue,
    ibFcPingRowStatus          RowStatus
}

ibFcPingIndex OBJECT-TYPE
    SYNTAX        Unsigned32 (1..65535)
    MAX-ACCESS    accessible-for-notify
    STATUS        current
    DESCRIPTION
        "The index of the current FC ping entry.  This object
         identifies a FC ping request entry uniquely in a
         specified VSAN (Virtual Storage Area Network)."
    ::= { ibFcPingEntry 1 }

ibFcPingVsan OBJECT-TYPE
    SYNTAX        IbFcVsanIndex
    MAX-ACCESS    read-create
    STATUS        current
    DESCRIPTION
        "The VSAN on which the FC ping request will be
         performed.  If the corresponding instance value of
         ibFcPingOperStatus is 'inProgress', the object
         cannot be modified."
    ::= { ibFcPingEntry 2 }

ibFcPingAddressType OBJECT-TYPE
    SYNTAX        IbFcAddressType
    MAX-ACCESS    read-create
    STATUS        current
    DESCRIPTION
        "The type of the corresponding instance of
         ibFcPingAddress object."
    DEFVAL        { fcid }
    ::= { ibFcPingEntry 3 }

ibFcPingAddress OBJECT-TYPE
    SYNTAX        IbFcAddress
    MAX-ACCESS    read-create
    STATUS        current
    DESCRIPTION
        "The address to which the route will be pinged.

         This object will contain an 8 octet long WWN(World Wide Name),
         if the value of the associated instance of ibFcPingAddressType
         object is 'wwn'.

         This object will contain a 3 octet long Fibre Channel Address ID,
         if the value of the associated instance of ibFcPingAddressType
         object is 'fcid'."
    ::= { ibFcPingEntry 4 }

ibFcPingPacketCount OBJECT-TYPE
    SYNTAX      Unsigned32 (1..2147483647)
    MAX-ACCESS  read-create
    STATUS      current
    DESCRIPTION
        "The number of FC ping packets to be sent to the
         target in this sequence."
    DEFVAL        { 5 }
    ::= { ibFcPingEntry 5 }

ibFcPingPayloadSize OBJECT-TYPE
    SYNTAX      Unsigned32
    MAX-ACCESS  read-only
    STATUS      current
    DESCRIPTION
        "This object specifies the size of the FC ping packet
         payload to be sent to the target in this sequence."
    ::= { ibFcPingEntry 6 }

ibFcPingTimeout OBJECT-TYPE
    SYNTAX        Unsigned32 (1..10)
    UNITS         "seconds"
    MAX-ACCESS    read-create
    STATUS        current
    DESCRIPTION
        "The value of timeout for this FC ping request."
    DEFVAL        { 5 }
    ::= { ibFcPingEntry 7 }

ibFcPingDelay OBJECT-TYPE
    SYNTAX      Unsigned32
    UNITS       "seconds"
    MAX-ACCESS  read-only
    STATUS      current
    DESCRIPTION
        "The minimum amount of time to wait before sending
         the next packet in a sequence, after receiving a
         response or declaring a timeout for a previously
         transmitted packet."
    ::= { ibFcPingEntry 8 }

ibFcPingAgeInterval OBJECT-TYPE
    SYNTAX        Unsigned32 (500..900)
    UNITS         "seconds"
    MAX-ACCESS    read-create
    STATUS        current
    DESCRIPTION
        "The interval time after a FC ping test completes
         before the entry is aged out."
    DEFVAL        { 500 }
    ::= { ibFcPingEntry 9 }

ibFcPingAdminStatus OBJECT-TYPE
    SYNTAX        IbFcStartOper
    MAX-ACCESS    read-create
    STATUS        current
    DESCRIPTION
        "The administrative status of each ibFcPingEntry.

         The object has two values:
         enable     -  Activate the entry.
         disable    -  Deactivate the entry.

         When the FC ping entry is executing, this object cannot be
         modified.  If this object is read at such a time, a value of
         'enable' will be returned.  When the test finishes, the value
         of this object will be set to 'disable'."
    DEFVAL        { disable }
    ::= { ibFcPingEntry 10 }

ibFcPingOperStatus OBJECT-TYPE
    SYNTAX        INTEGER {
      inProgress(1),     -- FC ping in progress
      complete(2),       -- FC ping complete
      disabled(3),       -- FC ping disabled
      failed(4)          -- FC ping failed
      }
    MAX-ACCESS    read-only
    STATUS        current
    DESCRIPTION
        "This object indicates the operational status
         of this ibFcPingEntry.

         The value specifications are listed as follows:
         inProgress     - FC ping is in progress.
         complete       - FC ping is complete.
         disabled       - FC ping is disabled.
         failed         - FC ping has failed due to resource limitations."
    ::= { ibFcPingEntry 11 }

ibFcPingTrapOnCompletion OBJECT-TYPE
    SYNTAX        TruthValue
    MAX-ACCESS    read-create
    STATUS        current
    DESCRIPTION
        "This object indicates that if ibFcPingCompletionNotify
         notification should be generated or not when the corresponding
         ping sequence completes."
    DEFVAL        { false }
    ::= { ibFcPingEntry 12 }

ibFcPingRowStatus OBJECT-TYPE
    SYNTAX        RowStatus
    MAX-ACCESS    read-create
    STATUS        current
    DESCRIPTION
        "The status of this conceptual row."
    ::= { ibFcPingEntry 13 }

-- FC Ping Statistics Table

ibFcPingStatTable OBJECT-TYPE
    SYNTAX        SEQUENCE OF IbFcPingStatEntry
    MAX-ACCESS    not-accessible
    STATUS        current
    DESCRIPTION
        "A table of FC ping statistics.
         This table notes the FC ping statistics of a FC ping test
         associated with an entry in the ibFcPingTable."
    ::= { ibFcPingStatistics 1 }

ibFcPingStatEntry OBJECT-TYPE
    SYNTAX        IbFcPingStatEntry
    MAX-ACCESS    not-accessible
    STATUS        current
    DESCRIPTION
        "A FC ping statistics entry.

         An entry will be created automatically in this table when the
         ibFcPingRowStatus of a ping request in the ibFcPingTable
         is set to 'active'.

         The entry in this table will have the same indices as the entry
         that in the ibFcPingTable.

         An entry in this table will be deleted when the corresponding
         entry in the ibFcPingTable is deleted."
    INDEX         { ibFcPingIndex }
    ::= { ibFcPingStatTable 1 }

IbFcPingStatEntry ::= SEQUENCE {
    ibFcPingReqPackets      Unsigned32,
    ibFcPingResPackets      Unsigned32,
    ibFcPingMinTime         Integer32,
    ibFcPingAverageTime     Integer32,
    ibFcPingMaxTime         Integer32,
    ibFcPingTimeoutNum      Unsigned32
}

ibFcPingReqPackets OBJECT-TYPE
    SYNTAX        Unsigned32
    MAX-ACCESS    read-only
    STATUS        current
    DESCRIPTION
        "The number of FC ping packets request in this sequence."
    ::= { ibFcPingStatEntry 1 }

ibFcPingResPackets OBJECT-TYPE
    SYNTAX        Unsigned32
    MAX-ACCESS    read-only
    STATUS        current
    DESCRIPTION
        "The number of FC ping packets response in this sequence."
    ::= { ibFcPingStatEntry 2 }

ibFcPingMinTime OBJECT-TYPE
    SYNTAX        Integer32
    UNITS         "microseconds"
    MAX-ACCESS    read-only
    STATUS        current
    DESCRIPTION
        "The minimum round trip time of all the packets that
         have been sent in this sequence."
    ::= { ibFcPingStatEntry 3 }

ibFcPingAverageTime OBJECT-TYPE
    SYNTAX        Integer32
    UNITS         "microseconds"
    MAX-ACCESS    read-only
    STATUS        current
    DESCRIPTION
        "The average round trip time of all the packets that
         have been sent in this sequence."
    ::= { ibFcPingStatEntry 4 }

ibFcPingMaxTime OBJECT-TYPE
    SYNTAX        Integer32
    UNITS         "microseconds"
    MAX-ACCESS    read-only
    STATUS        current
    DESCRIPTION
        "The maximum round trip time of all the packets that
         have been sent in this sequence."
    ::= { ibFcPingStatEntry 5 }


ibFcPingTimeoutNum OBJECT-TYPE
    SYNTAX        Unsigned32
    MAX-ACCESS    read-only
    STATUS        current
    DESCRIPTION
        "The number of timeouts encountered in this sequence."
    ::= { ibFcPingStatEntry 6 }

-- Notifications

ibFcPingCompletionNotify NOTIFICATION-TYPE
    OBJECTS       { ibFcPingIndex,
                    ibFcPingVsan,
                    ibFcPingAddressType,
                    ibFcPingAddress,
                    ibFcPingReqPackets,
                    ibFcPingResPackets}
    STATUS        current
    DESCRIPTION
        "When a FC ping test is finished and the instance of
         ibFcPingTrapOnCompletion associated with the test
         is set to 'true', this notification occurred."
    ::= { ibFcPingNotifyPrefix 1 }

END
