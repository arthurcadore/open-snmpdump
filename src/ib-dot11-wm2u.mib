-- =============================================================================
-- Copyright (C) 2023 Intelbras S.A. All rights reserved.
--
-- Description:
--   The file defines a MIB for the wireless multicast to unicast (WM2U) feature,
--   which is used to improve multicast performance.
-- Reference:
-- Version: V1.1
-- History:
--   V1.0 created by sunanzhi
--     Initial version 2015-04-27
--   V1.1 2016-1-25 updated by sunanzhi
--     Modify IbDot11WM2UAgingTimeEntry
-- =============================================================================
IB-DOT11-WM2U-MIB DEFINITIONS ::= BEGIN

IMPORTS
    TimeTicks, Unsigned32, OBJECT-TYPE, MODULE-IDENTITY
        FROM SNMPv2-SMI
    MacAddress, TEXTUAL-CONVENTION
        FROM SNMPv2-TC
    InetAddress, InetAddressType
        FROM INET-ADDRESS-MIB   -- [RFC4001]
    ibDot11
        FROM IB-OID-MIB;

ibDot11WM2U MODULE-IDENTITY
    LAST-UPDATED "201601251020Z"        -- January 25, 2016 at 10:20 GMT
    ORGANIZATION
        "Intelbras S.A. Industria de Telecomunicacao Eletronica Brasileria."
    CONTACT-INFO
        ""
    DESCRIPTION
        "This MIB provides information about the WM2U feature."
    REVISION "201601251020Z"        -- January 25, 2016 at 10:20 GMT
    DESCRIPTION
        "Modify IbDot11WM2UAgingTimeEntry."
    REVISION "201503311551Z"        -- March 31, 2015 at 13:51 GMT
    DESCRIPTION
        "The initial revision of this MIB module."
    ::= {  ibDot11 16 }

--
-- Textual conventions
--
IbDot11WM2UEnableStatus ::= TEXTUAL-CONVENTION
        STATUS      current
        DESCRIPTION
            "The enable status values for objects.
            Values include enabled and disbaled."
        SYNTAX      INTEGER { enabled(1), disabled(2) }

IbDot11WM2UAction ::= TEXTUAL-CONVENTION
        STATUS      current
        DESCRIPTION
            "Action to take when the number of clients exceeds the threshold."
        SYNTAX  INTEGER
            {
            drop(1),
            unicast(2),
            multicast(3)
            }

IbDot11WM2UGroupVersion ::= TEXTUAL-CONVENTION
        STATUS      current
        DESCRIPTION
            "Multicast protocol version."
        SYNTAX  INTEGER
            {
            igmpv1orv2(1),
            igmpv3(2),
            mldv1(3),
            mldv2(4)
            }

IbDot11WM2UGroupMode ::= TEXTUAL-CONVENTION
        STATUS      current
        DESCRIPTION
            "Multicast source filtering mode."
        SYNTAX  INTEGER
            {
            include(1),
            exclude(2)
            }


--
-- Node definitions
--
ibDot11WM2UConfigGroup OBJECT IDENTIFIER ::= { ibDot11WM2U 1 }
ibDot11WM2UDataGroup OBJECT IDENTIFIER ::= { ibDot11WM2U 2 }

ibDot11WM2USrvTempStatesTable OBJECT-TYPE
    SYNTAX SEQUENCE OF IbDot11WM2USrvTempStatesEntry
    MAX-ACCESS not-accessible
    STATUS current
    DESCRIPTION
        "The table contains the enable status of WM2U in service templates."
    ::= { ibDot11WM2UConfigGroup 1 }

ibDot11WM2USrvTempStatesEntry OBJECT-TYPE
    SYNTAX IbDot11WM2USrvTempStatesEntry
    MAX-ACCESS not-accessible
    STATUS current
    DESCRIPTION
        "Each entry contains the enable status of WM2U in a service template."
    INDEX { ibDot11WM2USrvTempName,  ibDot11WM2USrvTempAddressType}
    ::= { ibDot11WM2USrvTempStatesTable 1 }

IbDot11WM2USrvTempStatesEntry ::= SEQUENCE {
        ibDot11WM2USrvTempName                    OCTET STRING,
        ibDot11WM2USrvTempAddressType                  InetAddressType,
        ibDot11WM2USrvTempState                   IbDot11WM2UEnableStatus
     }

ibDot11WM2USrvTempName OBJECT-TYPE
    SYNTAX OCTET STRING (SIZE (1..63))
    MAX-ACCESS not-accessible
    STATUS current
    DESCRIPTION
        "Represents the name of the service template."
    ::= { ibDot11WM2USrvTempStatesEntry 1 }

ibDot11WM2USrvTempAddressType OBJECT-TYPE
    SYNTAX InetAddressType
    MAX-ACCESS not-accessible
    STATUS current
    DESCRIPTION
        "Represents the address type."
    ::= { ibDot11WM2USrvTempStatesEntry 2 }

ibDot11WM2USrvTempState OBJECT-TYPE
    SYNTAX IbDot11WM2UEnableStatus
    MAX-ACCESS read-write
    STATUS current
    DESCRIPTION
        "The enable status of WM2U."
    ::= { ibDot11WM2USrvTempStatesEntry 3 }

ibDot11WM2UAgingTimeTable OBJECT-TYPE
    SYNTAX SEQUENCE OF IbDot11WM2UAgingTimeEntry
    MAX-ACCESS not-accessible
    STATUS current
    DESCRIPTION
        "The table contains WM2U entry aging information."
    ::= { ibDot11WM2UConfigGroup 2 }

ibDot11WM2UAgingTimeEntry OBJECT-TYPE
    SYNTAX IbDot11WM2UAgingTimeEntry
    MAX-ACCESS not-accessible
    STATUS current
    DESCRIPTION
        "Each entry contains the aging time for an address type."
    INDEX { ibDot11WM2UAgingAddressType }
    ::= { ibDot11WM2UAgingTimeTable 1 }

IbDot11WM2UAgingTimeEntry ::= SEQUENCE {
        ibDot11WM2UAgingAddressType                    InetAddressType,
        ibDot11WM2UAgingTime                           Unsigned32,
        ibDot11WM2UAgingTimeState                      IbDot11WM2UEnableStatus
     }

ibDot11WM2UAgingAddressType OBJECT-TYPE
    SYNTAX InetAddressType
    MAX-ACCESS not-accessible
    STATUS current
    DESCRIPTION
        "Represents the address type."
    ::= { ibDot11WM2UAgingTimeEntry 1 }

ibDot11WM2UAgingTime OBJECT-TYPE
    SYNTAX Unsigned32 (60..3600)
    UNITS   "seconds"
    MAX-ACCESS read-write
    STATUS current
    DESCRIPTION
        "Represents the aging time."
    ::= { ibDot11WM2UAgingTimeEntry 2 }

ibDot11WM2UAgingTimeState OBJECT-TYPE
    SYNTAX IbDot11WM2UEnableStatus
    MAX-ACCESS read-write
    STATUS current
    DESCRIPTION
        "The configuration status of the aging time."
    ::= { ibDot11WM2UAgingTimeEntry 3 }

ibDot11WM2UClientEtyLmtTable OBJECT-TYPE
    SYNTAX SEQUENCE OF IbDot11WM2UClientEtyLmtEntry
    MAX-ACCESS not-accessible
    STATUS current
    DESCRIPTION
        "The table contains the WM2U entry limit for each client."
    ::= { ibDot11WM2UConfigGroup 3 }

ibDot11WM2UClientEtyLmtEntry OBJECT-TYPE
    SYNTAX IbDot11WM2UClientEtyLmtEntry
    MAX-ACCESS not-accessible
    STATUS current
    DESCRIPTION
        "Each entry contains the WM2U entry limit for each client of an
        address type."
    INDEX { ibDot11WM2UClientEtyAddrType }
    ::= { ibDot11WM2UClientEtyLmtTable 1 }

IbDot11WM2UClientEtyLmtEntry ::= SEQUENCE {
        ibDot11WM2UClientEtyAddrType                InetAddressType,
        ibDot11WM2UClientValue                         Unsigned32,
        ibDot11WM2UClientState                         IbDot11WM2UEnableStatus
     }

ibDot11WM2UClientEtyAddrType OBJECT-TYPE
    SYNTAX InetAddressType
    MAX-ACCESS not-accessible
    STATUS current
    DESCRIPTION
        "Represents the address type."
    ::= { ibDot11WM2UClientEtyLmtEntry 1 }

ibDot11WM2UClientValue OBJECT-TYPE
    SYNTAX Unsigned32 (8..1024)
    MAX-ACCESS read-write
    STATUS current
    DESCRIPTION
        "Maximum number of WM2U entries for each client of the address type."
    ::= { ibDot11WM2UClientEtyLmtEntry 2 }

ibDot11WM2UClientState OBJECT-TYPE
    SYNTAX IbDot11WM2UEnableStatus
    MAX-ACCESS read-write
    STATUS current
    DESCRIPTION
        "The enable status of the per-client WM2U entry limit."
    ::= { ibDot11WM2UClientEtyLmtEntry 3 }

ibDot11WM2UGlobalEtyLmtTable OBJECT-TYPE
    SYNTAX SEQUENCE OF IbDot11WM2UGlobalEntryLmtsEntry
    MAX-ACCESS not-accessible
    STATUS current
    DESCRIPTION
        "The table contains the WM2U table size."
    ::= { ibDot11WM2UConfigGroup 4 }

ibDot11WM2UGlobalEtyLmtEntry OBJECT-TYPE
    SYNTAX IbDot11WM2UGlobalEntryLmtsEntry
    MAX-ACCESS not-accessible
    STATUS current
    DESCRIPTION
        "Each entry contains the WM2U table size for an address type."
    INDEX { ibDot11WM2UGlobalEtyAddrType }
    ::= { ibDot11WM2UGlobalEtyLmtTable 1 }

IbDot11WM2UGlobalEntryLmtsEntry ::= SEQUENCE {
        ibDot11WM2UGlobalEtyAddrType                InetAddressType,
        ibDot11WM2UGlobalValue                         Unsigned32,
        ibDot11WM2UGlobalState                         IbDot11WM2UEnableStatus
     }

ibDot11WM2UGlobalEtyAddrType OBJECT-TYPE
    SYNTAX InetAddressType
    MAX-ACCESS not-accessible
    STATUS current
    DESCRIPTION
        "Represents the address type."
    ::= { ibDot11WM2UGlobalEtyLmtEntry 1 }

ibDot11WM2UGlobalValue OBJECT-TYPE
    SYNTAX Unsigned32 (8..8192)
    MAX-ACCESS read-write
    STATUS current
    DESCRIPTION
        "WM2U table size(The maximum number of entries that the WM2U table
        can contain)."
    ::= { ibDot11WM2UGlobalEtyLmtEntry 2 }

ibDot11WM2UGlobalState OBJECT-TYPE
    SYNTAX IbDot11WM2UEnableStatus
    MAX-ACCESS read-write
    STATUS current
    DESCRIPTION
        "The enable status of the WM2U table size setting."
    ::= { ibDot11WM2UGlobalEtyLmtEntry 3 }

ibDot11WM2UFwdClientLmtsTable OBJECT-TYPE
    SYNTAX SEQUENCE OF IbDot11WM2UFwdClientLmtsEntry
    MAX-ACCESS not-accessible
    STATUS current
    DESCRIPTION
        "The table contains the limit on the number of clients of each address
        type in the WM2U table."
    ::= { ibDot11WM2UConfigGroup 5 }

ibDot11WM2UFwdClientLmtsEntry OBJECT-TYPE
    SYNTAX IbDot11WM2UFwdClientLmtsEntry
    MAX-ACCESS not-accessible
    STATUS current
    DESCRIPTION
        "Each entry contains the limit on the number of clients of an address
        type in the WM2U table."
    INDEX { ibDot11WM2UFwdClientAddrType }
    ::= { ibDot11WM2UFwdClientLmtsTable 1 }

IbDot11WM2UFwdClientLmtsEntry ::= SEQUENCE {
        ibDot11WM2UFwdClientAddrType                InetAddressType,
        ibDot11WM2UFwdClientValue                      Unsigned32,
        ibDot11WM2UFwdClientAction                     IbDot11WM2UAction,
        ibDot11WM2UFwdClientState                      IbDot11WM2UEnableStatus
     }

ibDot11WM2UFwdClientAddrType OBJECT-TYPE
    SYNTAX InetAddressType
    MAX-ACCESS not-accessible
    STATUS current
    DESCRIPTION
        "Represents the address type."
    ::= { ibDot11WM2UFwdClientLmtsEntry 1 }

ibDot11WM2UFwdClientValue OBJECT-TYPE
    SYNTAX Unsigned32 (1..256)
    MAX-ACCESS read-write
    STATUS current
    DESCRIPTION
        "Limit on the number of clients of the address type."
    ::= { ibDot11WM2UFwdClientLmtsEntry 2 }

ibDot11WM2UFwdClientAction OBJECT-TYPE
    SYNTAX IbDot11WM2UAction
    MAX-ACCESS read-write
    STATUS current
    DESCRIPTION
        "Action to take when the number of clients exceeds the limit."
    ::= { ibDot11WM2UFwdClientLmtsEntry 3 }

ibDot11WM2UFwdClientState OBJECT-TYPE
    SYNTAX IbDot11WM2UEnableStatus
    MAX-ACCESS read-write
    STATUS current
    DESCRIPTION
        "The enable status of the client limit."
    ::= { ibDot11WM2UFwdClientLmtsEntry 4 }

ibDot11WM2URateLimitsTable OBJECT-TYPE
    SYNTAX SEQUENCE OF IbDot11WM2URateLimitsEntry
    MAX-ACCESS not-accessible
    STATUS current
    DESCRIPTION
        "The table contains multicast packet rate limit information."
    ::= { ibDot11WM2UConfigGroup 6 }

ibDot11WM2URateLimitsEntry OBJECT-TYPE
    SYNTAX IbDot11WM2URateLimitsEntry
    MAX-ACCESS not-accessible
    STATUS current
    DESCRIPTION
        "Each entry contains the packet rate limit for an address type."
    INDEX { ibDot11WM2URateLmtsAddrType }
    ::= { ibDot11WM2URateLimitsTable 1 }

IbDot11WM2URateLimitsEntry ::= SEQUENCE {
        ibDot11WM2URateLmtsAddrType                 InetAddressType,
        ibDot11WM2UInterval                            Unsigned32,
        ibDot11WM2UThreshold                           Unsigned32,
        ibDot11WM2URateLmtsState                       IbDot11WM2UEnableStatus
     }

ibDot11WM2URateLmtsAddrType OBJECT-TYPE
    SYNTAX InetAddressType
    MAX-ACCESS not-accessible
    STATUS current
    DESCRIPTION
        "Represents the address type."
    ::= { ibDot11WM2URateLimitsEntry 1 }

ibDot11WM2UInterval OBJECT-TYPE
    SYNTAX Unsigned32 (60..3600)
    UNITS  "seconds"
    MAX-ACCESS read-write
    STATUS current
    DESCRIPTION
        "Interval for calculating the incoming multicast packet rate,
         unit for seconds."
    ::= { ibDot11WM2URateLimitsEntry 2 }

ibDot11WM2UThreshold OBJECT-TYPE
    SYNTAX Unsigned32 (1..100000)
    MAX-ACCESS read-write
    STATUS current
    DESCRIPTION
        "Threshold on the number of multicast packets received over the
        specified interval."
    ::= { ibDot11WM2URateLimitsEntry 3 }

ibDot11WM2URateLmtsState OBJECT-TYPE
    SYNTAX IbDot11WM2UEnableStatus
    MAX-ACCESS read-write
    STATUS current
    DESCRIPTION
        "The enable status of IGMP packet rate limiting."
    ::= { ibDot11WM2URateLimitsEntry 4 }

ibDot11WM2UClientsTable OBJECT-TYPE
    SYNTAX SEQUENCE OF IbDot11WM2UClientsEntry
    MAX-ACCESS not-accessible
    STATUS current
    DESCRIPTION
        "The table contains WM2U client information."
    ::= { ibDot11WM2UDataGroup 1 }

ibDot11WM2UClientsEntry OBJECT-TYPE
    SYNTAX IbDot11WM2UClientsEntry
    MAX-ACCESS not-accessible
    STATUS current
    DESCRIPTION
        "Each entry contains information about a client."
    INDEX { ibDot11WM2UClientMacAddress }
    ::= { ibDot11WM2UClientsTable 1 }

IbDot11WM2UClientsEntry ::= SEQUENCE {
        ibDot11WM2UClientMacAddress                    MacAddress,
        ibDot11WM2UDuration                            TimeTicks,
        ibDot11WM2UGroupNum4                           Unsigned32,
        ibDot11WM2UGroupNum6                           Unsigned32
     }

ibDot11WM2UClientMacAddress OBJECT-TYPE
    SYNTAX MacAddress
    MAX-ACCESS not-accessible
    STATUS current
    DESCRIPTION
        "Client MAC address."
    ::= { ibDot11WM2UClientsEntry 1 }

ibDot11WM2UDuration OBJECT-TYPE
    SYNTAX TimeTicks
    MAX-ACCESS read-only
    STATUS current
    DESCRIPTION
        "The amount of time that has elapsed since the client was discovered."
    ::= { ibDot11WM2UClientsEntry 2 }

ibDot11WM2UGroupNum4 OBJECT-TYPE
    SYNTAX Unsigned32
    MAX-ACCESS read-only
    STATUS current
    DESCRIPTION
        "The number of IGMP multicast groups that the client has joined."
    ::= { ibDot11WM2UClientsEntry 3 }

ibDot11WM2UGroupNum6 OBJECT-TYPE
    SYNTAX Unsigned32
    MAX-ACCESS read-only
    STATUS current
    DESCRIPTION
        "The number of MLD multicast groups that the client has joined."
    ::= { ibDot11WM2UClientsEntry 4 }

ibDot11WM2UGroupsTable OBJECT-TYPE
    SYNTAX SEQUENCE OF IbDot11WM2UGroupsEntry
    MAX-ACCESS not-accessible
    STATUS current
    DESCRIPTION
        "The table contains WM2U group information."
    ::= { ibDot11WM2UDataGroup 2 }

ibDot11WM2UGroupsEntry OBJECT-TYPE
    SYNTAX IbDot11WM2UGroupsEntry
    MAX-ACCESS not-accessible
    STATUS current
    DESCRIPTION
        "Each entry contains information about each group."
    INDEX { ibDot11WM2UGrpMacAddress, ibDot11WM2UGrpAddressType, ibDot11WM2UAddress }
    ::= { ibDot11WM2UGroupsTable 1 }

IbDot11WM2UGroupsEntry ::= SEQUENCE {
        ibDot11WM2UGrpMacAddress                       MacAddress,
        ibDot11WM2UGrpAddressType                      InetAddressType,
        ibDot11WM2UAddress                             InetAddress,
        ibDot11WM2UVersion                             IbDot11WM2UGroupVersion,
        ibDot11WM2UMode                                IbDot11WM2UGroupMode,
        ibDot11WM2USourceNum                           Unsigned32,
        ibDot11WM2UGrpDurLastRefTime                   TimeTicks
     }

ibDot11WM2UGrpMacAddress OBJECT-TYPE
    SYNTAX MacAddress
    MAX-ACCESS not-accessible
    STATUS current
    DESCRIPTION
        "Client MAC address."
    ::= { ibDot11WM2UGroupsEntry 1 }

ibDot11WM2UGrpAddressType OBJECT-TYPE
    SYNTAX InetAddressType
    MAX-ACCESS not-accessible
    STATUS current
    DESCRIPTION
        "Represents the address type."
    ::= { ibDot11WM2UGroupsEntry 2 }

ibDot11WM2UAddress OBJECT-TYPE
    SYNTAX InetAddress
    MAX-ACCESS not-accessible
    STATUS current
    DESCRIPTION
        "Multicast group address."
    ::= { ibDot11WM2UGroupsEntry 3 }

ibDot11WM2UVersion OBJECT-TYPE
    SYNTAX IbDot11WM2UGroupVersion
    MAX-ACCESS read-only
    STATUS current
    DESCRIPTION
        "The version of the group."
    ::= { ibDot11WM2UGroupsEntry 4 }

ibDot11WM2UMode OBJECT-TYPE
    SYNTAX IbDot11WM2UGroupMode
    MAX-ACCESS read-only
    STATUS current
    DESCRIPTION
        "The source filtering mode of the group."
    ::= { ibDot11WM2UGroupsEntry 5 }

ibDot11WM2USourceNum OBJECT-TYPE
    SYNTAX Unsigned32
    MAX-ACCESS read-only
    STATUS current
    DESCRIPTION
        "The number of multicast sources."
    ::= { ibDot11WM2UGroupsEntry 6 }

ibDot11WM2UGrpDurLastRefTime OBJECT-TYPE
    SYNTAX TimeTicks
    MAX-ACCESS read-only
    STATUS current
    DESCRIPTION
        "The amount of time that has elapsed since the multicast group
        entry was created."
    ::= { ibDot11WM2UGroupsEntry 7 }

ibDot11WM2USourcesTable OBJECT-TYPE
    SYNTAX SEQUENCE OF IbDot11WM2USourcesEntry
    MAX-ACCESS not-accessible
    STATUS current
    DESCRIPTION
        "The table contains WM2U source information."
    ::= { ibDot11WM2UDataGroup 3 }

ibDot11WM2USourcesEntry OBJECT-TYPE
    SYNTAX IbDot11WM2USourcesEntry
    MAX-ACCESS not-accessible
    STATUS current
    DESCRIPTION
        "Each entry contains information about a multicast source."
    INDEX { ibDot11WM2USrcMacAddress, ibDot11WM2USrcAddressType, ibDot11WM2UGroupAddress, ibDot11WM2USourceAddress }
    ::= { ibDot11WM2USourcesTable 1 }

IbDot11WM2USourcesEntry ::= SEQUENCE {
        ibDot11WM2USrcMacAddress                       MacAddress,
        ibDot11WM2USrcAddressType                      InetAddressType,
        ibDot11WM2UGroupAddress                        InetAddress,
        ibDot11WM2USourceAddress                       InetAddress,
        ibDot11WM2USrcDurLastRefTime                   TimeTicks
     }

ibDot11WM2USrcMacAddress OBJECT-TYPE
    SYNTAX MacAddress
    MAX-ACCESS not-accessible
    STATUS current
    DESCRIPTION
        "Client MAC address."
    ::= { ibDot11WM2USourcesEntry 1 }

ibDot11WM2USrcAddressType OBJECT-TYPE
    SYNTAX InetAddressType
    MAX-ACCESS not-accessible
    STATUS current
    DESCRIPTION
        "Represents the address type."
    ::= { ibDot11WM2USourcesEntry 2 }

ibDot11WM2UGroupAddress OBJECT-TYPE
    SYNTAX InetAddress
    MAX-ACCESS not-accessible
    STATUS current
    DESCRIPTION
        "Multicast group address."
    ::= { ibDot11WM2USourcesEntry 3 }

ibDot11WM2USourceAddress OBJECT-TYPE
    SYNTAX InetAddress
    MAX-ACCESS not-accessible
    STATUS current
    DESCRIPTION
        "Source address."
    ::= { ibDot11WM2USourcesEntry 4 }

ibDot11WM2USrcDurLastRefTime OBJECT-TYPE
    SYNTAX TimeTicks
    MAX-ACCESS read-only
    STATUS current
    DESCRIPTION
        "The amount of time that has elapsed since the source was added
        to the multicast group."
    ::= { ibDot11WM2USourcesEntry 5 }

END
