-- ===========================================================================================================
-- Copyright (C) 2023 Intelbras S.A. All rights reserved.
--
-- Description: System Management MIB
-- Reference:
-- Version: V3.0
-- History:
--  revision 1.0 2002-12-20 created by xuqingwei
--  revision 1.1 2004-4-16  added the support for XRN  by xuqingwei
--  revision 1.2 2004-4-16  added 'ibSysImageType' in ibSysImageTable for dual image  by changxiangqing
--  revision 1.3 2004-5-14  convert MIB object name from ibXXX to ib, etc.
--  revision 1.31 2004-7-16 1. modified 'ibSysImageSize' in ibSysImageTable by zhaolina
--                      2.modified SYNTAX of 'ibSysReloadImage','ibSysImageIndex','ibSysCFGFileIndex'
--                           from (1..2147483647) to (0..2147483647) by zhaolina
--  revision 1.5 2004-8-1  1. added 'secure' attribute for ibSysImageType in ibSysImageTable by zhaolina
--                         2.modified 'MAX-ACCESS' of ibSysReloadTag from 'read-create' to 'read-write' by zhaolina
--                         3.modified DESCRIPTION of ibSysReloadNotification by zhaolina
--                         4.modified DESCRIPTION of ibSysImageType,ibSysImageIndex,ibSysImageTable and ibSysReloadImage by zhaolina
--  revision 1.6 2004-9-8  1.modified DESCRIPTION of ibSysImageType by wangyingxia
--                         2.added the trap object ibSysStartUpNotification by wangyingxia
--                         3.added ibSysStartUpNotification into the NOTIFICATION OF ibSystemManMIBNotifications
--  revision 1.7 2004-10-12 updated by gaolong
--               Change all underscore('_') characters to hyphen characters('-') because underscore character is not allowed in MIB module.
--               Remove ibSysCurEntPhysicalIndex from ibSysCurGroup because this object is not accessible.
--  revision 1.8 2004-11-08 Change the description of ibSysReloadScheduleIndex by gaolong
--  revision 1.9 2005-04-08 updated by songjie.
--               1. added the support of summer time.
--               2. correct word errors and adjust file format.
--  revision 2.0 2005-12-26 updated by jinyi
--               added ibSysCurBtmFileName, ibSysCurUpdateBtmFileName,
--               ibSysBtmLoadMaxNumber, and ibSysBtmLoadTable.
--  revision 2.1 2006-04-03 updated by shuaixiaojuan
--               modified descriptions of some objects.
--  revision 2.2 2009-06-07 Change the MAX-ACCESS of ibSysLocalClock.
--          V2.3 2010-03-17 add ibSysLocalClockString by jinyi
--  revision V2.4 2011-08-30 add  ibSysPackage, ibSysIpePackage by z02031
--  revision V2.5 2013-10-18 add ibSysPackageLoadAttribute, ibSysPackageModel, ibSysIpeFileModel,
--                ibSysIpePackageModel and ibSysSetBootImage by z03030 and z08715
--  revision V2.6 2015-07-07 add ibSysClockProtocolGroup, ibSysClockProtocol, ibSysClockProtocolSrcMdc
--                and ibSysClockProtocolSrcContext by l09650
--  revision V2.7 2017-05-27 add ibSysLocalClockString2 by h12133
--                2018-01-10 added 'interface' attribute for ibSysClockProtocol in ibSysClockProtocolGroup by t16382
--  revision V2.8 2020-02-21 added 'gnss' attribute for ibSysClockProtocol in ibSysClockProtocolGroup by d04404
--  revision V2.9 2022-07-11 added ibSysPatchInstallFail, ibSysPackageVerifyFailed, ibSysPatchInstallFailPkgname,
--                ibSysPatchInstallFailChassis, ibSysPatchInstallFailSlot, ibSysPatchInstallFailCpu,
--                ibSysPVFPhysicalName, ibSysPVFPackageName, and ibSysPVFFailReason by tkf9872
--  revision V3.0 2022-09-08 added ibSysPatchInstallSuccess, ibSysPatchInstalledPkgname, ibSysPatchInstalledChassis,
--                ibSysPatchInstalledSlot and ibSysPatchInstalledCpu by y04822
--                2022-10-25 added ibSysPatchActiveNeedRestart, ibSysPatchInactiveNeedRestart,
--                ibSysPatchOperPkgName, ibSysPatchOperChassis,  ibSysPatchOperSlot, ibSysPatchOperCpu
--                ibSysPatchInstallFailErrCode, and ibSysPatchInstallFailReason by y04822
--                2023-06-15 added ibSysVerChkDiffNotify, ibSysVerChkDiffRecoveryNotify,
--                ibSysTrapObjectChassis, ibSysTrapObjectSlot, and ibSysTrapObjectCpu by y04822
-- ============================================================================================================
IB-SYS-MAN-MIB DEFINITIONS ::= BEGIN

IMPORTS
    OBJECT-GROUP, MODULE-COMPLIANCE, NOTIFICATION-GROUP
        FROM SNMPv2-CONF
    Integer32, OBJECT-TYPE, MODULE-IDENTITY, NOTIFICATION-TYPE, TimeTicks, Unsigned32
        FROM SNMPv2-SMI
    DateAndTime, DisplayString, RowStatus, TruthValue
        FROM SNMPv2-TC
    SnmpTagList, SnmpTagValue
        FROM SNMP-TARGET-MIB
    ibCommon
        FROM IB-OID-MIB;


ibSystemMan MODULE-IDENTITY
    LAST-UPDATED "202306150000Z"
    ORGANIZATION
        "Intelbras S.A. Industria de Telecomunicacao Eletronica Brasileria."
    CONTACT-INFO
        ""
    DESCRIPTION
        "Added ibSysVerChkDiffNotify, ibSysVerChkDiffRecoveryNotify,
         ibSysTrapObjectChassis, ibSysTrapObjectSlot, and ibSysTrapObjectCpu."
    REVISION     "202306150000Z"
    DESCRIPTION
        "This MIB contains objects to manage the system.
         It focuses on the display of current configure file and image
         file,and the definition of reloading image.
         Add the support for XRN."
    REVISION     "202210250000Z"
    DESCRIPTION  "Added ibPatchActiveNeedRestart, ibPatchInactiveNeedRestart, ibSysPatchOperPkgName,
                  ibSysPatchOperChassis, ibSysPatchOperSlot, ibSysPatchOperCpu,
                  ibSysPatchInstallFailErrCode, and ibSysPatchInstallFailReason."
    REVISION     "202209080000Z"
    DESCRIPTION  "Added ibSysPatchInstallSuccess, ibSysPatchInstalledPkgname, ibSysPatchInstalledChassis,
                  ibSysPatchInstalledSlot and ibSysPatchInstalledCpu."
    REVISION     "202207110000Z"
    DESCRIPTION  "Added ibSysPatchInstallFail, ibSysPackageVerifyFailed, ibSysPatchInstallFailPkgname,
                  ibSysPatchInstallFailChassis, ibSysPatchInstallFailSlot, ibSysPatchInstallFailCpu,
                  ibSysPVFPhysicalName, ibSysPVFPackageName, ibSysPVFFailReason."
    REVISION     "202002210000Z"
    DESCRIPTION  "Added 'gnss' attribute for ibSysClockProtocol in ibSysClockProtocolGroup."
    REVISION     "201801100000Z"
    DESCRIPTION  "Added 'interface' attribute for ibSysClockProtocol in ibSysClockProtocolGroup."
    REVISION     "201706120000Z"
    DESCRIPTION  "Added ibSysLocalClockString2."
    REVISION     "201507270000Z"
    DESCRIPTION  "Added ibSysClockProtocolGroup, ibSysClockProtocol, ibSysClockProtocolSrcMdc
--                and ibSysClockProtocolSrcContext."
    REVISION "200404081345Z"        -- April 08, 2004 at 13:45 GMT
    DESCRIPTION
        " "
    ::= { ibCommon 3 }


-- XRN brief introduction:
--    Expandable resilient networking (XRN) is a technology to construct expandable
--    resilient networks. With XRN feature, you can connect several devices into a
--    combined device and treat them as a single one. The combined device is called
--    Fabric, while the member devices are units.




--
-- Node definitions
--

ibSystemManMIBObjects OBJECT IDENTIFIER ::= { ibSystemMan 1 }


ibSysClock OBJECT IDENTIFIER ::= { ibSystemManMIBObjects 1 }

ibSysLocalClock OBJECT-TYPE
    SYNTAX DateAndTime
    MAX-ACCESS read-write
    STATUS current
    DESCRIPTION
        "
        This node gives the current local time of the system.
        The unit of it is DateAndTime.
        "
    ::= { ibSysClock 1 }

ibSysSummerTime OBJECT IDENTIFIER ::= { ibSysClock 2 }

ibSysSummerTimeEnable OBJECT-TYPE
    SYNTAX INTEGER
    {
        enable(1),
        disable(2)
    }
    MAX-ACCESS read-only
    STATUS current
    DESCRIPTION
        "This node indicates the status of summer time.
        If the value of this node is enable, means that summer time is
        enabled.
        If the value is disable, means that summer time is disabled.
        "
    ::= { ibSysSummerTime 1 }

ibSysSummerTimeZone OBJECT-TYPE
    SYNTAX DisplayString (SIZE (0..255))
    MAX-ACCESS read-write
    STATUS current
    DESCRIPTION
        "
        This node describes the name of time zone in summer.
        The string is only used to display in local time when summer
        time is running.
        That the value of ibSysLocalClock has the time zone information
        means that summer time is running.
        "
    ::= { ibSysSummerTime 2 }

ibSysSummerTimeMethod OBJECT-TYPE
    SYNTAX INTEGER
    {
        oneOff(1),
        repeating(2)
    }
    MAX-ACCESS read-write
    STATUS current
    DESCRIPTION
        "
        This node provides the execute method of summer time.
        oneOff(1):   means that summer time only takes effect at specified time.
        repeating(2): means that summer time takes effect in specified month/day
                      once a year.
        "
    ::= { ibSysSummerTime 3 }

ibSysSummerTimeStart OBJECT-TYPE
    SYNTAX DateAndTime (SIZE(8))
    MAX-ACCESS read-write
    STATUS current
    DESCRIPTION
        "
        This node provides the start time of summer time.
        "
    ::= { ibSysSummerTime 4 }

ibSysSummerTimeEnd OBJECT-TYPE
    SYNTAX DateAndTime (SIZE(8))
    MAX-ACCESS read-write
    STATUS current
    DESCRIPTION
        "
        This node provides the end time of summer time.
        The end time must be more than start time one day and less
        than start time one year.
        "
    ::= { ibSysSummerTime 5 }

ibSysSummerTimeOffset OBJECT-TYPE
    SYNTAX Integer32 (0..86399)
    MAX-ACCESS read-write
    STATUS current
    DESCRIPTION
        "
        This node provides the offset time of summer time.
        The offset time(in seconds) means that how much time need to be
        appended to the local time.
        "
    ::= { ibSysSummerTime 6 }

ibSysLocalClockString OBJECT-TYPE
    SYNTAX OCTET STRING(SIZE (16..24))
    MAX-ACCESS read-write
    STATUS current
    DESCRIPTION
        "This node gives the current local time of the system.
        For example, Tuesday May 26, 2002 at 1:30:15 would be
        displayed as: 2002-5-26T13:30:15.0Z"
    ::= { ibSysClock 3 }

ibSysClockProtocolGroup OBJECT IDENTIFIER ::= { ibSysClock 4 }

ibSysLocalClockString2 OBJECT-TYPE
    SYNTAX OCTET STRING(SIZE (14..19))
    MAX-ACCESS read-write
    STATUS current
    DESCRIPTION
        "This node gives the current local time of the system.
        For example, 1:30:15 on Tuesday, May 26th, 2002 will be
        displayed as: 2002/05/26/01/30/15.
        2002/5/26/1/30/15 or 2002/05/26/01/30/15 will be applied in a write operation."
    ::= { ibSysClock 5 }

ibSysClockProtocol OBJECT-TYPE
    SYNTAX INTEGER
        {
        none(1),
        ntp(2),
        ptp(3),
        interface(4),
        gnss(5)
         }
    MAX-ACCESS read-write
    STATUS current
    DESCRIPTION
        "Writing none(1) to this object indicates to use the local system time.
        When the value is set to none(1), ibSysClockProtocolSrcMdc and
        ibSysClockProtocolSrcContext cannot be written and the value will be
        set to invalid.  Change system time will be performed through the node
        of ibSysLocalClock and ibSysSummerTime.
        Writing ntp(2) to this object indicates to use NTP time source.
        NTP means Network Time Protocol.  To get the system time through NTP,
        NTP must be configured successfully.  NTP time source can be obtained
        from non-default MDC and non-default context.
        When ntp(2) is set, the system time can't be changed manually.
        Support for this keyword depends on the device model.

        Writing ptp(3) to this object indicates to use PTP time source.
        PTP means Precision Time Protocol.  To get clock time through PTP, PTP
        must be configured successfully.  PTP time source can be obtained from
        non-default MDC but cannot be obtained from non-default context.
        When ptp(3) is set, the system time can't be changed manually.
        Support for this keyword depends on the device model.

        Writing interface(4) to this object indicates to get time source from interface.
        To get clock time through interface, interface must be configured successfully.
        When interface(4) is set, the system time can't be changed manually.
        Support for this keyword depends on the device model.

        Writing gnss(5) to this object indicates to get time source from Global
        Natvigtion Satelite System(GNSS).GNSS time source can be obtained from
        non-default MDC and non-default context. When gnss(5) is set, the system time
        can't be changed manually.
        Support for this keyword depends on the device model.

        All MDCs on the device share the same time source and use the same system time.
        The shared time source can be one of the following items:
        Local system time - the time signal that is generated by the local
        crystal oscillator
        Remote time source - the time signal that is obtained by the specified MDC
        from another device on the network."
    ::= { ibSysClockProtocolGroup 1 }

ibSysClockProtocolSrcMdc OBJECT-TYPE
    SYNTAX Integer32 (0..2147483647)
    MAX-ACCESS read-write
    STATUS current
    DESCRIPTION
        "The MDC ID that is used for the system time source.
        This node is valid when the clock protocol is NTP or PTP.
        If MDC is not supported on this system, this node is invalid.
        If the device supports MDC, the system time will be obtained
        from NTP or PTP on the specified MDC.
        If the device supports context and MDC, the most recent configuration of
        ibSysClockProtocolSrcContext and ibSysClockProtocolSrcMdc takes
        effect if set multiple times, and another one will be set to zero as an
        invalid value."
     DEFVAL { 1 }
    ::= { ibSysClockProtocolGroup 2 }

ibSysClockProtocolSrcContext OBJECT-TYPE
    SYNTAX Integer32 (0..2147483647)
    MAX-ACCESS read-write
    STATUS current
    DESCRIPTION
        "The context ID that is used for the system time source.
        This node is valid when the clock protocol is NTP or PTP.
        If context is not supported on this system, this node is invalid.
        If the system supports context, the system time will be obtained from
        NTP or PTP on the specified context.
        If the device supports context and MDC, the most recent configuration of
        ibSysClockProtocolSrcContext and ibSysClockProtocolSrcMdc takes
        effect if set multiple times, and another one will be set to zero as an
        invalid value."
    DEFVAL { 1 }
    ::= { ibSysClockProtocolGroup 3 }

ibSysCurrent OBJECT IDENTIFIER ::= { ibSystemManMIBObjects 2 }

ibSysCurTable OBJECT-TYPE
    SYNTAX SEQUENCE OF IbSysCurEntry
    MAX-ACCESS not-accessible
    STATUS current
    DESCRIPTION
        "
        The current status of system. A configuration file, an image
        file and bootrom information are used to describe the current status.
        "
    ::= { ibSysCurrent 1 }

ibSysCurEntry OBJECT-TYPE
    SYNTAX IbSysCurEntry
    MAX-ACCESS not-accessible
    STATUS current
    DESCRIPTION
        "
        An entry of ibSysCurTable.
        "
    INDEX { ibSysCurEntPhysicalIndex }
    ::= { ibSysCurTable 1 }

IbSysCurEntry ::=
    SEQUENCE {
        ibSysCurEntPhysicalIndex       Integer32,
        ibSysCurCFGFileIndex           Integer32,
        ibSysCurImageIndex             Integer32,
        ibSysCurBtmFileName            OCTET STRING,
        ibSysCurUpdateBtmFileName      OCTET STRING
     }

ibSysCurEntPhysicalIndex OBJECT-TYPE
    SYNTAX Integer32 (0..2147483647)
    MAX-ACCESS not-accessible
    STATUS current
    DESCRIPTION
        "The value of this object is the entity index
         which depends on the implementation of ENTITY-MIB.
         If ENTITY-MIB is not supported, the value for this object is the unit ID for XRN devices ,
         0 for non-XRN device which has only one mainboard,
         the board number for non-XRN device which have several mainboards.
        "
    ::= { ibSysCurEntry 1 }

ibSysCurCFGFileIndex OBJECT-TYPE
    SYNTAX Integer32 (0..2147483647)
    MAX-ACCESS read-only
    STATUS current
    DESCRIPTION
        "
        The startup configuration file currently used by the specified entity.
        If the value of it is zero, no configuration file is used. It will be
        the value of corresponding ibSysCFGFileIndex in ibSysCFGFileTable.
        "
    ::= { ibSysCurEntry 2 }

ibSysCurImageIndex OBJECT-TYPE
    SYNTAX Integer32 (0..2147483647)
    MAX-ACCESS read-only
    STATUS current
    DESCRIPTION
        "The image file currently used by the specified entity.
        It will be the value of corresponding ibSysImageIndex
        in ibSysImageTable."
    ::= { ibSysCurEntry 3 }

ibSysCurBtmFileName OBJECT-TYPE
    SYNTAX OCTET STRING(SIZE (1..64))
    MAX-ACCESS read-only
    STATUS current
    DESCRIPTION
        "The bootrom file currently used by the specified entity."
    ::= { ibSysCurEntry 4 }

ibSysCurUpdateBtmFileName OBJECT-TYPE
    SYNTAX OCTET STRING(SIZE (1..64))
    MAX-ACCESS read-only
    STATUS current
    DESCRIPTION
        "
        The default value of this object is the same as the value of
        ibSysCurBtmFileName. The value will be changed after updating
        the bootrom successfully. This bootrom will take effect on next
        startup.
        "
    ::= { ibSysCurEntry 5 }

-- Begin define reload group
ibSysReload OBJECT IDENTIFIER ::= { ibSystemManMIBObjects 3 }

ibSysReloadSchedule OBJECT-TYPE
    SYNTAX Integer32 (0..2147483647)
    MAX-ACCESS read-write
    STATUS current
    DESCRIPTION
        "
        The object points one row in ibSysReloadScheduleTable.
        Its value is equal to the value of ibSysReloadScheduleIndex.
        When a reload action is finished, the value of it
        would be zero which means no any reload schedule is selected.
        "
    ::= { ibSysReload 1 }

ibSysReloadAction OBJECT-TYPE
    SYNTAX INTEGER
        {
        reloadUnavailable(1),
        reloadOnSchedule(2),
        reloadAtOnce(3),
        reloadCancel(4)
        }
    MAX-ACCESS read-write
    STATUS current
    DESCRIPTION
        "
        Writing reloadOnSchedule(2) to this object performs the reload operation on schedule.
        If ibSysReloadScheduleTime is not set, the value of ibSysReloadAction can't be set to
        'reloadOnSchedule(2)'.

        Writing reloadAtOnce(3)to this object performs the reload operation at once,
        regardless of the ibSysReloadScheduleTime.

        When reloadCancel(4)is set, the scheduled reload action will be cancelled and the value of
        ibSysReloadAction will be 'reloadUnavailable(1)',the value of ibSysReloadSchedule will be
        0, ibSysReloadTag will be given a value of zero length, but the content of
        ibSysReloadScheduleTable will remain.


        The ibSysReloadSchedule and ibSysReloadTag  determine the reload entity(ies) in mutually
        exclusive way. And the ibSysReloadSchedule will be handled at first. If the value of
        ibSysReloadSchedule is invalid, then the ibSysReloadTag will be handled.

        If the value of ibSysReloadSchedule is valid, the value of ibSysReloadTag is ignored and a
        reload action will be implemented to the entity specified by ibSysReloadEntity in the entry
        pointed by ibSysReloadSchedule.

        If ibSysReloadSchedule is valid, but the entry ibSysReloadSchedule pointing to is not active,
        the reload action will be ignored , and an inconsistent value will be returned.


        If multiple entities are required to be reloaded at the same time, the value of ibSysReloadTag
        must be specified to select the reload parameters in the ibSysReloadSceduelTable, and
        ibSysReloadSchedule must have the value of '0'.

        If the whole fabric is to be reloaded in an XRN device, all the units in the fabric must
        have at least one entry in the ibSysReloadSceduelTable with the same tag in ibSysReloadSceduelTagList.

        When a reload action is done, or there is no reload action, the value
        should be reloadUnavailable(1).
        "
    ::= { ibSysReload 2 }

ibSysReloadScheduleTable OBJECT-TYPE
    SYNTAX SEQUENCE OF IbSysReloadScheduleEntry
    MAX-ACCESS not-accessible
    STATUS current
    DESCRIPTION
        "
        A reload parameters set table.

        The table is exclusively used for reloading.

        When reloading action finished, the value of the table may be empty or still exist.
        If the mainboard in non-XRN device or all the units of the fabric in XRN device are
        reloaded,then the table will be refreshed.
        "
    ::= { ibSysReload 3 }

ibSysReloadScheduleEntry OBJECT-TYPE
    SYNTAX IbSysReloadScheduleEntry
    MAX-ACCESS not-accessible
    STATUS current
    DESCRIPTION
        "Entry of ibSysReloadScheduleTable."
    INDEX { ibSysReloadScheduleIndex }
    ::= { ibSysReloadScheduleTable 1 }

IbSysReloadScheduleEntry ::=
    SEQUENCE {
        ibSysReloadScheduleIndex           Integer32,
        ibSysReloadEntity                  Integer32,
        ibSysReloadCfgFile                 Integer32,
        ibSysReloadImage                   Integer32,
        ibSysReloadReason                  DisplayString,
        ibSysReloadScheduleTime            DateAndTime,
        ibSysReloadRowStatus               RowStatus,
        ibSysReloadScheduleTagList         SnmpTagList
     }

ibSysReloadScheduleIndex OBJECT-TYPE
    SYNTAX Integer32 (1..2147483647)
    MAX-ACCESS not-accessible
    STATUS current
    DESCRIPTION
        "The index of ibSysReloadScheduleTable. There are two parts
        for this index depicted as follows:

        31                  15                  0
        +++++++++++++++++++++++++++++++++++++++++
        + physical index     +     random index +
        ( bit 16..31 )              ( bit 0..15 )
        +++++++++++++++++++++++++++++++++++++++++
        From bit0 to bit15 (two bytes), if the row is automatic created,
        the value is zero, and if the row is created by users, then the
        value is determined by the users.

        From bit16 to bit31 (two bytes) is the physical index the same as the
        entPhysicalIndex specified in ENTITY-MIB. For XRN devices,
        physical index is the value of a chassis entPhysicalIndex. 0 for non-XRN
        device which has only one main board, the board number for non-XRN device
        which have multiple main boards."
    ::= { ibSysReloadScheduleEntry 1 }

ibSysReloadEntity OBJECT-TYPE
    SYNTAX Integer32 (0..2147483647)
    MAX-ACCESS read-create
    STATUS current
    DESCRIPTION
        "
        The value of ibSysReloadEntity indicates an entry in entPhysicalTable,
        which is the physical entity to be reloaded.

        If ENTITY-MIB is not supported,the value for this object is the unit ID for XRN devices ,
        0 for non-XRN device which has only one mainboard,
        the board number for non-XRN device which have several mainboards.

        Each entity has only one row in ibSysReloadScheduleTable.
        "
    ::= { ibSysReloadScheduleEntry 2 }

ibSysReloadCfgFile OBJECT-TYPE
    SYNTAX Integer32 (0..2147483647)
    MAX-ACCESS read-create
    STATUS current
    DESCRIPTION
        "
        The value indicates an entry in ibSysCFGFileTable.
        It defines a configuration file for reload action.
        It is the value of corresponding ibSysCFGFileIndex in ibSysCFGFileTable.
        The zero value means no configuration file has been set for this entry, and
        no configuration file is used during system reloading.
        "
    ::= { ibSysReloadScheduleEntry 3 }

ibSysReloadImage OBJECT-TYPE
    SYNTAX Integer32 (0..2147483647)
    MAX-ACCESS read-create
    STATUS current
    DESCRIPTION
        "
        The value indicates an entry in ibSysImageTable.
        It defines an image file for reload action.
        It is the value of corresponding ibSysImageIndex in ibSysImageTable.

        If dual image is supported, the main image attribute can be
        set through this object or by ibSysImageType of ibSysImageTable
        of the entity. It is strongly suggested to set this attribute by
        the latter.

        If main image attribute is set here, the ibSysImageType in ibSysImageTable
        of the corresponding entity will be updated, and vice versa.

        Before reboot, the device will check the validation of the entry. If the file does
        not exist, the device will not reboot and a trap will be send to NMS.
        "
    ::= { ibSysReloadScheduleEntry 4 }

ibSysReloadReason OBJECT-TYPE
    SYNTAX DisplayString (SIZE (0..255))
    MAX-ACCESS read-create
    STATUS current
    DESCRIPTION
        "
        The reason of system's reloading.
        It is a zero length octet string when not set.
        "
    ::= { ibSysReloadScheduleEntry 5 }

ibSysReloadScheduleTime OBJECT-TYPE
    SYNTAX DateAndTime (SIZE(8))
    MAX-ACCESS read-create
    STATUS current
    DESCRIPTION
        "
        Specify the local time at which the reload action will
        occur. we will only take octet strings
        with length 8 for this object which indicates the
        local time of the switch. The maximum scheduled
        interval between the specified time and the current
        system clock time is 24 days .

            field  octets  contents                  range
            -----  ------  --------                  -----
              1      1-2   year                      0..65536
              2       3    month                     1..12
              3       4    day                       1..31
              4       5    hour                      0..23
              5       6    minutes                   0..59
              6       7    seconds                   0..60

         For example, Tuesday May 26, 1992 at 1:30:15 PM would be
         displayed as:

                    1992-5-26,13:30:15

        If the set value is less than the value of ibSysLocalClock
        or beyond the maximum scheduled time limit, a bad value error
        occurred.
        The value of all-zero octet strings indicates system reload
        at once if the reload action is reloadOnSchedule(2).
        "
    ::= { ibSysReloadScheduleEntry 6 }

ibSysReloadRowStatus OBJECT-TYPE
    SYNTAX RowStatus
    MAX-ACCESS read-create
    STATUS current
    DESCRIPTION
        "
        If one of the value of ibSysReloadEntity,ibSysReloadImage
        is invalid, the value of ibSysReloadRowStatus can not be set to the value
        of ACTIVE.

        A valid entry means the specified element is available in current system.
        "
    ::= { ibSysReloadScheduleEntry 7 }

ibSysReloadScheduleTagList OBJECT-TYPE
    SYNTAX SnmpTagList
    MAX-ACCESS read-create
    STATUS current
    DESCRIPTION
    "
    It specifies a tag list for the entry.
    "
    ::= { ibSysReloadScheduleEntry 8 }

ibSysReloadTag OBJECT-TYPE
    SYNTAX SnmpTagValue
    MAX-ACCESS read-write
    STATUS current
    DESCRIPTION
        "This object contains a single tag value which is used
        to select entries in the ibSysReloadScheduleTable.

        In the ibSysReloadScheduleTable,any entry that contains
        a tag value which is equal to the value of this object is
        selected.

        For example, the value of ibSysReloadTag is 'TOM',and the
        ibSysReloadScheduleTagList of each ibSysReloadScheduleTable
        entry are as follows:
        1)'TOM,ROBERT,MARY'
        2)'TOM,DAVE'
        3)'DAVE,MARY'
        Since there are 'TOM' in 1) and 2),so 1) and 2) are selected.


        If this object contains a value of zero length, no entries
        are selected.
        "
    ::= { ibSysReload 4 }
-- End define reload group
ibSysImage OBJECT IDENTIFIER ::= { ibSystemManMIBObjects 4 }

ibSysImageNum OBJECT-TYPE
    SYNTAX Integer32 (0..2147483647)
    MAX-ACCESS read-only
    STATUS current
    DESCRIPTION
        "
        The number of system images. It indicates the
        total entries of ibSysImageTable.
        "
    ::= { ibSysImage 1 }

ibSysImageTable OBJECT-TYPE
    SYNTAX SEQUENCE OF IbSysImageEntry
    MAX-ACCESS not-accessible
    STATUS current
    DESCRIPTION
        "The system image management table.


        When 'copy srcfile destfile' is executed via the CLI, if destfile is not existed,
        then ibSysImageType of the new file will be 'none'; otherwise ibSysImageType keeps its current value.
        When 'move srcfile destfile' is executed via the CLI, ibSysImageType and ibSysImageIndex
         remain the same while ibSysImageLocation changes.
        When 'rename srcfile' is executed via the CLI,ibSysImageType and ibSysImageIndex remain the same
        while ibSysImageName changes.
        When 'delete srcfile' is executed via the CLI, the file is deleted from ibSysImageTable
        while index of the file keeps and will not be allocated.
        "
    ::= { ibSysImage 2 }

ibSysImageEntry OBJECT-TYPE
    SYNTAX IbSysImageEntry
    MAX-ACCESS not-accessible
    STATUS current
    DESCRIPTION
        "
        An entity image entry. Each entry consists of information of an entity image.
        The ibSysImageIndex exclusively defines an image file.
        "
    INDEX { ibSysImageIndex }
    ::= { ibSysImageTable 1 }

IbSysImageEntry ::=
    SEQUENCE {
        ibSysImageIndex            Integer32,
        ibSysImageName             DisplayString,
        ibSysImageSize             Integer32,
        ibSysImageLocation         DisplayString,
        ibSysImageType             INTEGER
     }

ibSysImageIndex OBJECT-TYPE
    SYNTAX Integer32 (0..2147483647)
    MAX-ACCESS not-accessible
    STATUS current
    DESCRIPTION
        "There are two parts for the index depicted as follows:

        31                15             0
        +++++++++++++++++++++++++++++++++++
        + physical index   +  image index +
        +++++++++++++++++++++++++++++++++++

        From bit0 to bit15 (two bytes) is the image index;Image file Index
        is a monotonically increasing integer for the sole purpose of indexing
        events.  When it reaches the maximum value, an extremely unlikely event,
        the agent wraps the value back to 1 and may flush existing entries.

        From bit16 to bit31 (two bytes) is the physical index the same as the
        entPhysicalIndex specified in ENTITY-MIB.
        If ENTITY-MIB is not supported,the value for this object is the unit ID for XRN
        devices ,0 for non-XRN device which has only one main board,the board number for
        non-XRN device which have several main boards.


        Any index beyond the above range will not be supported.

        If a file is added in, its ibSysImageIndex will be the maximum image index plus one.
                        If the image file is removed, renamed, or moved from one place to another,
                        its ibSysImageIndex is not reallocated.
                        If the image file's content is replaced, its ibSysImageIndex will not change.

        "
    ::= { ibSysImageEntry 1 }

ibSysImageName OBJECT-TYPE
    SYNTAX DisplayString (SIZE (0..255))
    MAX-ACCESS read-only
    STATUS current
    DESCRIPTION
        "The file name of the image. It MUST NOT contain the path of the file."
    ::= { ibSysImageEntry 2 }

ibSysImageSize OBJECT-TYPE
    SYNTAX Integer32 (1..2147483647)
    MAX-ACCESS read-only
    STATUS current
    DESCRIPTION
        "
        Size of the file in bytes.
        "
    ::= { ibSysImageEntry 3 }

ibSysImageLocation OBJECT-TYPE
    SYNTAX DisplayString (SIZE (0..255))
    MAX-ACCESS read-only
    STATUS current
    DESCRIPTION
        "
        The directory path of the image.
        Its form should be the same as what defined in file system.
        Currently it is defined as follows:
        For mainboard:   flash:/
        For slave mainboard and subboards: slotN#flash:/
        For XRN devices: unitN>slotN#flash:/
        "
    ::= { ibSysImageEntry 4 }

ibSysImageType OBJECT-TYPE
    SYNTAX INTEGER
        {
        main(1),
        backup(2),
        none(3),
        secure(4),
        main-backup(5),
        main-secure(6),
        backup-secure(7),
        main-backup-secure(8)
        }
    MAX-ACCESS read-write
    STATUS current
    DESCRIPTION
        "
        It indicates the reloading sequence attribute of the image.

        For devices which support dual image:

        If the value is 'main(1)',the image will be the first image
        in the next reloading procedure. If the value is 'backup(2)',
        the image will be used if the main image fails. If the value
        is 'secure(4)', the image will be used if the main image and
        backup image both fail. If the value is 'none(3)',the image will
        not be used in the next reloading procedure.

        At the same time,you also can specify the main image by
        ibSysReloadImage in ibSysReloadScheduleTable. If the
        image is different from previous main image, the previous main image
        will not be main image again. And the image table will update with
        this variation. Vice versa, if you have defined the reload schedule,
        and then you define a new main image through ibSysImageType when you
        are waiting the reload schedule to be executed, the real main image
        will be the latest one.


        It is strongly suggested to define the main image here, not by ibSysReloadImage
        in ibSysReloadScheduleTable.

        There are some rules for setting the value of ibSysImageType:

        a)When a new image file is defined as 'main' or 'backup' file,the ibSysImageType
          of old 'main' or 'backup' file will automatically be 'none'.
        b)It is forbidden to set 'none' attribute manually.
        c)It is forbidden to set 'secure' attribute manually.
        d)If 'main' image is set to 'backup', the file keeps 'main'. And vice versa.
          At this time, the file has 'main-backup' property.
        e)If the secure image is set to 'main' or 'backup', the file has 'main-secure' or 'backup-secure'property.
        f)If the secure image is set to 'main' and 'backup', the file has the 'main-backup-secure' property.
        g)If the none image is set to 'main' or 'backup', the file has the 'main' or 'backup' property.

        The following table describes whether it is ok to set to another state
        directly from original state.

                        +--------------+-----------+-------------+-------------+
                        |   set to     | set to    |  set to     |   set to    |
                        |              |           |             |             |
             original   |    'main'    | 'backup'  |  'none'     |  'secure'   |
             state      |              |           |             |             |
          --------------+--------------+-----------+-------------+-------------+
                        |              |           |             |             |
             main       |     ---      |   yes     |   no        |   no        |
                        |              |           |             |             |
                        |              |           |             |             |
          --------------+--------------+-----------+-------------|-------------+
                        |              |           |             |             |
             backup     |     yes      |   ---     |   no        |   no        |
                        |              |           |             |             |
          --------------+--------------+-----------+-------------|-------------+
                        |              |           |             |             |
                        |              |           |             |             |
              none      |     yes      |   yes     |   ---       |   no        |
                        |              |           |             |             |
          --------------+--------------+-----------+-------------+-------------+
                        |              |           |             |             |
              secure    |     yes      |   yes     |   no        |   ---       |
                        |              |           |             |             |
                        |              |           |             |             |
          --------------+--------------+-----------+-------------+-------------+

        If there is one main image in the system, one row of IbSysReloadScheduleEntry
        whose  ibSysReloadImage is equal to the main image's ibSysImageIndex will be
        created automatically. But if any row is deleted, it will not be created
        automatically in ibSysReloadScheduleTable.




        For the device which doesn't support dual image(main/backup):

        Only 'main' and 'none' is supported and it only can be set from none to main.
        When a new image file is defined as 'main' file,the ibSysImageType of old 'main'
        file will automatically be 'none'.
        "
    ::= { ibSysImageEntry 5 }

-- End define sysImage group

ibSysCFGFile OBJECT IDENTIFIER ::= { ibSystemManMIBObjects 5 }

ibSysCFGFileNum OBJECT-TYPE
    SYNTAX Integer32 (0..2147483647)
    MAX-ACCESS read-only
    STATUS current
    DESCRIPTION
        "
        The number of the configuration files in the system. It indicates the
        total entries of ibSysCFGFileTable.
        "
    ::= { ibSysCFGFile 1 }

ibSysCFGFileTable OBJECT-TYPE
    SYNTAX SEQUENCE OF IbSysCFGFileEntry
    MAX-ACCESS not-accessible
    STATUS current
    DESCRIPTION
        "A table of configuration files in this system.
         At present, the system doesn't support dual configure file,
         it should act as 'dual image' if dual configure file is
         supported.
        "
    ::= { ibSysCFGFile 2 }

ibSysCFGFileEntry OBJECT-TYPE
    SYNTAX IbSysCFGFileEntry
    MAX-ACCESS not-accessible
    STATUS current
    DESCRIPTION
        "
        A configuration file entry. Each entry consists of information of
        a configuration file.
        ibSysCFGFileIndex exclusively decides a configuration file.
        "
    INDEX { ibSysCFGFileIndex }
    ::= { ibSysCFGFileTable 1 }

IbSysCFGFileEntry ::=
    SEQUENCE {
        ibSysCFGFileIndex          Integer32,
        ibSysCFGFileName           DisplayString,
        ibSysCFGFileSize           Integer32,
        ibSysCFGFileLocation       DisplayString
     }

ibSysCFGFileIndex OBJECT-TYPE
    SYNTAX Integer32 (0..2147483647)
    MAX-ACCESS not-accessible
    STATUS current
    DESCRIPTION
       "There are two parts for the index depicted as follows:

        31                15             0
        +++++++++++++++++++++++++++++++++++
        + physical index  + cfgFile index +
        +++++++++++++++++++++++++++++++++++

        From bit0 to bit15 (two bytes) is the configuration file index; the
        configuration file index is a monotonically increasing integer for
        the sole purpose of indexing events. When it reaches the maximum
        value, an extremely unlikely event, the agent wraps the value back
        to 1 and may flush existing entries.

        From bit16 to bit31 (two bytes) is the physical index the same
        as the entPhysicalIndex specified in ENTITY-MIB.
        If ENTITY-MIB is not supported, the value for this object is the unit ID for XRN
        devices ,0 for non-XRN device which has only one slot,the board number for
        non-XRN device which have several slots.

        Any index beyond the above range will not be supported.
        "
    ::= { ibSysCFGFileEntry 1 }

ibSysCFGFileName OBJECT-TYPE
    SYNTAX DisplayString (SIZE (0..255))
    MAX-ACCESS read-only
    STATUS current
    DESCRIPTION
        "
        Configuration file name. The name should not include the colon (:)
        character as it is a special separator character used
        to delineate the device name, partition name and the
        file name.
        "
    ::= { ibSysCFGFileEntry 2 }

ibSysCFGFileSize OBJECT-TYPE
    SYNTAX Integer32 (1..2147483647)
    MAX-ACCESS read-only
    STATUS current
    DESCRIPTION
        "
        Size of the file in bytes. Note that it does
        not include the size of the filesystem file header.
        File size will always be non-zero.
        "
    ::= { ibSysCFGFileEntry 3 }

ibSysCFGFileLocation OBJECT-TYPE
    SYNTAX DisplayString (SIZE (0..255))
    MAX-ACCESS read-only
    STATUS current
    DESCRIPTION
        "
        The directory path of the image.
        Its form should be the same as what defined in filesystem.
        Currently it is defined as follows:
        For mainboard:   flash:/
        For slave mainboard and subboards: slotN#flash:/
        For XRN devices: unitN>slotN#flash:/
        "
    ::= { ibSysCFGFileEntry 4 }
-- End define CFGFile group

-- Begin define bootrom group
ibSysBtmFile OBJECT IDENTIFIER ::= { ibSystemManMIBObjects 6 }

ibSysBtmFileLoad OBJECT IDENTIFIER ::= { ibSysBtmFile 1 }

ibSysBtmLoadMaxNumber OBJECT-TYPE
    SYNTAX Integer32
    MAX-ACCESS read-only
    STATUS current
    DESCRIPTION
        "
        This object shows the maximum number of ibSysBtmLoadEntry in
        each device/unit.
        "
    ::= { ibSysBtmFileLoad 1 }

ibSysBtmLoadTable OBJECT-TYPE
    SYNTAX SEQUENCE OF IbSysBtmLoadEntry
    MAX-ACCESS not-accessible
    STATUS current
    DESCRIPTION
        "
        This table is used to update the bootrom and show the results of
        the update operation.
        The bootrom files are listed at the ibFlhFileTable.  These files
        are used to update bootrom.
        "
    ::= { ibSysBtmFile 2 }

ibSysBtmLoadEntry OBJECT-TYPE
    SYNTAX IbSysBtmLoadEntry
    MAX-ACCESS not-accessible
    STATUS current
    DESCRIPTION
        "
        Entries in the ibSysBtmLoadTable are created and deleted using
        the ibSysBtmRowStatus object.

        When a new row is being created and the number of entries is
        ibSysBtmLoadMaxNumber, the row with minimal value of
        ibSysBtmLoadTime and the value of ibSysBtmFileType is none(2),
        should be destroyed automatically.
        "
    INDEX { ibSysBtmLoadIndex }
    ::= { ibSysBtmLoadTable 1 }

IbSysBtmLoadEntry ::=
    SEQUENCE {
        ibSysBtmLoadIndex          Integer32,
        ibSysBtmFileName           OCTET STRING,
        ibSysBtmFileType           INTEGER,
        ibSysBtmRowStatus          RowStatus,
        ibSysBtmErrorStatus        INTEGER,
        ibSysBtmLoadTime           TimeTicks
     }

ibSysBtmLoadIndex OBJECT-TYPE
    SYNTAX Integer32 (1..2147483647)
    MAX-ACCESS not-accessible
    STATUS current
    DESCRIPTION
        "
        The index of ibSysBtmLoadTable. There are two parts for this
        index depicted as follows:

        31                  15                  0
        +++++++++++++++++++++++++++++++++++++++++
        + physical index     +     random index +
        ( bit 16..31 )              ( bit 0..15 )
        +++++++++++++++++++++++++++++++++++++++++

        From bit0 to bit15 (two bytes), if the row is created by command
        line, the value is determined by system, and if the row is created
        by SNMP, the value is determined by users.

        From bit16 to bit31 (two bytes) is the physical index the same as
        the entPhysicalIndex specified in ENTITY-MIB.

        If ENTITY-MIB is not supported, the value of this object is the
        unit ID for XRN devices, 0 for non-XRN device which has only one
        main board, the board number for non-XRN device which has multiple
        main boards.
       "
    ::= { ibSysBtmLoadEntry 1 }

ibSysBtmFileName OBJECT-TYPE
    SYNTAX OCTET STRING(SIZE (1..64))
    MAX-ACCESS read-create
    STATUS current
    DESCRIPTION
        "
        The bootrom file name is determined by the users.  The file must
        exist in corresponding entity.

        The validity of the bootrom file will be identified by system.
        If the file is invalid, the bootrom should fail to be updated,
        and the value of ibSysBtmErrorStatus should be failed(4).
        "
    ::= { ibSysBtmLoadEntry 2 }

ibSysBtmFileType OBJECT-TYPE
    SYNTAX INTEGER
       {
       main(1),
       none(2)
       }
    MAX-ACCESS read-create
    STATUS current
    DESCRIPTION
        "
        main(1) - The effective bootrom file.
        none(2) - The noneffective file.

        When bootrom is being updated, this object must be set to main(1).

        When bootrom is updated successfully, this object should be
        main(1), and the former object with the same physical index should
        be none(2).

        When bootrom failed to be updated, this object should be none(2).
        "
    ::= { ibSysBtmLoadEntry 3 }

ibSysBtmRowStatus OBJECT-TYPE
    SYNTAX RowStatus
    MAX-ACCESS read-create
    STATUS current
    DESCRIPTION
        "
        Only support active(1), createAndGo(4), destroy(6).  When a row
        is created successfully, the value of this object should be active(1),
        the value of ibSysBtmFileName and ibSysBtmFileType can not be
        modified by users.

        When bootrom is being updated, the value of ibSysBtmErrorStatus
        is inProgress(2).

        When bootrom failed to be updated, the value of ibSysBtmErrorStatus
        should be failed(4).

        When bootrom is updated successfully, the value of ibSysBtmErrorStatus
        should be success(3).  The value of ibSysCurUpdateBtmFileName
        should change to the new bootrom file name.

        When another row is created successfully with the same physical
        index, and the update is successful, then the value of former
        ibSysBtmFileType should be none(2) automatically.

        If a row is destroyed, ibSysCurUpdateBtmFileName should not change.

        If a device/unit reboots, ibSysBtmLoadTable should be empty.
        "
    ::= { ibSysBtmLoadEntry 4 }

ibSysBtmErrorStatus OBJECT-TYPE
    SYNTAX INTEGER
       {
       invalidFile(1),
       inProgress(2),
       success(3),
       failed(4)
       }
    MAX-ACCESS read-only
    STATUS current
    DESCRIPTION
        "
        This object shows the status of the specified operation after
        creating a row.
        invalidFile(1) - file is invalid.
        inProgress(2)  - the operation is in progress.
        success(3)     - the operation was done successfully.
        failed(4)      - the operation failed.
        "
    ::= { ibSysBtmLoadEntry 5 }

ibSysBtmLoadTime OBJECT-TYPE
    SYNTAX TimeTicks
    MAX-ACCESS read-only
    STATUS current
    DESCRIPTION
        "
        This object indicates operation time.
        "
    ::= { ibSysBtmLoadEntry 6 }

-- End define Bootrom group

ibSysPackage OBJECT IDENTIFIER ::= { ibSystemManMIBObjects 7 }

ibSysPackageNum OBJECT-TYPE
    SYNTAX Integer32 (0..2147483647)
    MAX-ACCESS read-only
    STATUS current
    DESCRIPTION
        "
        The number of software packages.  It indicates the
        total entries of ibSysPackageTable.
        "
    ::= { ibSysPackage 1 }

ibSysPackageTable OBJECT-TYPE
    SYNTAX SEQUENCE OF IbSysPackageEntry
    MAX-ACCESS not-accessible
    STATUS current
    DESCRIPTION
        "The system package management table.
        "
    ::= { ibSysPackage 2 }

ibSysPackageEntry OBJECT-TYPE
    SYNTAX IbSysPackageEntry
    MAX-ACCESS not-accessible
    STATUS current
    DESCRIPTION
        "
        An software package entry.  Each entry consists of information of
        an software package.
        "
    INDEX { ibSysPackageIndex }
    ::= { ibSysPackageTable 1 }

IbSysPackageEntry ::=
    SEQUENCE {
        ibSysPackageIndex            Integer32,
        ibSysPackageName             DisplayString,
        ibSysPackageSize             Unsigned32,
        ibSysPackageLocation         DisplayString,
        ibSysPackageType             INTEGER,
        ibSysPackageAttribute        INTEGER,
        ibSysPackageStatus           INTEGER,
        ibSysPackageDescription      DisplayString,
        ibSysPackageFeature          DisplayString,
        ibSysPackageVersion          DisplayString,
        ibSysPackageLoadAttribute    INTEGER,
        ibSysPackageModel            DisplayString
    }

ibSysPackageIndex OBJECT-TYPE
    SYNTAX Integer32 (1..2147483647)
    MAX-ACCESS not-accessible
    STATUS current
    DESCRIPTION
        "There are two parts for the index depicted as follows:

        31                15             0
        +++++++++++++++++++++++++++++++++++
        + physical index   +  package index +
        +++++++++++++++++++++++++++++++++++

        From bit0 to bit15 (two bytes) is the Package index; Package file Index
        is a monotonically increasing integer for the sole purpose of indexing
        events.  When it reaches the maximum value, an extremely unlikely
        event, the agent wraps the value back to 1 and may flush existing
        entries.

        From bit16 to bit31 (two bytes) is the physical index the same as the
        entPhysicalIndex specified in ENTITY-MIB.

        Any index beyond the above range will not be supported.

        If a file is added in, its ibSysPackageIndex will be the maximum
        image index plus one.
        If the package file is removed, renamed, or moved from one place to
        another, its ibSysPackageIndex is not reallocated.
        If the package file's content is replaced, its ibSysPackageIndex will
        not change.
        "
    ::= { ibSysPackageEntry 1 }

ibSysPackageName OBJECT-TYPE
    SYNTAX DisplayString (SIZE (0..255))
    MAX-ACCESS read-only
    STATUS current
    DESCRIPTION
        "
        The file name of the package.  It MUST NOT contain the path
        of the file.
        "
    ::= { ibSysPackageEntry 2 }

ibSysPackageSize OBJECT-TYPE
    SYNTAX Unsigned32 (1..4294967295)
    MAX-ACCESS read-only
    STATUS current
    DESCRIPTION
        "
        Size of the file in bytes.
        "
    ::= { ibSysPackageEntry 3 }

ibSysPackageLocation OBJECT-TYPE
    SYNTAX DisplayString (SIZE (0..255))
    MAX-ACCESS read-only
    STATUS current
    DESCRIPTION
        "
        The directory path of the package.
        Its form should be the same as what defined in file system.
        Currently it is defined as follows:
        For mainboard:   flash:/
        For slave mainboard and subboards: slotN#flash:/
        "
    ::= { ibSysPackageEntry 4 }

ibSysPackageType OBJECT-TYPE
    SYNTAX INTEGER
        {
        boot(1),
        system(2),
        feature(3),
        patch(4)
        }
    MAX-ACCESS read-only
    STATUS current
    DESCRIPTION
        "
        It indicates the type of the package file.
        boot    :  kernel, file system, memory management and other
                   core components.
        system  :  interface management, configuration management and other
                   basic system package.
        feature :  feature packages, providing different services.
        patch   :  patch file contains fixes for a specific defect.
        "
    ::= { ibSysPackageEntry 5 }

ibSysPackageAttribute OBJECT-TYPE
    SYNTAX INTEGER
        {
        none(1),
        primary(2),
        secondary(3),
        primarySecondary(4)
        }
    MAX-ACCESS read-write
    STATUS current
    DESCRIPTION
        "
        It indicates the attribute of the package file.
        If the value is 'primary', the package will be the first package
        in the next reloading procedure.  If the value is 'secondary',
        the package will be used if the primary package fails.
        If the value is 'none', it will not be used in the next reloading
        procedure.
        "
    ::= { ibSysPackageEntry 6 }

ibSysPackageStatus OBJECT-TYPE
    SYNTAX INTEGER
        {
        active(1),
        inactive(2)
        }
    MAX-ACCESS read-only
    STATUS current
    DESCRIPTION
    "
    It indicates the status of the package file.  If this file is used in the
    current system, its status is 'active'.
    "
    ::= { ibSysPackageEntry 7 }

ibSysPackageDescription OBJECT-TYPE
    SYNTAX DisplayString (SIZE (0..255))
    MAX-ACCESS read-only
    STATUS current
    DESCRIPTION
    "
    It is the description of the package.
    "
    ::= { ibSysPackageEntry 8 }

ibSysPackageFeature OBJECT-TYPE
    SYNTAX DisplayString (SIZE (0..255))
    MAX-ACCESS read-only
    STATUS current
    DESCRIPTION
    "
    Indicate the feature of the package.  Different package files
    could be the same feature.
    "
    ::= { ibSysPackageEntry 9 }

ibSysPackageVersion OBJECT-TYPE
    SYNTAX DisplayString (SIZE (0..255))
    MAX-ACCESS read-only
    STATUS current
    DESCRIPTION
    "
    Indicate the version of the package.
    "
    ::= { ibSysPackageEntry 10 }

ibSysPackageLoadAttribute OBJECT-TYPE
    SYNTAX INTEGER
    {
        none(1),
        primary(2),
        secondary(3),
        primarySecondary(4)
    }
    MAX-ACCESS read-write
    STATUS current
    DESCRIPTION
    "File attribute of the startup image for an extended device to load from
    the parent device.  Examples of extended devices include PEXs and firewall
    modules.  The none attribute is returned if the image is not for extended
    devices, or if the load attribute is not specified."
    ::= { ibSysPackageEntry 11 }

ibSysPackageModel OBJECT-TYPE
    SYNTAX DisplayString (SIZE (0..63))
    MAX-ACCESS read-only
    STATUS current
    DESCRIPTION
    "Indicates whether the image file is for an extended device or the parent
    device.  Examples of extended devices include PEXs and firewall modules."
    ::= { ibSysPackageEntry 12 }

-- begin package operate table
ibSysPackageOperateEntryLimit OBJECT-TYPE
    SYNTAX Integer32 (0..2147483647)
    MAX-ACCESS read-write
    STATUS current
    DESCRIPTION
        "
        The maximum number of the entries in ibSysPackageOperateTable.
        "
    ::= { ibSysPackage 3 }

ibSysPackageOperateTable OBJECT-TYPE
    SYNTAX SEQUENCE OF IbSysPackageOperateEntry
    MAX-ACCESS not-accessible
    STATUS current
    DESCRIPTION
        "A table of package file operate."
   ::= { ibSysPackage 4 }

ibSysPackageOperateEntry OBJECT-TYPE
    SYNTAX IbSysPackageOperateEntry
    MAX-ACCESS not-accessible
    STATUS current
    DESCRIPTION
        "
        An operate request entry.
        "
    INDEX { ibSysPackageOperateIndex }
    ::= { ibSysPackageOperateTable 1 }

IbSysPackageOperateEntry ::=
    SEQUENCE {
        ibSysPackageOperateIndex                   Integer32,
        ibSysPackageOperatePackIndex               Integer32,
        ibSysPackageOperateStatus                  INTEGER,
        ibSysPackageOperateRowStatus               RowStatus,
        ibSysPackageOperateResult                  INTEGER
     }

ibSysPackageOperateIndex OBJECT-TYPE
    SYNTAX Integer32 (1..2147483647)
    MAX-ACCESS not-accessible
    STATUS current
    DESCRIPTION
        "
        The unique index value of a row in this table.
        "
    ::= { ibSysPackageOperateEntry 1 }

ibSysPackageOperatePackIndex OBJECT-TYPE
    SYNTAX Integer32 (1..2147483647)
    MAX-ACCESS   read-create
    STATUS current
    DESCRIPTION
        "
        Specify the package file in the ibSysPackageTable.
        "
    ::= { ibSysPackageOperateEntry 2 }

ibSysPackageOperateStatus OBJECT-TYPE
    SYNTAX INTEGER
        {
        active(1),
        inactive(2)
        }
    MAX-ACCESS read-create
    STATUS current
    DESCRIPTION
        "
        activate or deactivate a package in the ibSysPackageTable.
        "
    ::= { ibSysPackageOperateEntry 3 }

ibSysPackageOperateRowStatus OBJECT-TYPE
    SYNTAX  RowStatus
    MAX-ACCESS read-create
    STATUS current
    DESCRIPTION
        "
        the status of this table entry.
        When the status is active all the
        object's value in the entry is not
        allowed to modified.
        "
    ::= { ibSysPackageOperateEntry 4 }

ibSysPackageOperateResult OBJECT-TYPE
    SYNTAX  INTEGER
      {
        opInProgress(1),
        opSuccess(2),
        opUnknownFailure(3),
        opInvalidFile(4),
        opNotSupport(5)
      }
    MAX-ACCESS read-only
    STATUS current
    DESCRIPTION
        "
        the result of the operation.
        "
    ::= { ibSysPackageOperateEntry 5 }
-- End define sysPackage group

-- Begin define sysIpe group
ibSysIpeFile OBJECT IDENTIFIER ::= { ibSystemManMIBObjects 8 }

ibSysIpeFileNum OBJECT-TYPE
    SYNTAX Integer32 (0..2147483647)
    MAX-ACCESS read-only
    STATUS current
    DESCRIPTION
        "
        The number of software IPE(Image Package Envelop) files.
        It indicates the total entries of ibSysIpeFileTable.
        "
    ::= { ibSysIpeFile 1 }

ibSysIpeFileTable OBJECT-TYPE
    SYNTAX SEQUENCE OF IbSysIpeFileEntry
    MAX-ACCESS not-accessible
    STATUS current
    DESCRIPTION
        "The system IPE file manage table.
        "
    ::= { ibSysIpeFile 2 }

ibSysIpeFileEntry OBJECT-TYPE
    SYNTAX IbSysIpeFileEntry
    MAX-ACCESS not-accessible
    STATUS current
    DESCRIPTION
        "
        An IPE package file entry.  Each entry consists of information of
        an IPE package file.
        ibSysIpeFileIndex exclusively decides an IPE file.
        "
    INDEX { ibSysIpeFileIndex }
    ::= { ibSysIpeFileTable 1 }

IbSysIpeFileEntry ::=
    SEQUENCE {
        ibSysIpeFileIndex            Integer32,
        ibSysIpeFileName             DisplayString,
        ibSysIpeFileSize             Unsigned32,
        ibSysIpeFileLocation         DisplayString,
        ibSysIpeFileModel            SnmpTagList
     }

ibSysIpeFileIndex OBJECT-TYPE
    SYNTAX Integer32 (1..2147483647)
    MAX-ACCESS not-accessible
    STATUS current
    DESCRIPTION
        "There are two parts for the index depicted as follows:

        31                15             0
        +++++++++++++++++++++++++++++++++++
        + physical index   +  IPE   index +
        +++++++++++++++++++++++++++++++++++

        From bit0 to bit15 (two bytes) is the IPE file index; IPE file Index
        is a monotonically increasing integer for the sole purpose of indexing
        events.  When it reaches the maximum value, an extremely unlikely
        event, the agent wraps the value back to 1 and may flush existing
        entries.

        From bit16 to bit31 (two bytes) is the physical index the same as the
        entPhysicalIndex specified in ENTITY-MIB.

        Any index beyond the above range will not be supported.

        If a file is added in, its ibSysIpeFileIndex will be the maximum image
        ndex plus one.
        If the IPE file is removed, renamed, or moved from one place to
        another, its ibSysIpeFileIndex is not reallocated.
        If the IPE file's content is replaced, its ibSysIpeFileIndex will not
        change.
        "
    ::= { ibSysIpeFileEntry 1 }

ibSysIpeFileName OBJECT-TYPE
    SYNTAX DisplayString (SIZE (0..255))
    MAX-ACCESS read-only
    STATUS current
    DESCRIPTION
        "
        The file name of the IPE file.  It MUST NOT contain the path of
        the file.
        "
    ::= { ibSysIpeFileEntry 2 }

ibSysIpeFileSize OBJECT-TYPE
    SYNTAX Unsigned32 (1..4294967295)
    MAX-ACCESS read-only
    STATUS current
    DESCRIPTION
        "
        Size of the file in bytes.
        "
    ::= { ibSysIpeFileEntry 3 }

ibSysIpeFileLocation OBJECT-TYPE
    SYNTAX DisplayString (SIZE (0..255))
    MAX-ACCESS read-only
    STATUS current
    DESCRIPTION
        "
        The directory path of the IPE file.
        Its form should be the same as what defined in file system.
        Currently it is defined as follows:
        For mainboard:   flash:/
        For slave mainboard and subboards: slotN#flash:/
        "
    ::= { ibSysIpeFileEntry 4 }

ibSysIpeFileModel OBJECT-TYPE
    SYNTAX SnmpTagList
    MAX-ACCESS read-only
    STATUS current
    DESCRIPTION
        "Device models for which the IPE file contains software images.  For
        the ease of software upgrade, an IPE file might contain software images
        for a parent device and extended devices.  Examples of extended devices
        include PEXs and firewall modules."
    ::= { ibSysIpeFileEntry 5 }

-- Begin define Ipe-package
ibSysIpePackageTable OBJECT-TYPE
    SYNTAX SEQUENCE OF IbSysIpePackageEntry
    MAX-ACCESS not-accessible
    STATUS current
    DESCRIPTION
        "
        The IPE package file table.  It shows the package files in
        the IPE file.
        "
    ::= { ibSysIpeFile 3 }

ibSysIpePackageEntry OBJECT-TYPE
    SYNTAX IbSysIpePackageEntry
    MAX-ACCESS not-accessible
    STATUS current
    DESCRIPTION
        "
        An entry of the ibIpePackageTable.  Indexed by
        ibSysIpeFileIndex and ibSysIpePackageIndex.
        "
    INDEX { ibSysIpeFileIndex, ibSysIpePackageIndex }
    ::= { ibSysIpePackageTable 1 }

IbSysIpePackageEntry ::=
    SEQUENCE {
        ibSysIpePackageIndex            Integer32,
        ibSysIpePackageName             DisplayString,
        ibSysIpePackageSize             Unsigned32,
        ibSysIpePackageType             INTEGER,
        ibSysIpePackageDescription      DisplayString,
        ibSysIpePackageFeature          DisplayString,
        ibSysIpePackageVersion          DisplayString,
        ibSysIpePackageModel            DisplayString
     }

ibSysIpePackageIndex OBJECT-TYPE
    SYNTAX Integer32 (1..2147483647)
    MAX-ACCESS not-accessible
    STATUS current
    DESCRIPTION
        "
        It is the IPE package index; IPE Package Index
        is a monotonically increasing integer for the sole purpose of indexing
        events.  When it reaches the maximum value, an extremely unlikely
        event, the agent wraps the value back to 1 and may flush existing
        entries.

        Any index beyond the above range will not be supported.
        "
    ::= { ibSysIpePackageEntry 1 }

ibSysIpePackageName OBJECT-TYPE
    SYNTAX DisplayString (SIZE (0..255))
    MAX-ACCESS read-only
    STATUS current
    DESCRIPTION
        "The file name of the package file."
    ::= { ibSysIpePackageEntry 2 }

ibSysIpePackageSize OBJECT-TYPE
    SYNTAX Unsigned32 (1..4294967295)
    MAX-ACCESS read-only
    STATUS current
    DESCRIPTION
        "
        Size of the package file in bytes.
        "
    ::= { ibSysIpePackageEntry 3 }

ibSysIpePackageType OBJECT-TYPE
    SYNTAX INTEGER
        {
        boot(1),
        system(2),
        feature(3),
        patch(4)
        }
    MAX-ACCESS read-only
    STATUS current
    DESCRIPTION
        "
        It indicates the type of the package file.
        boot    : kernel, file system, memory management and
                  other core components.
        system  : interface management, configuration management and
                  other basic system package.
        feature : feature packages, providing different services.
        patch   : patch file contains fixes for a specific defect.
        "
    ::= { ibSysIpePackageEntry 4 }

ibSysIpePackageDescription OBJECT-TYPE
    SYNTAX DisplayString (SIZE (0..255))
    MAX-ACCESS read-only
    STATUS current
    DESCRIPTION
    "
    It is the description of the package.
    "
    ::= { ibSysIpePackageEntry 5 }

ibSysIpePackageFeature OBJECT-TYPE
    SYNTAX DisplayString (SIZE (0..255))
    MAX-ACCESS read-only
    STATUS current
    DESCRIPTION
    "
    Indicate the feature of the package.
    "
    ::= { ibSysIpePackageEntry 6 }

ibSysIpePackageVersion OBJECT-TYPE
    SYNTAX DisplayString (SIZE (0..255))
    MAX-ACCESS read-only
    STATUS current
    DESCRIPTION
    "
    The version of the package.
    "
    ::= { ibSysIpePackageEntry 7 }

ibSysIpePackageModel OBJECT-TYPE
    SYNTAX DisplayString (SIZE (0..63))
    MAX-ACCESS read-only
    STATUS current
    DESCRIPTION
    "Indicates whether the image package file is for an extended device, the
    parent device, or both.  Examples of extended devices include PEXs and
    firewall modules."
    ::= { ibSysIpePackageEntry 8 }
-- End define Ipe-package

-- Begin define Ipe File operate table
ibSysIpeFileOperateTable OBJECT-TYPE
    SYNTAX SEQUENCE OF IbSysIpeFileOperateEntry
    MAX-ACCESS not-accessible
    STATUS current
    DESCRIPTION
        "A table of IPE file operate."
   ::= { ibSysIpeFile 4 }

ibSysIpeFileOperateEntry OBJECT-TYPE
    SYNTAX IbSysIpeFileOperateEntry
    MAX-ACCESS not-accessible
    STATUS current
    DESCRIPTION
        "
        An operate request entry.
        "
    INDEX { ibSysIpeFileOperateIndex }
    ::= { ibSysIpeFileOperateTable 1 }

IbSysIpeFileOperateEntry ::=
    SEQUENCE {
        ibSysIpeFileOperateIndex                   Integer32,
        ibSysIpeFileOperateFileIndex               Integer32,
        ibSysIpeFileOperateAttribute               INTEGER,
        ibSysIpeFileOperateRowStatus               RowStatus,
        ibSysIpeFileOperateResult                  INTEGER
     }

ibSysIpeFileOperateIndex OBJECT-TYPE
    SYNTAX Integer32 (1..2147483647)
    MAX-ACCESS not-accessible
    STATUS current
    DESCRIPTION
        "
        The unique index value of a row in this table.
        "
    ::= { ibSysIpeFileOperateEntry 1 }

ibSysIpeFileOperateFileIndex OBJECT-TYPE
    SYNTAX Integer32 (1..2147483647)
    MAX-ACCESS   read-create
    STATUS current
    DESCRIPTION
        "
        Specify the IPE file in the ibSysIpeFileTable.  This IPE file
        will be unpacked to package files.
        "
    ::= { ibSysIpeFileOperateEntry 2 }

ibSysIpeFileOperateAttribute OBJECT-TYPE
    SYNTAX INTEGER
        {
        none(1),
        primary(2),
        secondary(3),
        primarySecondary(4)
        }
    MAX-ACCESS read-create
    STATUS current
    DESCRIPTION
        "
        It indicates the attribute of the IPE file when it is used in the reloading.
        If the value is 'primary', the packages in the IPE file will be the
        first packages in the next reloading procedure.
        If the value is 'secondary', the package in the IPE file will be used
        if the primary packages fails.
        If the value is 'none', the IPE file is only unpacked,
        will not be used in the reloading procedure.
        "
    ::= { ibSysIpeFileOperateEntry 3 }

ibSysIpeFileOperateRowStatus OBJECT-TYPE
    SYNTAX  RowStatus
    MAX-ACCESS read-create
    STATUS current
    DESCRIPTION
        "
        the status of this table entry.
        When the status is active all the
        object's value in the entry is not
        allowed to modified.
        "
    ::= { ibSysIpeFileOperateEntry 4 }

ibSysIpeFileOperateResult OBJECT-TYPE
    SYNTAX  INTEGER
      {
        opInProgress(1),
        opSuccess(2),
        opUnknownFailure(3),
        opInvalidFile(4),
        opDeviceFull(5),
        opFileOpenError(6)
      }
    MAX-ACCESS read-only
    STATUS current
    DESCRIPTION
        "
        the result of the operation.
        "
    ::= { ibSysIpeFileOperateEntry 5 }
-- End define IpePackage operate table

ibSysSetBootImage OBJECT IDENTIFIER ::= { ibSystemManMIBObjects 9 }

ibSysSetBootImageOp OBJECT IDENTIFIER ::= { ibSysSetBootImage 1 }

ibSysSetBootImageAction OBJECT-TYPE
    SYNTAX INTEGER
        {
        none(1),
        done(2),
        bootLoadPrimary(3),
        bootLoadSecondary(4),
        bootLoadPrimarySecondary(5),
        bootPrimary(6),
        bootSecondary(7),
        bootPrimarySecondary(8),
        loadPrimary(9),
        loadSecondary(10),
        loadPrimarySecondary(11)
        }
    MAX-ACCESS read-write
    STATUS current
    DESCRIPTION
        "Sets images as primary startup images, secondary startup images, or
        both.  Primary startup images are also called 'main' startup images.
        For extended devices, startup images saved on their local media are
        called 'local startup images,' and images saved on the parent device
        are called 'remote startup images.'
        none: Returns a success without setting image attributes.
        done: Clears data for the previous startup image operation.  This
        object must be set 'done' before each startup image operation.

        -------------------------+-----------------------+---------------------------------------------------
            Action               |   Parent devices      |                  Extended devices
        -------------------------+-----------------------+---------------------------------------------------
        bootLoadPrimary          | Sets images as the    | Sets images as the primary startup images
                                 | primary startup       |
                                 | images                | With storage medium: Sets both local and
                                 |                       |                      remote startup images
                                 |                       | Without storage medium: Sets remote startup images
        -------------------------+-----------------------+---------------------------------------------------
        bootLoadSecondary        | Sets images as the    | Sets images as the backup startup images
                                 | backup startup images |
                                 |                       | With storage medium: Sets both local and
                                 |                       |                      remote startup images
                                 |                       | Without storage medium: Sets remote startup images
        -------------------------+-----------------------+---------------------------------------------------
        bootLoadPrimarySecondary | Sets images as both   | Sets images as both the primary and backup startup
                                 | the primary and       | images
                                 | backup startup images | With storage medium: Sets both local and
                                 |                       |                      remote startup images
                                 |                       | Without storage medium: Sets remote startup images
        -------------------------+-----------------------+---------------------------------------------------
        bootPrimary              | Sets images as the    | Sets images as the primary startup images
                                 | primary startup       |
                                 | images                | With storage medium: Sets local startup images
                                 |                       | Without storage medium: N/A
        -------------------------+-----------------------+---------------------------------------------------
        bootSecondary            | Sets images as the    | Sets images as the backup startup images
                                 | backup startup images |
                                 |                       | With storage medium: Sets local startup images
                                 |                       | Without storage medium: N/A
        -------------------------+-----------------------+---------------------------------------------------
        bootPrimarySecondary     | Sets images as both   | Sets images as both the primary and backup startup
                                 | the primary and       | images
                                 | backup startup images | With storage medium: Sets local startup images
                                 |                       | Without storage medium: N/A
        -------------------------+-----------------------+---------------------------------------------------
        loadPrimary              | N/A                   | Sets images as the remote primary startup images
        -------------------------+-----------------------+---------------------------------------------------
        loadSecondary            | N/A                   | Sets images as the remote backup startup images
        -------------------------+-----------------------+---------------------------------------------------
        loadPrimarySecondary     | N/A                   | Sets images as both the remote primary and
                                 |                       | backup startup images
        -------------------------+-----------------------+---------------------------------------------------
        "
    ::= { ibSysSetBootImageOp 1 }

ibSysSetBootImageFileOverWrite OBJECT-TYPE
    SYNTAX TruthValue
    MAX-ACCESS read-write
    STATUS current
    DESCRIPTION
        "Determines whether to overwrite the existing image file with the same
        name as the downloaded image file. "
    DEFVAL { false }
    ::= { ibSysSetBootImageOp 2 }

ibSysSetBootImageRemoveIpeFile OBJECT-TYPE
    SYNTAX TruthValue
    MAX-ACCESS read-write
    STATUS current
    DESCRIPTION
        "Determines whether the IPE file will be removed when the startup
        images are set successfully.  If this object is set to TRUE,
        the IPE file will be removed."
    DEFVAL { false }
    ::= { ibSysSetBootImageOp 3 }

ibSysSetBootImageStatus OBJECT-TYPE
    SYNTAX INTEGER
        {
        none(1),
        doing(2),
        success(3),
        failed(4)
        }
    MAX-ACCESS read-only
    STATUS current
    DESCRIPTION
        "Status of the startup image set operation."
    ::= { ibSysSetBootImageOp 4 }

ibSysSetBootImageFailedReason OBJECT-TYPE
    SYNTAX DisplayString (SIZE (0..255))
    MAX-ACCESS read-only
    STATUS current
    DESCRIPTION
        "Startup image operation failure reason.  The field is empty if the
        operation was successful."
    ::= { ibSysSetBootImageOp 5 }

ibSysBootPackageTable OBJECT-TYPE
    SYNTAX SEQUENCE OF IbSysBootPackageEntry
    MAX-ACCESS not-accessible
    STATUS current
    DESCRIPTION
        "Table of images to be set as startup images.  It should be used when
         ibSysBootIpeTable is empty."
    ::= { ibSysSetBootImage 2 }

ibSysBootPackageEntry OBJECT-TYPE
    SYNTAX IbSysBootPackageEntry
    MAX-ACCESS not-accessible
    STATUS current
    DESCRIPTION
        "Entry of the image table."
    INDEX { ibSysBootPackageIndex }
    ::= { ibSysBootPackageTable 1 }

IbSysBootPackageEntry ::=
    SEQUENCE {
        ibSysBootPackageIndex
            Integer32,
        ibSysBootPackageRowStatus
            RowStatus
     }

ibSysBootPackageIndex OBJECT-TYPE
    SYNTAX Integer32 (1..2147483647)
    MAX-ACCESS not-accessible
    STATUS current
    DESCRIPTION
        "Index of the software images.  The index must be included
        in ibSysPackageTable."
    ::= { ibSysBootPackageEntry 1 }

ibSysBootPackageRowStatus OBJECT-TYPE
    SYNTAX RowStatus
    MAX-ACCESS read-create
    STATUS current
    DESCRIPTION
        "Row status of the image entry."
    ::= { ibSysBootPackageEntry 2 }

ibSysBootIpeTable OBJECT-TYPE
    SYNTAX SEQUENCE OF IbSysBootIpeEntry
    MAX-ACCESS not-accessible
    STATUS current
    DESCRIPTION
        "Table of the IPE files to be set for startup.  It should be used when
        ibSysBootPackageTable is empty."
    ::= { ibSysSetBootImage 3 }

ibSysBootIpeEntry OBJECT-TYPE
    SYNTAX IbSysBootIpeEntry
    MAX-ACCESS not-accessible
    STATUS current
    DESCRIPTION
        "Entry in the IPE file table."
    INDEX { ibSysBootIpeIndex }
    ::= { ibSysBootIpeTable 1 }

IbSysBootIpeEntry ::=
    SEQUENCE
        {
        ibSysBootIpeIndex
            Integer32,
        ibSysBootIpeRowStatus
            RowStatus
        }

ibSysBootIpeIndex OBJECT-TYPE
    SYNTAX Integer32 (1..2147483647)
    MAX-ACCESS not-accessible
    STATUS current
    DESCRIPTION
        "IPE file index.  The index must be included in ibSysIpeFileTable."
    ::= { ibSysBootIpeEntry 1 }

ibSysBootIpeRowStatus OBJECT-TYPE
    SYNTAX RowStatus
    MAX-ACCESS read-create
    STATUS current
    DESCRIPTION
        "Row status of the IPE file table entry."
    ::= { ibSysBootIpeEntry 2 }

ibSysSetBootImageResultTable OBJECT-TYPE
    SYNTAX SEQUENCE OF IbSysSetBootImageResultEntry
    MAX-ACCESS not-accessible
    STATUS current
    DESCRIPTION
        "Table of startup image operation results.  This table shows the
        result for each card."
    ::= { ibSysSetBootImage 4 }

ibSysSetBootImageResultEntry OBJECT-TYPE
    SYNTAX IbSysSetBootImageResultEntry
    MAX-ACCESS not-accessible
    STATUS current
    DESCRIPTION
        "Entry in the startup image operation result table."
    INDEX { ibSysSetBootImageResultIndex }
    ::= { ibSysSetBootImageResultTable 1 }

IbSysSetBootImageResultEntry ::=
    SEQUENCE {
        ibSysSetBootImageResultIndex
            Integer32,
        ibSysSetBootImageResultStatusOfEachCard
            INTEGER,
        ibSysSetBootImageFailedReasonOfEachCard
            DisplayString
     }

ibSysSetBootImageResultIndex OBJECT-TYPE
    SYNTAX Integer32 (1..65535)
    MAX-ACCESS not-accessible
    STATUS current
    DESCRIPTION
        "Index of a startup image operation result.  It is identical to the
        entity index of each card."
    ::= { ibSysSetBootImageResultEntry 1 }

ibSysSetBootImageResultStatusOfEachCard OBJECT-TYPE
    SYNTAX INTEGER
        {
        none(1),
        doing(2),
        success(3),
        failed(4)
        }
    MAX-ACCESS read-only
    STATUS current
    DESCRIPTION
        "Status of the startup image set operation."
    ::= { ibSysSetBootImageResultEntry 2 }

ibSysSetBootImageFailedReasonOfEachCard OBJECT-TYPE
    SYNTAX DisplayString (SIZE (0..255))
    MAX-ACCESS read-only
    STATUS current
    DESCRIPTION
        "Reason of the startup image set failure for a card.  It is empty if
        the operation was successful."
    ::= { ibSysSetBootImageResultEntry 3 }
-- End define Boot/Load image table

ibSystemManMIBNotifications OBJECT IDENTIFIER ::= { ibSystemMan 2 }


ibSysClockChangedNotification NOTIFICATION-TYPE
    OBJECTS { ibSysLocalClock }
    STATUS current
    DESCRIPTION
        "
        A clock changed notification is generated when the current
        local date and time for the system has been manually changed.
        The value of ibSysLocalClock reflects new date and time.
        "
    ::= { ibSystemManMIBNotifications 1 }


ibSysReloadNotification NOTIFICATION-TYPE
    OBJECTS { ibSysReloadImage, ibSysReloadCfgFile, ibSysReloadReason, ibSysReloadScheduleTime, ibSysReloadAction
         }
    STATUS current
    DESCRIPTION
        "
        A ibSysReloadNotification will be sent before the corresponding entity is
                        rebooted. It will also be sent if the entity fails to reboot because the clock
                        has changed.
        "
    ::= { ibSystemManMIBNotifications 2 }


    ibSysStartUpNotification NOTIFICATION-TYPE
            OBJECTS { ibSysImageType }
            STATUS current
            DESCRIPTION
            "
            a ibSysStartUpNotification trap will be sent when the system starts up with 'main' image file failed,
            a trap will be sent to indicate which type the current image file (I.e backup or secure)is.
            "
            ::={ ibSystemManMIBNotifications 3}


-- conformance and Compliance define
ibSystemManMIBConformance OBJECT IDENTIFIER ::= { ibSystemMan 3 }


ibSystemManMIBCompliances OBJECT IDENTIFIER ::= { ibSystemManMIBConformance 1 }


ibSystemManMIBCompliance MODULE-COMPLIANCE
    STATUS current
    DESCRIPTION
        "
        The compliance statement for entities which implement
        the system management MIB.
        "
    MODULE -- this module
        MANDATORY-GROUPS { ibSysClockGroup, ibSysReloadGroup, ibSysImageGroup,
                           ibSysCFGFileGroup, ibSystemManNotificationGroup,
                           ibSysCurGroup
             }
        GROUP ibSystemBtmLoadGroup
        DESCRIPTION
        "
        The ibSystemBtmLoadGroup is optional for system.
        "
    ::= { ibSystemManMIBCompliances 1 }


ibSystemManMIBGroups OBJECT IDENTIFIER ::= { ibSystemManMIBConformance 2 }


ibSysClockGroup OBJECT-GROUP
    OBJECTS { ibSysLocalClock, ibSysSummerTimeEnable, ibSysSummerTimeZone, ibSysSummerTimeMethod,
        ibSysSummerTimeStart, ibSysSummerTimeEnd, ibSysSummerTimeOffset }
    STATUS current
    DESCRIPTION
        "A collection of objects providing mandatory system clock information."
    ::= { ibSystemManMIBGroups 1 }


-- A collection of objects providing mandatory system image
-- information.
ibSysReloadGroup OBJECT-GROUP
    OBJECTS { ibSysReloadSchedule, ibSysReloadAction, ibSysReloadImage, ibSysReloadCfgFile, ibSysReloadReason,
        ibSysReloadScheduleTagList,ibSysReloadTag,ibSysReloadScheduleTime, ibSysReloadEntity, ibSysReloadRowStatus }
    STATUS current
    DESCRIPTION
        "A collection of objects providing mandatory system reload."
    ::= { ibSystemManMIBGroups 2 }


ibSysImageGroup OBJECT-GROUP
    OBJECTS { ibSysImageNum, ibSysImageName, ibSysImageSize, ibSysImageLocation,
              ibSysImageType }
    STATUS current
    DESCRIPTION
        "A collection of objects providing mandatory system image information."
    ::= { ibSystemManMIBGroups 3 }


ibSysCFGFileGroup OBJECT-GROUP
    OBJECTS { ibSysCFGFileNum, ibSysCFGFileName, ibSysCFGFileSize, ibSysCFGFileLocation }
    STATUS current
    DESCRIPTION
        "
        A collection of objects providing mandatory system
        configuration file information.
        "
    ::= { ibSystemManMIBGroups 4 }


ibSysCurGroup OBJECT-GROUP
    OBJECTS { ibSysCurCFGFileIndex, ibSysCurImageIndex }
    STATUS current
    DESCRIPTION
        "A collection of system current status."
    ::= { ibSystemManMIBGroups 5 }


ibSystemManNotificationGroup NOTIFICATION-GROUP
    NOTIFICATIONS { ibSysClockChangedNotification, ibSysReloadNotification,
                    ibSysStartUpNotification }
    STATUS current
    DESCRIPTION
        "A collection of notifications."
    ::= { ibSystemManMIBGroups 6 }


ibSystemBtmLoadGroup OBJECT-GROUP
    OBJECTS { ibSysCurBtmFileName, ibSysCurUpdateBtmFileName,
                    ibSysBtmLoadMaxNumber, ibSysBtmFileName,
                    ibSysBtmFileType, ibSysBtmRowStatus,
                    ibSysBtmErrorStatus, ibSysBtmLoadTime }
    STATUS current
    DESCRIPTION
        "A collection of objects providing system update bootrom information."
    ::= { ibSystemManMIBGroups 7 }

ibSystemManTrapV2 OBJECT IDENTIFIER ::= { ibSystemMan 4 }
ibSystemManTrapV2Prefix OBJECT IDENTIFIER ::= { ibSystemManTrapV2 0 }

ibSysPatchInstallFail NOTIFICATION-TYPE
    OBJECTS
        {
            ibSysPatchInstallFailPkgname,
            ibSysPatchInstallFailChassis,
            ibSysPatchInstallFailSlot,
            ibSysPatchInstallFailCpu,
            ibSysPatchInstallFailErrCode,
            ibSysPatchInstallFailReason
        }
    STATUS current
    DESCRIPTION
        "This notification is generated when the installation of a patch package fails."
    ::= { ibSystemManTrapV2Prefix 1 }

ibSysPackageVerifyFailed NOTIFICATION-TYPE
    OBJECTS
        {
            ibSysPVFPhysicalName,
            ibSysPVFPackageName,
            ibSysPVFFailReason
        }
    STATUS current
    DESCRIPTION
        "This notification is generated when a software image package fails validation."
    ::= { ibSystemManTrapV2Prefix 2 }

ibSysPatchInstallSuccess NOTIFICATION-TYPE
    OBJECTS
        {
            ibSysPatchInstalledPkgname,
            ibSysPatchInstalledChassis,
            ibSysPatchInstalledSlot,
            ibSysPatchInstalledCpu
        }
    STATUS current
    DESCRIPTION
        "This notification is generated when the installation of a patch package was completed successfully."
::= { ibSystemManTrapV2Prefix 3 }

ibSysPatchActiveNeedRestart NOTIFICATION-TYPE
    OBJECTS
        {
            ibSysPatchOperPkgName,
            ibSysPatchOperChassis,
            ibSysPatchOperSlot,
            ibSysPatchOperCpu
        }
    STATUS current
    DESCRIPTION
        "This notification is generated when restart is required for patch package activation."
::= { ibSystemManTrapV2Prefix 4 }

ibSysPatchInactiveNeedRestart NOTIFICATION-TYPE
    OBJECTS
        {
            ibSysPatchOperPkgName,
            ibSysPatchOperChassis,
            ibSysPatchOperSlot,
            ibSysPatchOperCpu
        }
    STATUS current
    DESCRIPTION
        "This notification is generated when restart is required for patch package deactivation."
::= { ibSystemManTrapV2Prefix 5 }

ibSysVerChkDiffNotify NOTIFICATION-TYPE
    OBJECTS
        {
            ibSysTrapObjectChassis,
            ibSysTrapObjectSlot,
            ibSysTrapObjectCpu
        }
    STATUS current
    DESCRIPTION
        "This notification is generated when inconsistent version check."
::= { ibSystemManTrapV2Prefix 6 }

ibSysVerChkDiffRecoveryNotify  NOTIFICATION-TYPE
    OBJECTS
        {
            ibSysTrapObjectChassis,
            ibSysTrapObjectSlot,
            ibSysTrapObjectCpu
        }
    STATUS current
    DESCRIPTION
        "This notification is generated when version check inconsistency failure recovery."
::= { ibSystemManTrapV2Prefix 7 }

ibSystemManTrapInfor OBJECT IDENTIFIER ::= { ibSystemMan 5 }

ibSysPatchInstallFailPkgname OBJECT-TYPE
    SYNTAX DisplayString (SIZE (0..255))
    MAX-ACCESS accessible-for-notify
    STATUS current
    DESCRIPTION
        "Name of the patch package that fails installation."
    ::= { ibSystemManTrapInfor 1}

ibSysPatchInstallFailChassis OBJECT-TYPE
    SYNTAX Integer32
    MAX-ACCESS accessible-for-notify
    STATUS current
    DESCRIPTION
        "Number of the chassis that fails to install the patch package."
    ::= { ibSystemManTrapInfor 2}

ibSysPatchInstallFailSlot OBJECT-TYPE
    SYNTAX Integer32
    MAX-ACCESS accessible-for-notify
    STATUS current
    DESCRIPTION
        "Number of the slot that fails to install the patch package."
    ::= { ibSystemManTrapInfor 3}

ibSysPatchInstallFailCpu OBJECT-TYPE
    SYNTAX Integer32
    MAX-ACCESS accessible-for-notify
    STATUS current
    DESCRIPTION
        "Number of the CPU that fails to install the patch package."
    ::= { ibSystemManTrapInfor 4}

ibSysPVFPhysicalName OBJECT-TYPE
    SYNTAX DisplayString (SIZE (0..255))
    MAX-ACCESS accessible-for-notify
    STATUS current
    DESCRIPTION
        "Name of the location where a software image package fails validation."
    ::= { ibSystemManTrapInfor 5}

ibSysPVFPackageName OBJECT-TYPE
    SYNTAX DisplayString (SIZE (0..255))
    MAX-ACCESS accessible-for-notify
    STATUS current
    DESCRIPTION
        "Name of the software image package that fails validation."
    ::= { ibSystemManTrapInfor 6}

ibSysPVFFailReason OBJECT-TYPE
    SYNTAX DisplayString (SIZE (0..255))
    MAX-ACCESS accessible-for-notify
    STATUS current
    DESCRIPTION
        "Reason for package validation failure."
    ::= { ibSystemManTrapInfor 7}

ibSysPatchInstalledPkgname OBJECT-TYPE
    SYNTAX DisplayString (SIZE (0..255))
    MAX-ACCESS accessible-for-notify
    STATUS current
    DESCRIPTION
        "Name of the patch package that succeeds installation."
    ::= { ibSystemManTrapInfor 8}

ibSysPatchInstalledChassis OBJECT-TYPE
    SYNTAX Integer32
    MAX-ACCESS accessible-for-notify
    STATUS current
    DESCRIPTION
        "Number of the chassis that succeeds to install the patch package."
    ::= { ibSystemManTrapInfor 9}

ibSysPatchInstalledSlot OBJECT-TYPE
    SYNTAX Integer32
    MAX-ACCESS accessible-for-notify
    STATUS current
    DESCRIPTION
        "Number of the slot that succeeds to install the patch package."
    ::= { ibSystemManTrapInfor 10}

ibSysPatchInstalledCpu OBJECT-TYPE
    SYNTAX Integer32
    MAX-ACCESS accessible-for-notify
    STATUS current
    DESCRIPTION
        "Number of the CPU that succeeds to install the patch package."
    ::= { ibSystemManTrapInfor 11}

ibSysPatchOperPkgName OBJECT-TYPE
    SYNTAX DisplayString (SIZE (1..255))
    MAX-ACCESS accessible-for-notify
    STATUS current
    DESCRIPTION
        "Name of the patch package."
    ::= { ibSystemManTrapInfor 12}

ibSysPatchOperChassis OBJECT-TYPE
    SYNTAX Integer32
    MAX-ACCESS accessible-for-notify
    STATUS current
    DESCRIPTION
        "Chassis number."
    ::= { ibSystemManTrapInfor 13}

ibSysPatchOperSlot OBJECT-TYPE
    SYNTAX Integer32
    MAX-ACCESS accessible-for-notify
    STATUS current
    DESCRIPTION
        "Slot number."
    ::= { ibSystemManTrapInfor 14}

ibSysPatchOperCpu OBJECT-TYPE
    SYNTAX Integer32
    MAX-ACCESS accessible-for-notify
    STATUS current
    DESCRIPTION
        "CPU number."
    ::= { ibSystemManTrapInfor 15}

ibSysPatchInstallFailErrCode OBJECT-TYPE
    SYNTAX Integer32
    MAX-ACCESS accessible-for-notify
    STATUS current
    DESCRIPTION
        "Error code for patch installation failure. Values include:
        1 for Operation failed.
        2 for Invalid file name."
    ::= { ibSystemManTrapInfor 16}

ibSysPatchInstallFailReason OBJECT-TYPE
    SYNTAX DisplayString (SIZE (1..255))
    MAX-ACCESS read-only
    STATUS current
    DESCRIPTION
        "Failure reason for patch installation."
    ::= { ibSystemManTrapInfor 17}

ibSysTrapObjectChassis OBJECT-TYPE
    SYNTAX Integer32
    MAX-ACCESS accessible-for-notify
    STATUS current
    DESCRIPTION
        "Chassis number."
    ::= { ibSystemManTrapInfor 18}

ibSysTrapObjectSlot OBJECT-TYPE
    SYNTAX Integer32
    MAX-ACCESS accessible-for-notify
    STATUS current
    DESCRIPTION
        "Slot number."
    ::= { ibSystemManTrapInfor 19}

ibSysTrapObjectCpu OBJECT-TYPE
    SYNTAX Integer32
    MAX-ACCESS accessible-for-notify
    STATUS current
    DESCRIPTION
        "CPU number."
    ::= { ibSystemManTrapInfor 20}

END
