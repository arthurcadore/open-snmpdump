-- =====================================================================
-- Copyright (C) 2023 Intelbras S.A. All rights reserved.
--
-- Description: Timerange MIB Definition
-- Reference:
-- Version: V1.1
-- History:
-- V1.0 xujunjie,2012-05-14,Initial Version.
-- V1.1 modified by MouXuanli
--     Change name "trng" to "trange".
-- =====================================================================
IB-TRNG2-MIB DEFINITIONS ::= BEGIN
IMPORTS
    ibCommon
        FROM IB-OID-MIB
    Integer32, OBJECT-TYPE, MODULE-IDENTITY
        FROM SNMPv2-SMI
    TruthValue, DateAndTime, RowStatus
        FROM SNMPv2-TC;

ibTRNG2 MODULE-IDENTITY
    LAST-UPDATED "201303080000Z"        -- Mar 8, 2013 at 00:00 GMT
    ORGANIZATION
        "Intelbras S.A. Industria de Telecomunicacao Eletronica Brasileria."
    CONTACT-INFO
        ""
    DESCRIPTION
        "The IB-TRNG2-MIB contains objects to
        Configure the system absolute and periodic time-range."
    REVISION "201303080000Z"        -- Mar 8, 2013 at 00:00 GMT
    DESCRIPTION
        "Modified to change node name from 'trng' to 'trange'."
    REVISION "201205140000Z"        -- May 14, 2012 at 00:00 GMT
    DESCRIPTION
        "201205140000Z, --The initial revision of this MIB module."
    ::= { ibCommon 121 }

--
-- Node definitions
--

ibTRNG2MibObjects OBJECT IDENTIFIER ::= { ibTRNG2 1 }

-- ibTrangeCreateTimerangeTable

ibTrangeCreateTimerangeTable OBJECT-TYPE
    SYNTAX SEQUENCE OF IbTrangeCreateTimerangeEntry
    MAX-ACCESS not-accessible
    STATUS current
    DESCRIPTION
        "Creat TimeRange."
    ::= { ibTRNG2MibObjects 1 }

ibTrangeCreateTimerangeEntry OBJECT-TYPE
    SYNTAX IbTrangeCreateTimerangeEntry
    MAX-ACCESS not-accessible
    STATUS current
    DESCRIPTION
        "Define the entry of ibTrangeCreateTimerangeTable"
    INDEX { ibTrangeIndex }
    ::= { ibTrangeCreateTimerangeTable 1 }

IbTrangeCreateTimerangeEntry ::=
    SEQUENCE {
        ibTrangeIndex
            Integer32,
        ibTrangeName
            OCTET STRING,
        ibTrangeValidFlag
            TruthValue,
        ibTrangeCreateRowStatus
            RowStatus
     }

ibTrangeIndex OBJECT-TYPE
    SYNTAX Integer32 (0..2147483647)
    MAX-ACCESS not-accessible
    STATUS current
    DESCRIPTION
        "TimeRange's index"
    ::= { ibTrangeCreateTimerangeEntry 1 }

ibTrangeName OBJECT-TYPE
    SYNTAX OCTET STRING (SIZE (1..32))
    MAX-ACCESS read-create
    STATUS current
    DESCRIPTION
        "TimeRange's name"
    ::= { ibTrangeCreateTimerangeEntry 2 }

ibTrangeValidFlag OBJECT-TYPE
    SYNTAX TruthValue
    MAX-ACCESS read-only
    STATUS current
    DESCRIPTION
        "Valid or Invalid flag"
    ::= { ibTrangeCreateTimerangeEntry 3 }

ibTrangeCreateRowStatus OBJECT-TYPE
    SYNTAX RowStatus
    MAX-ACCESS read-create
    STATUS current
    DESCRIPTION
        "The status of this conceptual row.Now only realize CreateAndGo and Destroy and Active."
    ::= { ibTrangeCreateTimerangeEntry 4 }

-- ibTrangeAbsoluteTable

ibTrangeAbsoluteTable OBJECT-TYPE
    SYNTAX SEQUENCE OF IbTrangeAbsoluteEntry
    MAX-ACCESS not-accessible
    STATUS current
    DESCRIPTION
        "Creat absoluteness time item of the TimeRange"
    ::= { ibTRNG2MibObjects 2 }

ibTrangeAbsoluteEntry OBJECT-TYPE
    SYNTAX IbTrangeAbsoluteEntry
    MAX-ACCESS not-accessible
    STATUS current
    DESCRIPTION
        "Define the entry of ibTrangeAbsoluteTable"
    INDEX { ibTrangeAbsoluteNameIndex, ibTrangeAbsoluteSubIndex }
    ::= { ibTrangeAbsoluteTable 1 }

IbTrangeAbsoluteEntry ::=
    SEQUENCE {
        ibTrangeAbsoluteNameIndex
            Integer32,
        ibTrangeAbsoluteSubIndex
            Integer32,
        ibTrangeAbsoluteStartTime
            DateAndTime,
        ibTrangeAbsoluteEndTime
            DateAndTime,
        ibTrangeAbsolueRowStatus
            RowStatus
     }

ibTrangeAbsoluteNameIndex OBJECT-TYPE
    SYNTAX Integer32 (0..2147483647)
    MAX-ACCESS not-accessible
    STATUS current
    DESCRIPTION
        "TimeRange's index"
    ::= { ibTrangeAbsoluteEntry 1 }

ibTrangeAbsoluteSubIndex OBJECT-TYPE
    SYNTAX Integer32 (1..12)
    MAX-ACCESS not-accessible
    STATUS current
    DESCRIPTION
        "SubItem's index"
    ::= { ibTrangeAbsoluteEntry 2 }

ibTrangeAbsoluteStartTime OBJECT-TYPE
    SYNTAX DateAndTime
    MAX-ACCESS read-create
    STATUS current
    DESCRIPTION
        "Start point of the timerange.The format defined like 'YYYY-MM-DD,hh:mm:0.0'."
    ::= { ibTrangeAbsoluteEntry 3 }

ibTrangeAbsoluteEndTime OBJECT-TYPE
    SYNTAX DateAndTime
    MAX-ACCESS read-create
    STATUS current
    DESCRIPTION
        "End point of the timerange.The format defined like 'YYYY-MM-DD,hh:mm:0.0'."
    ::= { ibTrangeAbsoluteEntry 4 }

ibTrangeAbsolueRowStatus OBJECT-TYPE
    SYNTAX RowStatus
    MAX-ACCESS read-create
    STATUS current
    DESCRIPTION
        "The status of this conceptual row. Now only realize CreateAndGo and Destroy and Active."
    ::= { ibTrangeAbsoluteEntry 5 }

-- ibTrangePeriodicTable

ibTrangePeriodicTable OBJECT-TYPE
    SYNTAX SEQUENCE OF IbTrangePeriodicEntry
    MAX-ACCESS not-accessible
    STATUS current
    DESCRIPTION
        "Creat periodic time item of the TimeRange"
    ::= { ibTRNG2MibObjects 3 }

ibTrangePeriodicEntry OBJECT-TYPE
    SYNTAX IbTrangePeriodicEntry
    MAX-ACCESS not-accessible
    STATUS current
    DESCRIPTION
        "Define the index of ibTrangePeriodicTable"
    INDEX { ibTrangePeriodicNameIndex, ibTrangePeriodicSubIndex }
    ::= { ibTrangePeriodicTable 1 }

IbTrangePeriodicEntry ::=
    SEQUENCE {
        ibTrangePeriodicNameIndex
            Integer32,
        ibTrangePeriodicSubIndex
            Integer32,
        ibTrangePeriodicDayOfWeek
            BITS,
        ibTrangePeriodicStartTime
            DateAndTime,
        ibTrangePeriodicEndTime
            DateAndTime,
        ibTrangePeriodicRowStatus
            RowStatus
     }

ibTrangePeriodicNameIndex OBJECT-TYPE
    SYNTAX Integer32 (0..2147483647)
    MAX-ACCESS not-accessible
    STATUS current
    DESCRIPTION
        "TimeRange's index"
    ::= { ibTrangePeriodicEntry 1 }

ibTrangePeriodicSubIndex OBJECT-TYPE
    SYNTAX Integer32 (1..32)
    MAX-ACCESS not-accessible
    STATUS current
    DESCRIPTION
        "SubItem's index"
    ::= { ibTrangePeriodicEntry 2 }

ibTrangePeriodicDayOfWeek OBJECT-TYPE
    SYNTAX BITS {
                    sunday(0),
                    monday(1),
                    tuesday(2),
                    wednesday(3),
                    thursday(4),
                    friday(5),
                    saturday(6)
                }
    MAX-ACCESS read-create
    STATUS current
    DESCRIPTION
        "The day of week. This is a bit-map of possible conditions.
        The various bit positions are:
        |0        |sunday                 |
        |1        |monday                 |
        |2        |tuesday                |
        |3        |wednesday              |
        |4        |thursday               |
        |5        |friday                 |
        |6        |saturday               |
        "
    ::= { ibTrangePeriodicEntry 3 }

ibTrangePeriodicStartTime OBJECT-TYPE
    SYNTAX DateAndTime
    MAX-ACCESS read-create
    STATUS current
    DESCRIPTION
        "Start point of this timerange,The format defined like 'hh:mm:0,0'."
    ::= { ibTrangePeriodicEntry 4 }

ibTrangePeriodicEndTime OBJECT-TYPE
    SYNTAX DateAndTime
    MAX-ACCESS read-create
    STATUS current
    DESCRIPTION
        "End point of this timerange. The format definedlike 'hh:mm:0,0'."
    ::= { ibTrangePeriodicEntry 5 }

ibTrangePeriodicRowStatus OBJECT-TYPE
    SYNTAX RowStatus
    MAX-ACCESS read-create
    STATUS current
    DESCRIPTION
        "The status of this conceptual row, Now only realize CreateAndGo and Destroy and Active."
    ::= { ibTrangePeriodicEntry 6 }

END
