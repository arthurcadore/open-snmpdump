-- ==================================================================
-- Copyright (C) 2023 Intelbras S.A. All rights reserved.
-- 
-- Description: 802.1X MIB
-- Reference:
-- Version: V1.3
-- History:
-- 1) 2003-03-27 Fuzhenyu created  
-- 2) v1.1 2004-08-28 chaiyongfu 
--         change node  ibdot1xAuthServerTimeout's DEFVAL { 30 } to DEFVAL { 100 }
--    v1.2 2004-10-12 updated by gaolong
--         Import NOTIFICATION-TYPE
--         Remove chinese characters
--         Fix time format of  ibpaeExtMib.
--    v1.3 2007-10-23 updated by chaiyongfu
--         Add node ibdot1xAuthMethod, ibdot1xpaeportMcastTrigStatus,
--         ibdot1xpaeportHandshakeStatus
-- ==================================================================

IB-8021PAE-MIB DEFINITIONS ::= BEGIN

    IMPORTS
    ibRhw          
        FROM IB-OID-MIB
    OBJECT-TYPE,Unsigned32,NOTIFICATION-TYPE
        FROM SNMPv2-SMI
    
    MODULE-IDENTITY
            FROM SNMPv2-SMI 
    MacAddress
        FROM SNMPv2-TC

    dot1xPaePortNumber
            FROM IEEE8021-PAE-MIB;          
   

     ibpaeExtMib MODULE-IDENTITY
            LAST-UPDATED "200106290000Z"
            ORGANIZATION
                "Intelbras S.A. Industria de Telecomunicacao Eletronica Brasileria."
            CONTACT-INFO
                ""
            DESCRIPTION
            "this file extends IEEE8021-PAE-MIB(802.1x)"
            REVISION "200106290000Z"
            DESCRIPTION
            ""
            ::= { ibRhw 6 }
   -- ============================================================
   -- groups in the PAE MIB
   -- ============================================================

   ibpaeExtMibObjects           OBJECT IDENTIFIER ::= { ibpaeExtMib 1 }    
   ibdot1xPaeSystem             OBJECT IDENTIFIER ::= { ibpaeExtMibObjects 1 }
   ibdot1xPaeAuthenticator      OBJECT IDENTIFIER ::= { ibpaeExtMibObjects 2 }
 
   -- ============================================================

    ibdot1xAuthQuietPeriod OBJECT-TYPE
            SYNTAX             Unsigned32
            MAX-ACCESS     read-write
            STATUS             current
            DESCRIPTION
                    "The value, in seconds, of the quietPeriod constant
                    currently in use by the Authenticator PAE state
                    machine."
            REFERENCE
                    " 9.4.1, quietPeriod"
            DEFVAL { 60 }
            ::= { ibdot1xPaeSystem 1 }

    ibdot1xAuthTxPeriod OBJECT-TYPE
            SYNTAX             Unsigned32
            MAX-ACCESS     read-write
            STATUS             current
            DESCRIPTION
                    "The value, in seconds, of the txPeriod constant
                    currently in use by the Authenticator PAE state
                    machine."
            REFERENCE
                    " 9.4.1, txPeriod"
            DEFVAL { 30 }
            ::= { ibdot1xPaeSystem 2 }

    ibdot1xAuthSuppTimeout OBJECT-TYPE
            SYNTAX             Unsigned32
            MAX-ACCESS     read-write
            STATUS             current
            DESCRIPTION
                   "The value, in seconds, of the suppTimeout constant
                   currently in use by the Backend Authentication state
                   machine."
            REFERENCE
                   " 9.4.1, suppTimeout"
            DEFVAL { 30 }
            ::= { ibdot1xPaeSystem 3 }

   ibdot1xAuthServerTimeout OBJECT-TYPE
           SYNTAX             Unsigned32
           MAX-ACCESS     read-write
           STATUS             current
           DESCRIPTION
                   "The value, in seconds, of the serverTimeout constant
                   currently in use by the Backend Authentication state
                   machine."
           REFERENCE
                   " 9.4.1, serverTimeout"
           DEFVAL { 100 }
           ::= { ibdot1xPaeSystem 4 }

   ibdot1xAuthMaxReq OBJECT-TYPE
           SYNTAX             Unsigned32
           MAX-ACCESS     read-write
           STATUS             current
           DESCRIPTION
                   "The value of the maxReq constant currently in use by
                   the Backend Authentication state machine."
           REFERENCE
                   " 9.4.1, maxReq"
           DEFVAL { 2 }
           ::= { ibdot1xPaeSystem 5 }

   ibdot1xAuthReAuthPeriod OBJECT-TYPE
           SYNTAX             Unsigned32
           MAX-ACCESS     read-write
           STATUS             current
           DESCRIPTION
                   "The value, in seconds, of the reAuthPeriod constant
                   currently in use by the Reauthentication Timer state
                   machine."
           REFERENCE
                   " 9.4.1, reAuthPeriod"
           DEFVAL  { 3600 }
           ::= { ibdot1xPaeSystem 6 }
 
   ibdot1xAuthMethod OBJECT-TYPE
           SYNTAX         INTEGER { chap(1), pap(2), eap(3) }
           MAX-ACCESS     read-write
           STATUS         current
           DESCRIPTION
                   "The value defines the 802.1X authenticatin method."
           REFERENCE
                   ""
           DEFVAL  { 1 }
           ::= { ibdot1xPaeSystem 7 }

   -- ============================================================
   -- The Authenticator Configuration Extracte Table
   -- ============================================================

   ibdot1xAuthConfigExtTable OBJECT-TYPE
           SYNTAX             SEQUENCE OF Ibdot1xAuthConfigExtEntry
           MAX-ACCESS     not-accessible
           STATUS             current
           DESCRIPTION
                   " table extends dot1xAuthConfigTable"
            REFERENCE
                    " 9.4.1 Authenticator Configuration"
            ::= { ibdot1xPaeAuthenticator 1 }

    ibdot1xAuthConfigExtEntry OBJECT-TYPE
            SYNTAX             Ibdot1xAuthConfigExtEntry
            MAX-ACCESS     not-accessible
            STATUS             current
            DESCRIPTION
                    " The configuration information for an Authenticator PAE."
            INDEX { dot1xPaePortNumber }
            ::= { ibdot1xAuthConfigExtTable 1 }
            
    Ibdot1xAuthConfigExtEntry   ::=
    SEQUENCE {
        ibdot1xpaeportAuthAdminStatus   INTEGER ,
        ibdot1xpaeportControlledType    INTEGER ,
        ibdot1xpaeportMaxUserNum        INTEGER ,
        ibdot1xpaeportUserNumNow		INTEGER ,
        ibdot1xpaeportClearStatistics	INTEGER ,
        ibdot1xpaeportMcastTrigStatus   INTEGER ,
        ibdot1xpaeportHandshakeStatus   INTEGER
        }
        
    ibdot1xpaeportAuthAdminStatus  OBJECT-TYPE
           SYNTAX             INTEGER { enabled( 1), disabled( 2) }
           MAX-ACCESS     read-write
           STATUS             current
           DESCRIPTION
                   "The administrative enable/disable state for Port Access Control in a port."
           REFERENCE
                   ""
           DEFVAL  {2}
           ::= { ibdot1xAuthConfigExtEntry 1 }
           
           
    ibdot1xpaeportControlledType  OBJECT-TYPE
           SYNTAX             INTEGER { port(1), mac(2) }
           MAX-ACCESS     read-write
           STATUS             current
           DESCRIPTION
                   "Port Access Control type , base port access control or base MAC access control"
           REFERENCE
                   ""
           DEFVAL  {2}
           ::= { ibdot1xAuthConfigExtEntry 2 }
           
    ibdot1xpaeportMaxUserNum  OBJECT-TYPE
           SYNTAX             INTEGER 
           MAX-ACCESS     read-write
           STATUS             current
           DESCRIPTION
                   "the max num of online user in a port"
           REFERENCE
                   ""
           DEFVAL  {256}
           ::= { ibdot1xAuthConfigExtEntry 3 }
          
    ibdot1xpaeportUserNumNow  OBJECT-TYPE
           SYNTAX             INTEGER 
           MAX-ACCESS     read-only
           STATUS             current
           DESCRIPTION
                   "the num of online user in a port now "
           REFERENCE
                   ""
           ::= { ibdot1xAuthConfigExtEntry 4 }             
      
        
    ibdot1xpaeportClearStatistics  OBJECT-TYPE
           SYNTAX             INTEGER {clear(1)}
           MAX-ACCESS     read-write
           STATUS             current
           DESCRIPTION
                   "Clear various Statistics viz. "
           REFERENCE
                   ""
           ::= { ibdot1xAuthConfigExtEntry 5 }    
           
           
    ibdot1xpaeportMcastTrigStatus  OBJECT-TYPE
           SYNTAX         INTEGER { enabled( 1), disabled( 2) }
           MAX-ACCESS     read-write
           STATUS         current
           DESCRIPTION
                   "The administrative enable/disable state for sending
                   muticast EAP_REQ/ID packet."
           REFERENCE
                   ""
           DEFVAL  {1}
           ::= { ibdot1xAuthConfigExtEntry 6 }
           
    ibdot1xpaeportHandshakeStatus  OBJECT-TYPE
           SYNTAX         INTEGER { enabled( 1 ), disabled( 2 ) }
           MAX-ACCESS     read-write
           STATUS         current
           DESCRIPTION
                   "The administrative enable/disable state for sending
                   handshake EAP_REQ/ID packet."
           REFERENCE
                   ""
           DEFVAL  {1}
           ::= { ibdot1xAuthConfigExtEntry 7 }

  -- trap defination
    ibdot1xPaeTraps             OBJECT IDENTIFIER ::= { ibpaeExtMibObjects 0 }

    ibsupplicantproxycheck NOTIFICATION-TYPE 
      OBJECTS { ibproxycheckVlanId, ibproxycheckPortName, ibproxycheckMacAddr, ibproxycheckIpaddr, ibproxycheckUsrName }
      STATUS current
      DESCRIPTION ""
      ::= { ibdot1xPaeTraps 1 }

    ibproxycheckVlanId OBJECT-TYPE 
      SYNTAX INTEGER
      MAX-ACCESS accessible-for-notify
      STATUS current
      DESCRIPTION "."
      ::= { ibdot1xPaeTraps 2 }

    ibproxycheckPortName OBJECT-TYPE 
      SYNTAX OCTET STRING
      MAX-ACCESS accessible-for-notify
      STATUS current
      DESCRIPTION "."
      ::= { ibdot1xPaeTraps 3 }

    ibproxycheckMacAddr OBJECT-TYPE 
      SYNTAX MacAddress
      MAX-ACCESS accessible-for-notify
      STATUS current
      DESCRIPTION "."
      ::= { ibdot1xPaeTraps 4 }
      
    ibproxycheckIpaddr OBJECT-TYPE 
      SYNTAX IpAddress
      MAX-ACCESS accessible-for-notify
      STATUS current
      DESCRIPTION "."
      ::= { ibdot1xPaeTraps 5 } 
              
    ibproxycheckUsrName OBJECT-TYPE 
      SYNTAX OCTET STRING
      MAX-ACCESS accessible-for-notify
      STATUS current
      DESCRIPTION "."
      ::= { ibdot1xPaeTraps 6 }               
END
