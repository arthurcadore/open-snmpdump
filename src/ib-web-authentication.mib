-- =================================================================
-- Copyright (C) 2023 Intelbras S.A. All rights reserved.
--
-- Description: description of Web Authentication
-- Reference:
-- Version: V1.0
-- History:
--   V1.0 2008-6-25, Created by dupengfei
-- =================================================================
IB-WEB-AUTHENTICATION-MIB DEFINITIONS ::= BEGIN

IMPORTS
    ibCommon
        FROM IB-OID-MIB
    ifDescr
        FROM RFC1213-MIB
    OBJECT-TYPE, NOTIFICATION-TYPE, MODULE-IDENTITY, Integer32
        FROM SNMPv2-SMI
    MacAddress
        FROM SNMPv2-TC;

ibWebAuthentication MODULE-IDENTITY
    LAST-UPDATED "200806250000Z"
    ORGANIZATION
        "Intelbras S.A. Industria de Telecomunicacao Eletronica Brasileria."
    CONTACT-INFO
        ""
    DESCRIPTION
        "The MIB module is used for web authentication to send traps."
    REVISION "200806250000Z"
    DESCRIPTION
        "The initial version of ibWebAuthenticationMIB"
    ::= { ibCommon 93 }


ibWaTrapObjects OBJECT IDENTIFIER ::= { ibWebAuthentication 1 }

--
-- WEB AUTHENTICATION TRAPS OBJECT
--
ibWaVlanID OBJECT-TYPE
    SYNTAX      Integer32
    MAX-ACCESS  accessible-for-notify
    STATUS      current
    DESCRIPTION
        "The Vlan ID associate with the port and the MAC address."
    ::= { ibWaTrapObjects 1 }

ibWaReasonCode OBJECT-TYPE
    SYNTAX INTEGER
    {
         globalNumberMax(1),
         configNumberMax(2),
         portNumberMax(3),
         invalidUsername(4),
         authFail(5),
         setACLFail(6),
         changeVlanFail(7),
         other(8),
         onlineOverTime(9),
         noTransferData(10),
         cutOperation(11),
         portDisabled(12),
         portDown(13),
         userLogout(14),
         vlanChanged(15),
         vlanDelted(16)
    }
    MAX-ACCESS  accessible-for-notify
    STATUS      current
    DESCRIPTION
        "The code indicates the reason for the action of this trap.
         globalNumberMax:
            The global number of connections is up to max.
         configNumberMax:
            The global number of connections is up to configured max value.
         portNumberMax:
            The interface number of connections is up to max.
         invalidUsername:
            The username or password is too long or username is empty.
         authFail:
            Wrong username or password.
         setACLFail:
            Failed to set ACL.
         changeVlanFail:
            Failed to set VLAN.
         other:
            Other reasons.
         onlineOverTime:
            The online time is over the max value.
         noTransferData:
            There was no data flow for the connection.
         cutOperation:
            There was a cut operation.
         portDisabled:
            Web authentication was disabled on interface.
         portDown:
            The interface turned down.
         userLogout:
            The client required to logout.
         vlanChanged:
            The interface VLAN value was changed.
         vlanDelted:
            The interface VLAN was deleted."
    ::= { ibWaTrapObjects 2 }

ibWaActionCode OBJECT-TYPE
    SYNTAX INTEGER
    {
        enabled(1),
        disabled(2)
    }
    MAX-ACCESS  accessible-for-notify
    STATUS      current
    DESCRIPTION
        "The code indicates the system action.
         enabled:
            Web authentication turns enabled.
         disabled:
            Web authentication turns disabled."
    ::= { ibWaTrapObjects 3 }

ibWaClientMacAddr OBJECT-TYPE
    SYNTAX      MacAddress
    MAX-ACCESS  accessible-for-notify
    STATUS      current
    DESCRIPTION
        "The MAC address of the client."
    ::= { ibWaTrapObjects 4 }

ibWaTrap OBJECT IDENTIFIER ::= { ibWebAuthentication 2 }

ibWaTrapPrefix OBJECT IDENTIFIER ::= { ibWaTrap 0 }


ibWaClientLogon NOTIFICATION-TYPE
    OBJECTS
        {
            ibWaClientMacAddr,
            ifDescr,
            ibWaVlanID
        }
    STATUS      current
    DESCRIPTION
        "It is generated when a client succeeded to logon."
    ::= { ibWaTrapPrefix 1 }

ibWaClientLogonFail NOTIFICATION-TYPE
    OBJECTS
        {
            ibWaClientMacAddr,
            ifDescr,
            ibWaVlanID,
            ibWaReasonCode
        }
    STATUS      current
    DESCRIPTION
        "It is generated when a client failed to logon, the ibWaReasonCode
         shows the failure reason."
    ::= { ibWaTrapPrefix 2 }

ibWaClientLogout NOTIFICATION-TYPE
    OBJECTS
        {
            ibWaClientMacAddr,
            ifDescr,
            ibWaVlanID,
            ibWaReasonCode
        }
    STATUS      current
    DESCRIPTION
        "It is generated when a client logout, the ibWaReasonCode
         shows the logout reason."
    ::= { ibWaTrapPrefix 3 }

ibWaSysAction NOTIFICATION-TYPE
    OBJECTS
        {
            ibWaActionCode
        }
    STATUS      current
    DESCRIPTION
        "It is generated when a system action was occurred, the ibWaActionCode
         shows the action information."
    ::= { ibWaTrapPrefix 4 }

END
