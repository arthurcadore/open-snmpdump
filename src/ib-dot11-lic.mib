-- =============================================================================
-- Copyright (C) 2023 Intelbras S.A. All rights reserved.
--
-- Description:
--   The file defines a MIB to provide WLAN license feature.
-- Reference:
-- Version: V1.0
-- History:
--   V1.0 created by luoguixing
--     Initial version 2012-04-25
-- =============================================================================
IB-DOT11-LIC-MIB DEFINITIONS ::= BEGIN

IMPORTS
        MODULE-IDENTITY,
        OBJECT-TYPE,
        Integer32
    FROM SNMPv2-SMI
        TruthValue
    FROM SNMPv2-TC
        ibDot11
    FROM IB-DOT11-REF-MIB;

ibDot11LIC MODULE-IDENTITY
    LAST-UPDATED "201204251800Z"        -- Apr 25, 2012 at 18:00 GMT
    ORGANIZATION
        "Intelbras S.A. Industria de Telecomunicacao Eletronica Brasileria."
    CONTACT-INFO
        ""
    DESCRIPTION
        "This MIB provides information for WLAN license configuration in AC.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Fit AP
        Applied in the enterprise environment, it will work
        under the control and management from AC.

        Control And Provisioning of Wireless Access Points Protocol
        The short name of protocol is CAPWAP. AC will control
        and manage AP by CAPWAP tunnel protocol defined by IETF.
        Also, a data tunnel will be set up between AC and AP.

        Basic Service Set
        The IEEE 802.11 BSS of an AP comprises of the
        stations directly associating with the AP. It will
        be identified by BSSID."

    REVISION "201204251800Z"        -- Apr 25, 2012 at 18:00 GMT
    DESCRIPTION
        "The initial revision of this MIB module."
    ::= { ibDot11 14 }

-- *****************************************************************************
-- *  Major sections
-- *****************************************************************************

--  License Configuration Group
--  DEFINED AS "The group to provide the license configuration information for AC"

ibDot11LICConfigGroup OBJECT IDENTIFIER     ::= { ibDot11LIC 1 }

--  License ap number Group
--  DEFINED AS "The group to provide the ap number information for AC."
ibDot11LICApNumGroup OBJECT IDENTIFIER  ::= { ibDot11LIC 2 }
--  AP Number Group has the following children:
--  ibDot11LICApNumAttrTable          ::= { ibDot11LICApNumGroup 1 }
--  ibDot11LICApNumLicTable            ::= { ibDot11LICApNumGroup 2 }

--  License wlan feature Group
--  DEFINED AS "The group to provide the wlan feature information for AC."
ibDot11LICFeatureGroup OBJECT IDENTIFIER    ::= { ibDot11LIC 3 }
--  License wlan feature Group has the following children:
--  ibDot11LICFeatureAttrTable          ::= { ibDot11LICFeatureGroup 1 }
--  ibDot11LICFeatureLicTable            ::= { ibDot11LICFeatureGroup 2 }

-- *****************************************************************************
-- *  ibDot11LICConfigGroup Definition
-- *****************************************************************************
ibDot11LICSerialNumber OBJECT-TYPE
    SYNTAX    OCTET STRING (SIZE(0..255))
    MAX-ACCESS    read-only
    STATUS    current
    DESCRIPTION
        "The device serial number."
    ::= { ibDot11LICConfigGroup 1 }

ibDot11LicApNumGroupSupport OBJECT-TYPE
    SYNTAX      TruthValue
    MAX-ACCESS  read-only
    STATUS      current
    DESCRIPTION
        "Represents support ibDot11LicApNumGroup
        'ture': device spport ibDot11LicApNumGroup.
        'false': device not spport ibDot11LicApNumGroupp."
    DEFVAL       { false }
    ::= { ibDot11LICConfigGroup 2 }

-- *****************************************************************************
-- *  End of ibDot11LICConfigGroup Definition
-- *****************************************************************************


-- *****************************************************************************
-- *  ibDot11LICApNumTable Definition
-- *****************************************************************************

ibDot11LICApNumAttrTable OBJECT IDENTIFIER     ::= { ibDot11LICApNumGroup 1 }

ibDot11LICDefautAPNumPermit OBJECT-TYPE
    SYNTAX      Integer32
    MAX-ACCESS  read-only
    STATUS      current
    DESCRIPTION
        "Represents the number of AP connection permitted
        for one AC without license."
    ::= { ibDot11LICApNumAttrTable 1 }

ibDot11LICCurrentAPNumPermit OBJECT-TYPE
    SYNTAX      Integer32
    MAX-ACCESS  read-only
    STATUS      current
    DESCRIPTION
        "Represents the total number of AP connection permitted
        for one AC, include default number and the licenses
        that installed."
    ::= { ibDot11LICApNumAttrTable 2 }

ibDot11LICMaxAPNumPermit OBJECT-TYPE
    SYNTAX      Integer32
    MAX-ACCESS  read-only
    STATUS      current
    DESCRIPTION
        "Represents the maximum number of AP to support connection permitted
        for one AC, include default number and full licenses."
    ::= { ibDot11LICApNumAttrTable 3 }


ibDot11LICApNumLicTable OBJECT-TYPE
    SYNTAX      SEQUENCE OF IbDot11LICApNumLicEntry
    MAX-ACCESS  not-accessible
    STATUS      current
    DESCRIPTION
        "Each entry contains license information of ap number."
    ::= { ibDot11LICApNumGroup 2 }

ibDot11LICApNumLicEntry OBJECT-TYPE
    SYNTAX      IbDot11LICApNumLicEntry
    MAX-ACCESS  not-accessible
    STATUS      current
    DESCRIPTION
        "Each entry contains association information of each station."
   INDEX
        { ibDot11LICLicenseKeyIndex }
    ::= { ibDot11LICApNumLicTable 1 }

IbDot11LICApNumLicEntry ::= SEQUENCE
    {
        ibDot11LICLicenseKeyIndex   Integer32,
        ibDot11LICLicenseKey        OCTET STRING,
        ibDot11LICActivationKey     OCTET STRING,
        ibDot11LICApNum          Integer32
    }

ibDot11LICLicenseKeyIndex OBJECT-TYPE
    SYNTAX      Integer32 (0..2147483647)
    MAX-ACCESS  read-only
    STATUS      current
    DESCRIPTION
        "Licensed key index value."
    ::= { ibDot11LICApNumLicEntry 1 }

ibDot11LICLicenseKey OBJECT-TYPE
    SYNTAX      OCTET STRING
    MAX-ACCESS  read-only
    STATUS      current
    DESCRIPTION
        "Specifies a certain license key."
    ::= { ibDot11LICApNumLicEntry 2 }

ibDot11LICActivationKey OBJECT-TYPE
    SYNTAX      OCTET STRING
    MAX-ACCESS  read-only
    STATUS      current
    DESCRIPTION
        "Specifies a certain activation key."
    ::= { ibDot11LICApNumLicEntry 3 }

ibDot11LICApNum OBJECT-TYPE
    SYNTAX      Integer32
    MAX-ACCESS  read-only
    STATUS      current
    DESCRIPTION
        "Represents support connect ap number of the license."
    ::= { ibDot11LICApNumLicEntry 4 }

-- *****************************************************************************
-- *  End of ibDot11LICApNumTable Definition
-- *****************************************************************************


-- *****************************************************************************
-- *  ibDot11LICFeatureTable Definition
-- *****************************************************************************
ibDot11LICFeatureAttrTable OBJECT-TYPE
    SYNTAX      SEQUENCE OF IbDot11LICFeatureAttrEntry
    MAX-ACCESS  not-accessible
    STATUS      current
    DESCRIPTION
        "Each entry contains attribute information of wlan feature."
    ::= { ibDot11LICFeatureGroup 1 }

ibDot11LICFeatureAttrEntry OBJECT-TYPE
    SYNTAX      IbDot11LICFeatureAttrEntry
    MAX-ACCESS  not-accessible
    STATUS      current
    DESCRIPTION
        "Each entry contains feature attribute information of licensetypename."
   INDEX
        {
            ibDot11LICAttrIndex
        }
    ::= { ibDot11LICFeatureAttrTable 1 }

IbDot11LICFeatureAttrEntry ::= SEQUENCE
    {
        ibDot11LICAttrIndex     Integer32,
        ibDot11LICAttrTypeName  OCTET STRING,
        ibDot11LICAttrDefVal    Integer32,
        ibDot11LICAttrMaxVal    Integer32
    }

ibDot11LICAttrIndex OBJECT-TYPE
    SYNTAX      Integer32 (0..2147483647)
    MAX-ACCESS  read-only
    STATUS      current
    DESCRIPTION
        "Attribute index value."
    ::= { ibDot11LICFeatureAttrEntry 1 }

ibDot11LICAttrTypeName OBJECT-TYPE
    SYNTAX      OCTET STRING
    MAX-ACCESS  read-only
    STATUS      current
    DESCRIPTION
        "Represents attribute type name"
    ::= { ibDot11LICFeatureAttrEntry 2 }

ibDot11LICAttrDefVal OBJECT-TYPE
    SYNTAX      Integer32
    MAX-ACCESS  read-only
    STATUS      current
    DESCRIPTION
        "Represents the default value of the license type."
    ::= { ibDot11LICFeatureAttrEntry 3 }

ibDot11LICAttrMaxVal OBJECT-TYPE
    SYNTAX      Integer32
    MAX-ACCESS  read-only
    STATUS      current
    DESCRIPTION
        "Represents the maximum value of the license type."
    ::= { ibDot11LICFeatureAttrEntry 4 }

ibDot11LICFeatureLicTable OBJECT-TYPE
    SYNTAX      SEQUENCE OF IbDot11LICFeatureLicEntry
    MAX-ACCESS  not-accessible
    STATUS      current
    DESCRIPTION
        "Each entry contains license information of wlan feature."
    ::= { ibDot11LICFeatureGroup 2 }

ibDot11LICFeatureLicEntry OBJECT-TYPE
    SYNTAX      IbDot11LICFeatureLicEntry
    MAX-ACCESS  not-accessible
    STATUS      current
    DESCRIPTION
        "Each entry contains wlan feature information of license."
   INDEX
        {
            ibDot11LICKeyIndex
        }
    ::= { ibDot11LICFeatureLicTable 1 }

IbDot11LICFeatureLicEntry ::= SEQUENCE
    {
        ibDot11LICKeyIndex   Integer32,
        ibDot11LICTypeName   OCTET STRING,
        ibDot11LICKey        OCTET STRING,
        ibDot11LICTimeLimit  Integer32,
        ibDot11LICValue      Integer32
    }

ibDot11LICKeyIndex OBJECT-TYPE
    SYNTAX      Integer32 (0..2147483647)
    MAX-ACCESS  read-only
    STATUS      current
    DESCRIPTION
        "Licensed key index value."
    ::= { ibDot11LICFeatureLicEntry 1 }

ibDot11LICTypeName OBJECT-TYPE
    SYNTAX      OCTET STRING
    MAX-ACCESS  read-only
    STATUS      current
    DESCRIPTION
        "Represents the type name of the license entry."
    ::= { ibDot11LICFeatureLicEntry 2 }

ibDot11LICKey OBJECT-TYPE
    SYNTAX      OCTET STRING
    MAX-ACCESS  read-only
    STATUS      current
    DESCRIPTION
        "Specifies a certain license key."
    ::= { ibDot11LICFeatureLicEntry 3 }

ibDot11LICTimeLimit OBJECT-TYPE
    SYNTAX      Integer32
    MAX-ACCESS  read-only
    STATUS      current
    DESCRIPTION
        "Represents available time left of the license entry."
    ::= { ibDot11LICFeatureLicEntry 4 }

ibDot11LICValue OBJECT-TYPE
    SYNTAX      Integer32
    MAX-ACCESS  read-only
    STATUS      current
    DESCRIPTION
        "Represents the value of the license entry.
        If ibDot11LICFeatureTypeName is 'AP',
        this meaning of ap number, and so no."
    ::= { ibDot11LICFeatureLicEntry 5 }

-- *****************************************************************************
-- *  End of ibDot11LICFeatureTable Definition
-- *****************************************************************************

END
