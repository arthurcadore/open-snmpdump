-- ===========================================================================================================
-- Copyright (C) 2023 Intelbras S.A. All rights reserved.
--
-- Description: Mdc MIB
-- Reference:
-- Version: V1.1
-- History:
--  revision 1.0 2013-03-05 created by c08124
--  revision 1.1 2014-03-12 Modified ibMDCAllocateGroupIndex
--                          from (1..2147483647) to (-2147483648..2147483647)
--                          by j08116
--
-- ============================================================================================================
IB-MDC-MIB DEFINITIONS ::= BEGIN

IMPORTS
    entPhysicalIndex
        FROM ENTITY-MIB
    ibCommon
        FROM IB-OID-MIB
    Integer32, Unsigned32, OBJECT-TYPE, MODULE-IDENTITY, NOTIFICATION-TYPE
        FROM SNMPv2-SMI
    DisplayString, RowStatus, TruthValue, TEXTUAL-CONVENTION
        FROM SNMPv2-TC;

ibMDC MODULE-IDENTITY
    LAST-UPDATED "201303051448Z"
    ORGANIZATION
        "Intelbras S.A. Industria de Telecomunicacao Eletronica Brasileria."
    CONTACT-INFO
        ""
    DESCRIPTION
        "This MIB contains objects to manage MDC (Multitenant Device Context) operations.

        Such as:
        1. Configure MDCs for a device and display MDCs and their status.
        2. Assign CPU, storage space, and memory space resources to the MDC, and display their status.
        3. Authorize the MDC to use the interface cards, and assign physical interfaces to an MDC.

        Default MDC: A device supporting MDCs is an MDC itself, and it is called the default MDC.
        From the default MDC, administrators can manage the entire physical device, create and delete non-default MDCs,
        and assign interfaces, CPU resources, storage space, and memory space to non-default MDCs.

        Non-default MDC: No MDCs can be created on a non-default MDC.
        Administrators of non-default MDCs can only manage and maintain their respective MDCs.
        A non-default MDC can use only the resources assigned to it."
    REVISION "201303051448Z"
    DESCRIPTION
        "The initial revision of this MIB module."
    ::= { ibCommon 136 }


-- Scalar MIB objects, which are considered as global variables
-- Global Level Configuration
IbMdcActionValue ::= TEXTUAL-CONVENTION
    STATUS current
    DESCRIPTION
        "start: start the MDC
         stop: stop the MDC"
    SYNTAX INTEGER
        {
            start(1),
            stop(2)
        }

IbMdcRunStatus ::= TEXTUAL-CONVENTION
    STATUS current
    DESCRIPTION
        "Status of the MDC:
        inactive: The MDC is stopped or not started yet.
        starting: The device is executing the mdc start command to start the MDC.
        active: The MDC is operating properly.
        stopping: The device is executing the undo mdc start command to stop the MDC.
        updating: The device is executing the location command to authorize the MDC to use an interface card."
    SYNTAX INTEGER
        {
            inactive(1),
            starting(2),
            active(3),
            stopping(4),
            updating(5)
        }


-- Node definitions

ibMDCScalarObjects OBJECT IDENTIFIER ::= { ibMDC 1 }

ibMDCMaxMDCNum OBJECT-TYPE
    SYNTAX Integer32
    MAX-ACCESS read-only
    STATUS current
    DESCRIPTION
        "The maximum number of MDCs which the system supported to create."
    ::= { ibMDCScalarObjects 1 }


ibMDCCurrentMDCNum OBJECT-TYPE
    SYNTAX Integer32
    MAX-ACCESS read-only
    STATUS current
    DESCRIPTION
        "The current number of MDCs which the system has created."
    ::= { ibMDCScalarObjects 2 }

ibMDCTables OBJECT IDENTIFIER ::= { ibMDC 2 }

-- The operation and information for MDC.
ibMDCControl OBJECT IDENTIFIER ::= { ibMDCTables 1 }


ibMDCControlTable OBJECT-TYPE
    SYNTAX SEQUENCE OF IbMDCControlEntry
    MAX-ACCESS not-accessible
    STATUS current
    DESCRIPTION
        "This table is used to configure MDCs for a device and show MDC's status."
    ::= { ibMDCControl 1 }


ibMDCControlEntry OBJECT-TYPE
    SYNTAX IbMDCControlEntry
    MAX-ACCESS not-accessible
    STATUS current
    DESCRIPTION
        "An entry of the ibMDCControlTable, every entry is corresponding with an MDC."
    INDEX { ibMDCIndex }
    ::= { ibMDCControlTable 1 }


IbMDCControlEntry ::=
    SEQUENCE
        {
            ibMDCIndex
                Integer32,
            ibMDCName
                DisplayString,
            ibMDCAction
                IbMdcActionValue,
            ibMDCStatus
                IbMdcRunStatus,
            ibMDCRowStatus
                RowStatus
        }

ibMDCIndex OBJECT-TYPE
    SYNTAX Integer32 (1..2147483647)
    MAX-ACCESS accessible-for-notify
    STATUS current
    DESCRIPTION
        "MDC ID is used as MDCIndex, the value range of MDC ID depends on the device model.
         MDCIndex cannot be modified after creation."
    ::= { ibMDCControlEntry 1 }


ibMDCName OBJECT-TYPE
    SYNTAX DisplayString (SIZE (1..15))
    MAX-ACCESS read-create
    STATUS current
    DESCRIPTION
        "Specifies the MDC name, a case-sensitive string of 1 to 15 characters.
        The MDC name cannot be modified after creation."
    ::= { ibMDCControlEntry 2 }


ibMDCAction OBJECT-TYPE
    SYNTAX IbMdcActionValue
    MAX-ACCESS read-write
    STATUS current
    DESCRIPTION
        "State of MDC action: start/stop.
        After an MDC is started, administrators of the MDC can log in to
        the MDC for MDC configuration and maintenance.
        Stopping an MDC interrupts all services on the MDC and logs out
        all users of the MDC.

        Non-default MDC cannot operate."
    DEFVAL { stop }
    ::= { ibMDCControlEntry 3 }


ibMDCStatus OBJECT-TYPE
    SYNTAX IbMdcRunStatus
    MAX-ACCESS read-only
    STATUS current
    DESCRIPTION
        "Status of MDCs."
    ::= { ibMDCControlEntry 4 }


ibMDCRowStatus OBJECT-TYPE
    SYNTAX RowStatus
    MAX-ACCESS read-create
    STATUS current
    DESCRIPTION
        "The status of this table entry.
        Only support active, createAndGo and destroy."
    ::= { ibMDCControlEntry 5 }


ibMDCResource OBJECT IDENTIFIER ::= { ibMDCTables 2 }


ibMDCDISKResourceTable OBJECT-TYPE
    SYNTAX SEQUENCE OF IbMDCDISKResourceEntry
    MAX-ACCESS not-accessible
    STATUS current
    DESCRIPTION
        "This table is for disk resource management:
        Specify a disk space percentage for an MDC and display the disk space usage.

        Default: All MDCs share the disk space in the system,
        and an MDC can use all free disk space in the system.

        Non-default MDC can only query the disk space usage."
    ::= { ibMDCResource 1 }


ibMDCDISKResourceEntry OBJECT-TYPE
    SYNTAX IbMDCDISKResourceEntry
    MAX-ACCESS not-accessible
    STATUS current
    DESCRIPTION
        "An entry of the ibMDCDISKResourceTable, every entry is corresponding to
        disk resource of an MDC.

        Note that only entPhysicalIndex values that represent
        physical boards (i.e., associated entPhysicalClass value is
        'module(9)') are permitted to exist in this table."
    INDEX { entPhysicalIndex, ibMDCIndex, ibMDCDISKResourceInstance }
    ::= { ibMDCDISKResourceTable 1 }


IbMDCDISKResourceEntry ::=
    SEQUENCE {
        ibMDCDISKResourceInstance
            Integer32,
        ibMDCDISKResourceInstanceName
            DisplayString,
        ibMDCDISKResourceMinLimit
            Integer32,
        ibMDCDISKResourceMaxLimit
            Integer32,
        ibMDCDISKResourceReserve
            Unsigned32,
        ibMDCDISKResourceQuota
            Unsigned32,
        ibMDCDISKResourceUsage
            Unsigned32,
        ibMDCDISKResourceAvailable
            Unsigned32
     }

ibMDCDISKResourceInstance OBJECT-TYPE
    SYNTAX Integer32 (1..2147483647)
    MAX-ACCESS not-accessible
    STATUS current
    DESCRIPTION
        "Instance index of disk resource.
         Different instances for disk: Flash, CF cards."
    ::= { ibMDCDISKResourceEntry 1 }


ibMDCDISKResourceInstanceName OBJECT-TYPE
    SYNTAX DisplayString (SIZE (1..32))
    MAX-ACCESS read-only
    STATUS current
    DESCRIPTION
        "Instance name of disk resource.

        Such as: Flash, CF cards."
    ::= { ibMDCDISKResourceEntry 2 }


ibMDCDISKResourceMinLimit OBJECT-TYPE
    SYNTAX Integer32 (0..100)
    UNITS       "percent"
    MAX-ACCESS read-write
    STATUS current
    DESCRIPTION
        "Limit minimum (reserve resources, must be all 0)."
    ::= { ibMDCDISKResourceEntry 3 }


ibMDCDISKResourceMaxLimit OBJECT-TYPE
    SYNTAX Integer32 (1..100)
    UNITS       "percent"
    MAX-ACCESS read-write
    STATUS current
    DESCRIPTION
        "Maximum of available resources of disk.
        Make sure the disk space amount assigned to an MDC is
        greater than the disk space amount the MDC is using.
        Non-default MDC cannot set"
    ::= { ibMDCDISKResourceEntry 4 }

ibMDCDISKResourceReserve OBJECT-TYPE
    SYNTAX Unsigned32
    UNITS       "KB"
    MAX-ACCESS read-only
    STATUS current
    DESCRIPTION
        "The reserve limit resources of disk."
    ::= { ibMDCDISKResourceEntry 5 }

ibMDCDISKResourceQuota OBJECT-TYPE
    SYNTAX Unsigned32
    UNITS       "KB"
    MAX-ACCESS read-only
    STATUS current
    DESCRIPTION
        "The total limit resources of disk according to ibMDCDiskResourceMaxLimit."
    ::= { ibMDCDISKResourceEntry 6 }


ibMDCDISKResourceUsage OBJECT-TYPE
    SYNTAX Unsigned32
    UNITS       "KB"
    MAX-ACCESS read-only
    STATUS current
    DESCRIPTION
        "Current usage of disk resources."
    ::= { ibMDCDISKResourceEntry 7 }


ibMDCDISKResourceAvailable OBJECT-TYPE
    SYNTAX Unsigned32
    UNITS       "KB"
    MAX-ACCESS read-only
    STATUS current
    DESCRIPTION
        "Current available resources of disk."
    ::= { ibMDCDISKResourceEntry 8 }

ibMDCMemoryResourceTable OBJECT-TYPE
    SYNTAX SEQUENCE OF IbMDCMemoryResourceEntry
    MAX-ACCESS not-accessible
    STATUS current
    DESCRIPTION
        "This table is for memory resource management:
         Specify a memory space percentage for an MDC and display the memory space usage.
         Default: All MDCs share the memory space in the system, and an MDC can use all free memory.

         Non-default MDC can only query resource message of memory."
    ::= { ibMDCResource 2 }


ibMDCMemoryResourceEntry OBJECT-TYPE
    SYNTAX IbMDCMemoryResourceEntry
    MAX-ACCESS not-accessible
    STATUS current
    DESCRIPTION
        "An entry of the ibMDCMemoryResourceTable, every entry is corresponding
        with memory resource of an MDC.

        Note that only entPhysicalIndex values that represent
        physical boards (i.e., associated entPhysicalClass value is
        'module(9)') are permitted to exist in this table."
    INDEX { entPhysicalIndex, ibMDCIndex }
    ::= { ibMDCMemoryResourceTable 1 }


IbMDCMemoryResourceEntry ::=
    SEQUENCE {
        ibMDCMemoryResourceMinLimit
            Integer32,
        ibMDCMemoryResourceMaxLimit
            Integer32,
        ibMDCMemoryResourceReserve
            Unsigned32,
        ibMDCMemoryResourceQuota
            Unsigned32,
        ibMDCMemoryResourceUsage
            Unsigned32,
        ibMDCMemoryResourceAvailable
            Unsigned32
     }

ibMDCMemoryResourceMinLimit OBJECT-TYPE
    SYNTAX Integer32 (0..100)
    UNITS       "percent"
    MAX-ACCESS read-write
    STATUS current
    DESCRIPTION
        "Limit minimum(reserve resources, must be all 0).

        Non-default MDC cannot set."
    ::= { ibMDCMemoryResourceEntry 1 }


ibMDCMemoryResourceMaxLimit OBJECT-TYPE
    SYNTAX Integer32 (1..100)
    UNITS       "percent"
    MAX-ACCESS read-write
    STATUS current
    DESCRIPTION
        "Maximum of available resources of memory,
        it specifies the ratio of the memory space that an MDC can use.
        Make sure this amount is sufficient for the MDC to operate properly.
        Non-default MDC cannot set."
    ::= { ibMDCMemoryResourceEntry 2 }

ibMDCMemoryResourceReserve OBJECT-TYPE
    SYNTAX Unsigned32
    UNITS       "KB"
    MAX-ACCESS read-only
    STATUS current
    DESCRIPTION
        "The reserve limit resources of memory."
    ::= { ibMDCMemoryResourceEntry 3 }

ibMDCMemoryResourceQuota OBJECT-TYPE
    SYNTAX Unsigned32
    UNITS       "KB"
    MAX-ACCESS read-only
    STATUS current
    DESCRIPTION
        "The total limit resources of memory."
    ::= { ibMDCMemoryResourceEntry 4 }

ibMDCMemoryResourceUsage OBJECT-TYPE
    SYNTAX Unsigned32
    UNITS       "KB"
    MAX-ACCESS read-only
    STATUS current
    DESCRIPTION
        "Current usage of memory resources."
    ::= { ibMDCMemoryResourceEntry 5 }

ibMDCMemoryResourceAvailable OBJECT-TYPE
    SYNTAX Unsigned32
    UNITS       "KB"
    MAX-ACCESS read-only
    STATUS current
    DESCRIPTION
        "Current available value of memory resources."
    ::= { ibMDCMemoryResourceEntry 6 }

ibMDCCPUResourceTable OBJECT-TYPE
    SYNTAX SEQUENCE OF IbMDCCPUResourceEntry
    MAX-ACCESS not-accessible
    STATUS current
    DESCRIPTION
        "This table is for CPU resource management:
        Specify a CPU weight for an MDC and display the CPU usage.
        The amount of CPU resources an MDC can use depends on the CPU weight
        settings for all MDCs that share the same CPU.

        Non-default MDC can only query CPU resources."
    ::= { ibMDCResource 3 }


ibMDCCPUResourceEntry OBJECT-TYPE
    SYNTAX IbMDCCPUResourceEntry
    MAX-ACCESS not-accessible
    STATUS current
    DESCRIPTION
        "An entry of the ibMDCCPUResourceTable, every entry is corresponding
        with CPU resources of an MDC.

        Note that only entPhysicalIndex values that represent
        physical boards (i.e., associated entPhysicalClass value is
        'module(9)') are permitted to exist in this table."
    INDEX {entPhysicalIndex, ibMDCIndex }
    ::= { ibMDCCPUResourceTable 1 }


IbMDCCPUResourceEntry ::=
    SEQUENCE {
        ibMDCCPUResourceLimit
            Integer32,
        ibMDCCPUResourceUsage
            Integer32
     }

ibMDCCPUResourceLimit OBJECT-TYPE
    SYNTAX Integer32 (1..10)
    UNITS     "weight"
    MAX-ACCESS read-write
    STATUS current
    DESCRIPTION
        "CPU weight-maximum of available resources of CPU,
        this number specifies a CPU weight for an MDC.
        Non-default MDC cannot set."
    ::= { ibMDCCPUResourceEntry 1 }


ibMDCCPUResourceUsage OBJECT-TYPE
    SYNTAX Integer32 (0..100)
    UNITS    "percent"
    MAX-ACCESS read-only
    STATUS current
    DESCRIPTION
        "the CPU usage"
    ::= { ibMDCCPUResourceEntry 2 }


-- The MDC location status.
ibMDCLocation OBJECT IDENTIFIER ::= { ibMDCTables 3 }

ibMDCLocationTable OBJECT-TYPE
    SYNTAX SEQUENCE OF IbMDCLocationEntry
    MAX-ACCESS not-accessible
    STATUS current
    DESCRIPTION
        "This table is for location management:
        Authorize an MDC to use an interface card and query state of location.
        To assign physical interfaces to an MDC, administrators must authorize the MDC
        to use the interface cards to which the physical interfaces belong.

        Default: All interface cards of the device belong to the default MDC,
        and a non-default MDC cannot use any interface card.
        Non-default MDC can only query location state."
    ::= { ibMDCLocation 1 }


ibMDCLocationEntry OBJECT-TYPE
    SYNTAX IbMDCLocationEntry
    MAX-ACCESS not-accessible
    STATUS current
    DESCRIPTION
        "An entry of the ibMDCLocationTable, every entry is the status
        whether an MDC has been Authorized to use the interface cards.

        Note that only entPhysicalIndex values that represent
        physical boards (i.e., associated entPhysicalClass value is
        'module(9)') are permitted to exist in this table."
    INDEX { entPhysicalIndex, ibMDCIndex }
    ::= { ibMDCLocationTable 1 }


IbMDCLocationEntry ::=
    SEQUENCE {
        ibMDCLocationStatus
            TruthValue
     }

ibMDCLocationStatus OBJECT-TYPE
    SYNTAX TruthValue
    MAX-ACCESS read-write
    STATUS current
    DESCRIPTION
        "To authorize the MDC to use the interface cards, set the value
        of this object to 'true (1)'.  To cancel the authorization, set this
        value to 'false (2)'.

        Note that the return noError means the command is being executed.
        For the execution result, check ibMDCLocationStatus."
    ::= { ibMDCLocationEntry 1 }


-- The interfaces allocate information.
ibMDCAllocate OBJECT IDENTIFIER ::= { ibMDCTables 4 }

ibMDCGroupIfTable OBJECT-TYPE
    SYNTAX SEQUENCE OF IbMDCGroupIfEntry
    MAX-ACCESS not-accessible
    STATUS current
    DESCRIPTION
        "This table indication of relation between interfaces and groups,
        which helps to realize the allocation, together with ibMDCAllocateTable.

        Non-default MDC cannot operate."
    ::= { ibMDCAllocate 1 }


ibMDCGroupIfEntry OBJECT-TYPE
    SYNTAX IbMDCGroupIfEntry
    MAX-ACCESS not-accessible
    STATUS current
    DESCRIPTION
        "An entry of the ibMDCGroupIfTable, every entry is the relationship
        between interfaces and groups.

        Due to hardware restrictions, the interfaces on some interface cards are grouped.
        The interfaces in a group must be assigned to the same MDC at the same time or
        removed from an MDC at the same time. Interface grouping depends on the device model.

        This table is used for ibMDCAllocateTable to show interfae group lists.

        Note that only entPhysicalIndex values that represent
        physical ports (i.e., associated entPhysicalClass value is
        'port(10)') are permitted to exist in this table."
    INDEX { entPhysicalIndex }
    ::= { ibMDCGroupIfTable 1 }


IbMDCGroupIfEntry ::=
    SEQUENCE {
        ibMDCGroupIdentity
            Integer32
     }

ibMDCGroupIdentity OBJECT-TYPE
    SYNTAX Integer32
    MAX-ACCESS read-only
    STATUS current
    DESCRIPTION
        "The interface group ID. There are two parts for this id
         depicted as follows:

         31                  7                  0
         +++++++++++++++++++++++++++++++++++++++++
         +   entity index    +    group index    +
         +   ( bit 8..31 )       ( bit 0..7 )    +
         +++++++++++++++++++++++++++++++++++++++++

         From bit0 to bit7 (one byte), it is interfaces group index.

         From bit8 to bit31 (three bytes), it is the physical index
         the same as the entPhysicalIndex specified in ENTITY-MIB.
         Note that only entPhysicalIndex values that represent
         physical boards (i.e., associated entPhysicalClass value is
         'module(9)') are permitted to exist in this table."
    ::= { ibMDCGroupIfEntry 2 }

ibMDCAllocateTable OBJECT-TYPE
    SYNTAX SEQUENCE OF IbMDCAllocateEntry
    MAX-ACCESS not-accessible
    STATUS current
    DESCRIPTION
        "This table is used to assigning a physical interface to an MDC.
        It is allowed that allocate interfaces to a non-default MDC from the default MDC,
        and allocate interfaces back to the default MDC from a non-default MDC.

        All physical interfaces on the device belong to the default MDC,
        and a non-default MDC has no physical interfaces to use.
        Multiple physical interfaces can be assigned to a non-default MDC.
        A physical interface must meet the following conditions to be assigned to a non-default MDC:
        1. Belongs to the default MDC.
        2. Not the console or AUX port.
        3. Not the management Ethernet interface.
        4. Not in an interface group with an interface assigned to another MDC.
        5. The default MDC uses only the physical interfaces that are not assigned to a non-default MDC.

        Non-default MDC cannot set this table."
    ::= { ibMDCAllocate 2 }


ibMDCAllocateEntry OBJECT-TYPE
    SYNTAX IbMDCAllocateEntry
    MAX-ACCESS not-accessible
    STATUS current
    DESCRIPTION
        "An entry of the ibMDCAllocateTable, every entry is the status
        whether physical interfaces have been assigned to an MDC."
    INDEX { ibMDCAllocateGroupIndex }
    ::= { ibMDCAllocateTable 1 }


IbMDCAllocateEntry ::=
    SEQUENCE {
        ibMDCAllocateGroupIndex
            Integer32,
        ibMDCAllocateGroupDescription
            DisplayString,
        ibMDCAllocateMDCId
            Integer32
     }

ibMDCAllocateGroupIndex OBJECT-TYPE
    SYNTAX Integer32 (-2147483648..2147483647)
    MAX-ACCESS not-accessible
    STATUS current
    DESCRIPTION
        "The interface group ID, the same as ibMDCGroupIdentity.
         There are two parts for this id.

         depicted as follows:
         31                  7                  0
         +++++++++++++++++++++++++++++++++++++++++
         +   entity index    +    group index    +
         +   ( bit 8..31 )       ( bit 0..7 )    +
         +++++++++++++++++++++++++++++++++++++++++

         From bit0 to bit7 (one byte), it is interfaces group index.

         From bit8 to bit31 (three bytes), it is the physical index
         the same as the entPhysicalIndex specified in ENTITY-MIB.
         Note that only entPhysicalIndex values that represent
         physical boards (i.e., associated entPhysicalClass value is
         'module(9)') are permitted to exist in this table."
    ::= { ibMDCAllocateEntry 1 }

ibMDCAllocateGroupDescription OBJECT-TYPE
    SYNTAX DisplayString (SIZE (1..255))
    MAX-ACCESS read-only
    STATUS current
    DESCRIPTION
        "Interfaces list
        Such as:
        GigabitEthernet4/5/0/1 to GigabitEthernet4/5/0/24,
        GigabitEthernet4/5/0/48"
    ::= { ibMDCAllocateEntry 2 }


ibMDCAllocateMDCId OBJECT-TYPE
    SYNTAX Integer32 (1..2147483647)
    MAX-ACCESS read-write
    STATUS current
    DESCRIPTION
        "MDC ID is used as ibMDCAllocateMDCId.
        Default MDC: It is allowed that allocate interfaces to non-default MDC from
        the default MDC, and allocate interfaces back to the default MDC from
        a non-default MDC.
        Non-default MDC cannot set allocation, can only query grouping of own MDC."
    ::= { ibMDCAllocateEntry 3 }


ibMDCNotification OBJECT IDENTIFIER ::= { ibMDC 3 }

ibMDCNotificationObjects OBJECT IDENTIFIER ::= { ibMDCNotification 0 }

ibMDCStateChangeToActive NOTIFICATION-TYPE
    OBJECTS {ibMDCIndex, ibMDCName}
    STATUS current
    DESCRIPTION
        "The ibMDCStateChangeToActive trap indicates that the MDC status has changed to active."
    ::= { ibMDCNotificationObjects 1 }

ibMDCStateChangeToInactive NOTIFICATION-TYPE
    OBJECTS {ibMDCIndex, ibMDCName}
    STATUS current
    DESCRIPTION
        "The ibMDCStateChangeToInactive trap indicates that the MDC status has changed to inactive."
    ::= { ibMDCNotificationObjects 2 }

END
