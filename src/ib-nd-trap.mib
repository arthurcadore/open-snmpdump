-- ============================================================================
-- Copyright (C) 2023 Intelbras S.A. All rights reserved.
--
-- Description: The purpose of this MIB file is to provide the definition of
--              the Neighbor Discovery general configuration.
-- Reference:
-- Version: V1.2
-- History:
-- V1.0 2022-01-06
--   Initial version, created by qiankangkang
-- V1.1 2022-06-01
--   Added ibNDTrapRatelimitOverspeed by shaojunjun
-- V1.2 2023-04-20
--   Added ibNDTrapPktQueThresholdAlarm, ibNDTrapPktQueThresholdResume and
--   ibNDTrapPktQueueObjects by yuanyuchen
-- ============================================================================

IB-ND-TRAP-MIB DEFINITIONS ::= BEGIN

IMPORTS
        ibCommon
    FROM IB-OID-MIB
        Unsigned32, OBJECT-TYPE, MODULE-IDENTITY, NOTIFICATION-TYPE
    FROM SNMPv2-SMI
        DisplayString
    FROM SNMPv2-TC;

-- Node definitions
ibNDTrap MODULE-IDENTITY
    LAST-UPDATED "202304201730Z"        -- ARP 20, 2023 at 17:30 GMT
    ORGANIZATION
        "Intelbras S.A. Industria de Telecomunicacao Eletronica Brasileria."
    CONTACT-INFO
        ""
    DESCRIPTION
        "Added ibNDTrapRatelimitOverspeed."
    REVISION "202304201730Z"        -- ARP 20, 2023 at 17:30 GMT
    DESCRIPTION
        "Add ibNDTrapPktQueThresholdAlarm, ibNDTrapPktQueThresholdResume
         and ibNDTrapPktQueueObjects."
    REVISION "202206011700Z"        -- JUN 01, 2022 at 17:00 GMT
    DESCRIPTION
        "This MIB file defines the ND warning feature only."
    REVISION "202201061800Z"
    DESCRIPTION
        "The initial version of this MIB file."
    ::= { ibCommon 218}


ibNDTrapEntry OBJECT IDENTIFIER ::= { ibNDTrap 1 }

ibNDTrapEntrys OBJECT IDENTIFIER  ::= { ibNDTrapEntry 0 }

-- ibNDTrapEntrys
ibNDTrapAllThresholdExceed NOTIFICATION-TYPE
    OBJECTS
        {
            ibNDTrapEntryThreshold,
            ibNDTrapEntryDynamicNum,
            ibNDTrapEntryStaticNum,
            ibNDTrapEntryOtherNum
        }
    STATUS      current
    DESCRIPTION
        "The number of ND entries exceeded the threshold."
    ::= { ibNDTrapEntrys 1 }

ibNDTrapAllThresholdResume NOTIFICATION-TYPE
    OBJECTS
        {
            ibNDTrapEntryThreshold,
            ibNDTrapEntryDynamicNum,
            ibNDTrapEntryStaticNum,
            ibNDTrapEntryOtherNum
        }
    STATUS      current
    DESCRIPTION
        "The number of ND entries was restored to the threshold."
    ::= { ibNDTrapEntrys 2 }

ibNDTrapSlotThresholdExceed NOTIFICATION-TYPE
    OBJECTS
        {
            ibNDTrapEntryChassis,
            ibNDTrapEntrySlot,
            ibNDTrapEntryThreshold,
            ibNDTrapEntryDynamicNum
        }
    STATUS      current
    DESCRIPTION
        "The number of ND entries exceeded the threshold of slot."
    ::= { ibNDTrapEntrys 3 }

ibNDTrapSlotThresholdResume NOTIFICATION-TYPE
    OBJECTS
        {
            ibNDTrapEntryChassis,
            ibNDTrapEntrySlot,
            ibNDTrapEntryThreshold,
            ibNDTrapEntryDynamicNum
        }
    STATUS      current
    DESCRIPTION
        "The number of ND entries was restored to the threshold of slot."
    ::= { ibNDTrapEntrys 4 }

ibNDTrapIfThresholdExceed NOTIFICATION-TYPE
    OBJECTS
        {
            ibNDTrapEntryIfName,
            ibNDTrapEntryThreshold,
            ibNDTrapEntryDynamicNum
        }
    STATUS      current
    DESCRIPTION
        "The number of ND entries exceeded the threshold of interface."
    ::= { ibNDTrapEntrys 5 }

ibNDTrapIfThresholdResume NOTIFICATION-TYPE
    OBJECTS
        {
            ibNDTrapEntryIfName,
            ibNDTrapEntryThreshold,
            ibNDTrapEntryDynamicNum
        }
    STATUS      current
    DESCRIPTION
        "The number of ND entries was restored to the threshold of interface."
    ::= { ibNDTrapEntrys 6 }

ibNDTrapSuppThresholdExceed NOTIFICATION-TYPE
    OBJECTS
        {
            ibNDTrapEntryThreshold,
            ibNDTrapEntrySuppNum
        }
    STATUS      current
    DESCRIPTION
        "The number of ND suppression entries exceeded the threshold."
    ::= { ibNDTrapEntrys 7 }

ibNDTrapSuppThresholdResume NOTIFICATION-TYPE
    OBJECTS
        {
            ibNDTrapEntryThreshold,
            ibNDTrapEntrySuppNum
        }
    STATUS      current
    DESCRIPTION
        "The number of ND suppression entries was restored to the threshold."
    ::= { ibNDTrapEntrys 8 }

ibNDTrapEntryObjects OBJECT IDENTIFIER  ::= { ibNDTrapEntry 1 }

-- ibNDTrapEntryObjects
ibNDTrapEntryChassis OBJECT-TYPE
    SYNTAX      Unsigned32
    MAX-ACCESS  accessible-for-notify
    STATUS      current
    DESCRIPTION
        "The number of chassis. If the value is 65535, the device is not
        a stacked device."
    ::= { ibNDTrapEntryObjects 1 }

ibNDTrapEntrySlot OBJECT-TYPE
    SYNTAX      Unsigned32
    MAX-ACCESS  accessible-for-notify
    STATUS      current
    DESCRIPTION
        "The number of slot."
    ::= { ibNDTrapEntryObjects 2 }

ibNDTrapEntryIfName OBJECT-TYPE
    SYNTAX      DisplayString(SIZE (0..255))
    MAX-ACCESS  accessible-for-notify
    STATUS      current
    DESCRIPTION
        "The name of interface."
    ::= { ibNDTrapEntryObjects 3 }

ibNDTrapEntryThreshold OBJECT-TYPE
    SYNTAX      Unsigned32
    MAX-ACCESS  accessible-for-notify
    STATUS      current
    DESCRIPTION
        "The number of ND entries threshold."
    ::= { ibNDTrapEntryObjects 4 }

ibNDTrapEntryDynamicNum OBJECT-TYPE
    SYNTAX      Unsigned32
    MAX-ACCESS  accessible-for-notify
    STATUS      current
    DESCRIPTION
        "The number of dynamic ND entries."
    ::= { ibNDTrapEntryObjects 5 }

ibNDTrapEntryStaticNum OBJECT-TYPE
    SYNTAX      Unsigned32
    MAX-ACCESS  accessible-for-notify
    STATUS      current
    DESCRIPTION
        "The number of static ND entries."
    ::= { ibNDTrapEntryObjects 6 }

ibNDTrapEntryOtherNum OBJECT-TYPE
    SYNTAX      Unsigned32
    MAX-ACCESS  accessible-for-notify
    STATUS      current
    DESCRIPTION
        "The number of other ND entries."
    ::= { ibNDTrapEntryObjects 7 }

ibNDTrapEntrySuppNum OBJECT-TYPE
    SYNTAX      Unsigned32
    MAX-ACCESS  accessible-for-notify
    STATUS      current
    DESCRIPTION
        "The number of ND suppression entries."
    ::= { ibNDTrapEntryObjects 8 }

ibNDTrapPkt OBJECT IDENTIFIER  ::= { ibNDTrap 2 }

-- ibNDTrapPkt
ibNDTrapPkts OBJECT IDENTIFIER ::= { ibNDTrapPkt 0 }

-- ibNDTrapPkts
ibNDTrapPktSpeedAlarm NOTIFICATION-TYPE
    OBJECTS
        {
            ibNDTrapPktSpeedChassis,
            ibNDTrapPktSpeedSlot,
            ibNDTrapPktSpeedSupValue,
            ibNDTrapPktSpeedCurValue,
            ibNDTrapPktSpeedSupType
        }
    STATUS      current
    DESCRIPTION
        "Send ND packets speed exceeds the limit."
    ::= { ibNDTrapPkts 1 }

ibNDTrapPktSpeedAlarmResume NOTIFICATION-TYPE
    OBJECTS
        {
            ibNDTrapPktSpeedChassis,
            ibNDTrapPktSpeedSlot,
            ibNDTrapPktSpeedSupValue,
            ibNDTrapPktSpeedCurValue,
            ibNDTrapPktSpeedSupType
        }
    STATUS      current
    DESCRIPTION
        "The speed of sending nd packets is restored to the limit."
    ::= { ibNDTrapPkts 2 }

ibNDTrapHostIPConflict NOTIFICATION-TYPE
    OBJECTS
        {
            ibNDTrapHostIPCftLocalIPv6,
            ibNDTrapHostIPCftLocalMAC,
            ibNDTrapHostIPCftLocalIf,
            ibNDTrapHostIPCftLocalPevid,
            ibNDTrapHostIPCftLocalCevid,
            ibNDTrapHostIPCftRemoteIPv6,
            ibNDTrapHostIPCftRemoteMAC,
            ibNDTrapHostIPCftRemotePevid,
            ibNDTrapHostIPCftRemoteCevid
        }
    STATUS      current
    DESCRIPTION
        "ND packets Host IPv6 address conflict."
    ::= { ibNDTrapPkts 3 }

ibNDTrapHostIPConflictResume NOTIFICATION-TYPE
    OBJECTS
        {
            ibNDTrapHostIPCftLocalIPv6,
            ibNDTrapHostIPCftLocalMAC,
            ibNDTrapHostIPCftLocalIf,
            ibNDTrapHostIPCftLocalPevid,
            ibNDTrapHostIPCftLocalCevid,
            ibNDTrapHostIPCftRemoteIPv6,
            ibNDTrapHostIPCftRemoteMAC,
            ibNDTrapHostIPCftRemotePevid,
            ibNDTrapHostIPCftRemoteCevid
        }
    STATUS      current
    DESCRIPTION
        "ND packets host IPv6 address conflict resolution."
    ::= { ibNDTrapPkts 4 }

ibNDTrapDuplicateIPv6 NOTIFICATION-TYPE
    OBJECTS
        {
            ibNDTrapDupIPv6NewMac,
            ibNDTrapDupIPv6NewSevid,
            ibNDTrapDupIPv6NewCevid,
            ibNDTrapDupIPv6NewIFName,
            ibNDTrapDupIPv6OldMac,
            ibNDTrapDupIPv6OldSevid,
            ibNDTrapDupIPv6OldCevid,
            ibNDTrapDupIPv6OldIFName,
            ibNDTrapDupIPv6DupAddr
        }
    STATUS      current
    DESCRIPTION
        "Received a conflict packet with a duplicate ipv6 address."
    ::= { ibNDTrapPkts 5 }

-- ibNDTrapPktSpeedObjects
ibNDTrapPktSpeedObjects OBJECT IDENTIFIER ::= { ibNDTrapPkt 1 }

ibNDTrapPktSpeedChassis OBJECT-TYPE
    SYNTAX      Unsigned32
    MAX-ACCESS  accessible-for-notify
    STATUS      current
    DESCRIPTION
        "The chassis id of nd packets. If the value is 65535, the device is not
        a stacked device."
    ::= { ibNDTrapPktSpeedObjects 1 }

ibNDTrapPktSpeedSlot OBJECT-TYPE
    SYNTAX      Unsigned32
    MAX-ACCESS  accessible-for-notify
    STATUS      current
    DESCRIPTION
        "The slot id of nd packets."
    ::= { ibNDTrapPktSpeedObjects 2 }

ibNDTrapPktSpeedSupValue OBJECT-TYPE
    SYNTAX      Unsigned32
    MAX-ACCESS  accessible-for-notify
    STATUS      current
    DESCRIPTION
        "The limit speed of nd packets."
    ::= { ibNDTrapPktSpeedObjects 3 }

ibNDTrapPktSpeedCurValue OBJECT-TYPE
    SYNTAX      Unsigned32
    MAX-ACCESS  accessible-for-notify
    STATUS      current
    DESCRIPTION
        "The current speed of nd packets."
    ::= { ibNDTrapPktSpeedObjects 4 }

ibNDTrapPktSpeedSupType OBJECT-TYPE
    SYNTAX      OCTET STRING(SIZE(1..48))
    MAX-ACCESS  accessible-for-notify
    STATUS      current
    DESCRIPTION
        "The speed limit type of nd packets."
    ::= { ibNDTrapPktSpeedObjects 5 }

-- ibNDTrapHostIPConflictObjs
ibNDTrapHostIPConflictObjs OBJECT IDENTIFIER ::= { ibNDTrapPkt 2 }

ibNDTrapHostIPCftLocalIPv6 OBJECT-TYPE
    SYNTAX      OCTET STRING(SIZE(1..48))
    MAX-ACCESS  accessible-for-notify
    STATUS      current
    DESCRIPTION
        "The ipv6 address of local device."
    ::= { ibNDTrapHostIPConflictObjs 1 }

ibNDTrapHostIPCftLocalMAC OBJECT-TYPE
    SYNTAX      OCTET STRING(SIZE(1..48))
    MAX-ACCESS  accessible-for-notify
    STATUS      current
    DESCRIPTION
        "The mac address of local device."
    ::= { ibNDTrapHostIPConflictObjs 2 }

ibNDTrapHostIPCftLocalIf OBJECT-TYPE
    SYNTAX      DisplayString(SIZE (0..255))
    MAX-ACCESS  accessible-for-notify
    STATUS      current
    DESCRIPTION
        "The interface name of local device."
    ::= { ibNDTrapHostIPConflictObjs 3 }

ibNDTrapHostIPCftLocalPevid OBJECT-TYPE
    SYNTAX      Unsigned32
    MAX-ACCESS  accessible-for-notify
    STATUS      current
    DESCRIPTION
        "The interface outer layer vlan id of local device."
    ::= { ibNDTrapHostIPConflictObjs 4 }

ibNDTrapHostIPCftLocalCevid OBJECT-TYPE
    SYNTAX      Unsigned32
    MAX-ACCESS  accessible-for-notify
    STATUS      current
    DESCRIPTION
        "The interface inner layer vlan id of local device."
    ::= { ibNDTrapHostIPConflictObjs 5 }

ibNDTrapHostIPCftRemoteIPv6 OBJECT-TYPE
    SYNTAX      OCTET STRING(SIZE(1..48))
    MAX-ACCESS  accessible-for-notify
    STATUS      current
    DESCRIPTION
        "The ipv6 address of remote device."
    ::= { ibNDTrapHostIPConflictObjs 6 }

ibNDTrapHostIPCftRemoteMAC OBJECT-TYPE
    SYNTAX      OCTET STRING(SIZE(1..48))
    MAX-ACCESS  accessible-for-notify
    STATUS      current
    DESCRIPTION
        "The mac address of remote device."
    ::= { ibNDTrapHostIPConflictObjs 7 }

ibNDTrapHostIPCftRemotePevid OBJECT-TYPE
    SYNTAX      Unsigned32
    MAX-ACCESS  accessible-for-notify
    STATUS      current
    DESCRIPTION
        "The interface outer layer vlan id of remote device."
    ::= { ibNDTrapHostIPConflictObjs 8 }

ibNDTrapHostIPCftRemoteCevid OBJECT-TYPE
    SYNTAX      Unsigned32
    MAX-ACCESS  accessible-for-notify
    STATUS      current
    DESCRIPTION
        "The interface inner layer vlan id of remote device."
    ::= { ibNDTrapHostIPConflictObjs 9 }


-- ibNDTrapDuplicateIPv6Objs
ibNDTrapDuplicateIPv6Objs OBJECT IDENTIFIER ::= { ibNDTrapPkt 3 }

ibNDTrapDupIPv6NewMac OBJECT-TYPE
    SYNTAX      OCTET STRING(SIZE(1..48))
    MAX-ACCESS  accessible-for-notify
    STATUS      current
    DESCRIPTION
        "The mac address of new user."
    ::= { ibNDTrapDuplicateIPv6Objs 1 }

ibNDTrapDupIPv6NewSevid OBJECT-TYPE
    SYNTAX      OCTET STRING(SIZE(1..48))
    MAX-ACCESS  accessible-for-notify
    STATUS      current
    DESCRIPTION
        "The outer layer vlan id of new user."
    ::= { ibNDTrapDuplicateIPv6Objs 2 }

ibNDTrapDupIPv6NewCevid OBJECT-TYPE
    SYNTAX      OCTET STRING(SIZE(1..48))
    MAX-ACCESS  accessible-for-notify
    STATUS      current
    DESCRIPTION
        "The inner layer vlan id of new user."
    ::= { ibNDTrapDuplicateIPv6Objs 3 }

ibNDTrapDupIPv6NewIFName OBJECT-TYPE
    SYNTAX      DisplayString(SIZE (0..255))
    MAX-ACCESS  accessible-for-notify
    STATUS      current
    DESCRIPTION
        "The interface name of new user."
    ::= { ibNDTrapDuplicateIPv6Objs 4 }

ibNDTrapDupIPv6OldMac OBJECT-TYPE
    SYNTAX      OCTET STRING(SIZE(1..48))
    MAX-ACCESS  accessible-for-notify
    STATUS      current
    DESCRIPTION
        "The mac address of old user."
    ::= { ibNDTrapDuplicateIPv6Objs 5 }

ibNDTrapDupIPv6OldSevid OBJECT-TYPE
    SYNTAX      OCTET STRING(SIZE(1..48))
    MAX-ACCESS  accessible-for-notify
    STATUS      current
    DESCRIPTION
        "The outer layer vlan id of old user."
    ::= { ibNDTrapDuplicateIPv6Objs 6 }

ibNDTrapDupIPv6OldCevid OBJECT-TYPE
    SYNTAX      OCTET STRING(SIZE(1..48))
    MAX-ACCESS  accessible-for-notify
    STATUS      current
    DESCRIPTION
        "The inner layer vlan id of old user."
    ::= { ibNDTrapDuplicateIPv6Objs 7 }

ibNDTrapDupIPv6OldIFName OBJECT-TYPE
    SYNTAX      DisplayString(SIZE (0..255))
    MAX-ACCESS  accessible-for-notify
    STATUS      current
    DESCRIPTION
        "The interface name of old user."
    ::= { ibNDTrapDuplicateIPv6Objs 8 }

ibNDTrapDupIPv6DupAddr OBJECT-TYPE
    SYNTAX      OCTET STRING(SIZE(1..48))
    MAX-ACCESS  accessible-for-notify
    STATUS      current
    DESCRIPTION
        "The duplicate ipv6 address."
    ::= { ibNDTrapDuplicateIPv6Objs 9 }

-- ibNDTrapRatelimitOverspeed
ibNDTrapRatelimitOverspeed NOTIFICATION-TYPE
    OBJECTS
        {
            ibNDTrapRatelimitVer,
            ibNDTrapRatelimitCount,
            ibNDTrapRatelimitMsg
        }
    STATUS      current
    DESCRIPTION
        "If the rate of ND packets delivered to the CPU on a device
        exceeds the threshold, a trap message is generated and sent
        to the remote monitoring device."
    ::= { ibNDTrapPkts 6 }

-- ibNDTrapRatelimitObjects
ibNDTrapRatelimitObjects OBJECT IDENTIFIER ::= { ibNDTrapPkt 4 }

ibNDTrapRatelimitVer OBJECT-TYPE
    SYNTAX      Unsigned32
    MAX-ACCESS  accessible-for-notify
    STATUS      current
    DESCRIPTION
        "The version of trap information."
    ::= { ibNDTrapRatelimitObjects 1 }

ibNDTrapRatelimitCount OBJECT-TYPE
    SYNTAX      Unsigned32
    MAX-ACCESS  accessible-for-notify
    STATUS      current
    DESCRIPTION
        "Number of cells in the trap message.  A trap message may contain
        multiple cells, each of which indicates that the rate information of
        ND packets exceeds the threshold."
    ::= { ibNDTrapRatelimitObjects 2 }

ibNDTrapRatelimitMsg OBJECT-TYPE
    SYNTAX      OCTET STRING(SIZE(1..254))
    MAX-ACCESS  accessible-for-notify
    STATUS      current
    DESCRIPTION
        "This object is the cell section in a trap message sent from a
        monitored device.  This object can contain multiple cells.
        This object is in the format of '<cell1><cell2>...'.  Each cell
        consists of 17 octets in the format of
        '<TrapOrigin><IfIndex><OverSpeedValue><Threshold><Interval>'.

        <TrapOrigin> indicates the source of the trap message and has
        size of 1 octet.  It only supports the following values.
        1 - Global.
        2 - Interface.

        <IfIndex> is the index of the interface where the rate of ND packet
        exceeds the threshold and has size of 4 octets.  It is 0xFFFFFFFF
        when <TrapOrigin> is 1(Global).

        <OverSpeedValue> indicates the rate that ND packets are actually
        delivered and has size of 4 octets.

        <Threshold> indicates the threshold that ND packets can be delivered
        to CPU and has size of 4 octets.

        <Interval> indicates the interval that a trap message is sent out
        and has size of 4 octets."

    ::= { ibNDTrapRatelimitObjects 3 }

-- ibNDTrapPktQueThreshold
ibNDTrapPktQueThresholdAlarm NOTIFICATION-TYPE
    OBJECTS
        {
            ibNDTrapPktQueChassis,
            ibNDTrapPktQueSlot,
            ibNDTrapPktQueNum
        }
    STATUS      current
    DESCRIPTION
        "The current size of the ND_PKT queue exceeds the threshold."
    ::= { ibNDTrapPkts 7 }

ibNDTrapPktQueThresholdResume NOTIFICATION-TYPE
    OBJECTS
        {
            ibNDTrapPktQueChassis,
            ibNDTrapPktQueSlot,
            ibNDTrapPktQueNum
        }
    STATUS      current
    DESCRIPTION
        "The current size of the ND_PKT queue drops below the threshold."
    ::= { ibNDTrapPkts 8 }

-- ibNDTrapPktQueueObjects
ibNDTrapPktQueueObjects OBJECT IDENTIFIER ::= { ibNDTrapPkt 5 }

ibNDTrapPktQueChassis OBJECT-TYPE
    SYNTAX      Unsigned32
    MAX-ACCESS  accessible-for-notify
    STATUS      current
    DESCRIPTION
        "The information of chassis ID. If the value is 65535, the device is
         not a stacked device."
    ::= { ibNDTrapPktQueueObjects 1 }

ibNDTrapPktQueSlot OBJECT-TYPE
    SYNTAX      Unsigned32
    MAX-ACCESS  accessible-for-notify
    STATUS      current
    DESCRIPTION
        "The information of slot."
    ::= { ibNDTrapPktQueueObjects 2 }

ibNDTrapPktQueNum OBJECT-TYPE
    SYNTAX      Unsigned32
    MAX-ACCESS  accessible-for-notify
    STATUS      current
    DESCRIPTION
        "The number of packets in the ND_PKT queue."
    ::= { ibNDTrapPktQueueObjects 3 }

END
