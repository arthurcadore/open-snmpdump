-- ====================================================================
-- Copyright (C) 2023 Intelbras S.A. All rights reserved.
--
-- Description: The MIB is designed to get IPsec tunnels' statistic information.
-- Reference:
-- Version: 1.4
-- History:
--   V1.0: The initial version created by Wanghaisheng and Weiyanheng.
--   V1.1: 2017-10-31 Added ibIPsecTunnelStatByDescripV2Table,ibIPsecConnectionStopV2,
--         ibIPsecConnectionStartV2,ibIPsecConnectionStopCntlV2 and
--         ibIPsecConnectionStartCntlV2 by shihaohao
--   V1.2: 2021-04-23 Added by Yangbaotao. This revision is about the node
--         IbIPsecEncryptAlgoV2 and IbIPsecAuthAlgoV2.
--         Deprecated ibIPsecTunIKETunLocalIDVal1V2,
--         ibIPsecTunIKETunRemoteIDVal1V2,added ibIPsecTunIKETunLocalIDVal3V2
--         ibIPsecTunIKETunRemoteIDVal3V2 by Zhaoming.
--   V1.3: 2021-07-14 Added by Fanchuanqi. This revision is about the node
--         IbIPsecEncryptAlgoV2 and IbIPsecAuthAlgoV2.
--         2021-07-19 Added by Zoumingquan. This revision is about the node
--         ibIPsecTunProfileNameV2.
--   V1.4: 2023-09-27 Added by Lijin. This revision is about the node
--         ibIPsecTunStopReasonV2.
-- =====================================================================
IB-IPSEC-MONITOR-V2-MIB DEFINITIONS ::= BEGIN

    IMPORTS
        ifIndex
            FROM RFC1213-MIB
        InterfaceIndex
            FROM IF-MIB
        DisplayString, TEXTUAL-CONVENTION, TruthValue
            FROM SNMPv2-TC
        Integer32, Counter32, Counter64, OBJECT-TYPE,
        MODULE-IDENTITY, Gauge32, NOTIFICATION-TYPE, Unsigned32
            FROM SNMPv2-SMI
        InetAddressType, InetAddress
            FROM INET-ADDRESS-MIB
        MODULE-COMPLIANCE, OBJECT-GROUP, NOTIFICATION-GROUP
            FROM SNMPv2-CONF
        ibCommon
            FROM IB-OID-MIB;

    ibIPsecMonitorV2 MODULE-IDENTITY
        LAST-UPDATED "202309271410Z"
        ORGANIZATION
            "Intelbras S.A. Industria de Telecomunicacao Eletronica Brasileria."
        CONTACT-INFO
            ""
        DESCRIPTION
            "The MIB is designed to get statistic information of IPsec tunnels.
             With this MIB, we can get information of a certain tunnel or all
             tunnels."
         REVISION "202309271410Z"
         DESCRIPTION
            "This revision is about the node ibIPsecTunStopReasonV2."
         REVISION "202107191350Z"
         DESCRIPTION
            "This revision is about the node ibIPsecTunProfileNameV2."
         REVISION "202107141530Z"
         DESCRIPTION
            "This revision is about the node IbIPsecEncryptAlgoV2
             and IbIPsecAuthAlgoV2."
         REVISION "202104231730Z"
         DESCRIPTION
            "This revision is about the node IbIPsecEncryptAlgoV2
             and IbIPsecAuthAlgoV2.Deprecate ibIPsecTunIKETunLocalIDVal1V2,
             ibIPsecTunIKETunRemoteIDVal1V2, add ibIPsecTunIKETunLocalIDVal3V2
             and ibIPsecTunIKETunRemoteIDVal3V2."
         REVISION "201710311650Z"
         DESCRIPTION
            "Add the objects of ibIPsecTunnelStatByDescripV2Table,ibIPsecConnectionStopV2,
            ibIPsecConnectionStartV2,ibIPsecConnectionStopCntlV2 and
            ibIPsecConnectionStartCntlV2."
        REVISION
            "201206270000Z"
        DESCRIPTION
            "Initial version."
        ::= { ibCommon 126 }

    IbIPsecDiffHellmanGrpV2   ::= TEXTUAL-CONVENTION
        STATUS     current
        DESCRIPTION
            "The Diffie Hellman Group used in the IKE and IPsec negotiations.
             invalidGroup(2147483647) is defined as invalid value."
        SYNTAX INTEGER {
            none(0),
            dhGroup1(1),
            dhGroup2(2),
            dhGroup5(5),
            dhGroup14(14),
            dhGroup24(24),
            invalidGroup(2147483647)
        }

    IbIPsecEncapModeV2        ::= TEXTUAL-CONVENTION
        STATUS     current
        DESCRIPTION
            "The encapsulation mode used by an IPsec Phase-2 Tunnel.
             invalidMode(2147483647) is defined as invalid value."
        SYNTAX INTEGER {
            tunnel(1),
            transport(2),
            invalidMode(2147483647)
        }

    IbIPsecEncryptAlgoV2   ::= TEXTUAL-CONVENTION
        STATUS     current
        DESCRIPTION
            "The encryption algorithm used in the IKE and IPsec negotiations.
             invalidAlg(2147483647) is defined as invalid value."
        SYNTAX INTEGER {
            none(0),
            desCbc(1),
            ideaCbc(2),
            blowfishCbc(3),
            rc5R16B64Cbc(4),
            tripleDesCbc(5),
            castCbc(6),
            aesCbc(7),
            nsaCbc(8),
            aesCbc128(9),
            aesCbc192(10),
            aesCbc256(11),
            aesCtr(12),
            aesCamelliaCbc(13),
            rc4(14),
            aesCtr128(15),
            aesCtr192(16),
            aesCtr256(17),
            camelliaCbc128(18),
            camelliaCbc192(19),
            camelliaCbc256(20),
            gmac128(21),
            gmac192(22),
            gmac256(23),
            gcm128(24),
            gcm192(25),
            gcm256(26),
            sm1Cbc128(128),
            sm1Cbc192(129),
            sm1Cbc256(130),
            sm4Cbc(131),
            invalidAlg(2147483647)
        }

    IbIPsecAuthAlgoV2   ::= TEXTUAL-CONVENTION
        STATUS     current
        DESCRIPTION
            "The authentication algorithm used in the IKE negotiations.
             invalidAlg(2147483647) is defined as invalid value."
        SYNTAX INTEGER {
            none(0),
            md5(1),
            sha1(2),
            sha256(3),
            sha384(4),
            sha512(5),
            aesXcbcMac(6),
            sm3(128),
            invalidAlg(2147483647)
        }

    IbIPsecSaProtocolV2   ::= TEXTUAL-CONVENTION
        STATUS     current
        DESCRIPTION
            "The protocol of security association."
        SYNTAX INTEGER {
            reserved(0),
            ah(2),
            esp(3),
            ipcomp(4)
        }

    IbIPsecIDTypeV2   ::= TEXTUAL-CONVENTION
        STATUS     current
        DESCRIPTION
            "The type of IPsec Identity."
        SYNTAX INTEGER {
            reserved(0),
            ipv4Addr(1),
            fqdn(2),         -- fully-qualified domain name
            userFqdn(3),     -- fully-qualified username
            ipv4AddrSubnet(4),
            ipv6Addr(5),
            ipv6AddrSubnet(6),
            ipv4AddrRange(7),
            ipv6AddrRange(8),
            derAsn1Dn(9),    -- the binary DER encoding of an ASN.1 X.500 Distinguished
                             -- Name [X.501] of the princIPal whose certificates are
                             -- being exchanged to establish the SA.
            derAsn1Gn(10),   -- the binary DER encoding of an ASN.1 X.500 GeneralName
                             -- [X.509] of the princIPal whose certificates are being
                             -- exchanged to establish the SA.
            keyId(11)        -- specifies an opaque byte stream which may be used to
                             -- pass vendor-specific information necessary to identify
                             -- which pre-shared key should be used to authenticate
                             -- Aggressive mode negotiations.
        }

    IbIPsecTrafficTypeV2   ::= TEXTUAL-CONVENTION
        STATUS     current
        DESCRIPTION
            "The type of the data flow."
        SYNTAX INTEGER {
            ipv4Addr(1),
            ipv4AddrSubnet(4),
            ipv6Addr(5),
            ipv6AddrSubnet(6),
            ipv4AddrRange(7),
            ipv6AddrRange(8)
        }

    IbIPsecNegoTypeV2   ::= TEXTUAL-CONVENTION
        STATUS     current
        DESCRIPTION
            "The type of key used by an IPsec Phase-2 Tunnel.
            invalidType(2147483647) is defined as invalid value."
        SYNTAX INTEGER {
            ike(1),
            manual(2),
            invalidType(2147483647)
        }

    IbIPsecTunnelStateV2   ::= TEXTUAL-CONVENTION
        STATUS     current
        DESCRIPTION
            "The state of IPsec tunnel."
        SYNTAX INTEGER {
            active(1),
            timeout(2)
        }

    IbIPsecTunnelErrorCodeV2    ::= TEXTUAL-CONVENTION
        STATUS     current
        DESCRIPTION
            "The error code mode."
        SYNTAX INTEGER {
            reserved(1),
            dpdFailure(2),       -- dpd(dead peer detection)
            otherReasons(3)
        }
-- ========================================================================
-- Node definitions
-- ========================================================================
-- Begin the node of ibIPsecObjectsV2.

    ibIPsecObjectsV2 OBJECT IDENTIFIER ::= { ibIPsecMonitorV2 1 }

-- =======================================
-- Begin the ibIPsecScalarObjectsV2.
-- =======================================
    ibIPsecScalarObjectsV2 OBJECT IDENTIFIER ::= { ibIPsecObjectsV2 1 }

    ibIPsecMIBVersion OBJECT-TYPE
        SYNTAX DisplayString(SIZE(0..255))
        MAX-ACCESS read-only
        STATUS current
        DESCRIPTION
            "Version string of this MIB."
        ::= { ibIPsecScalarObjectsV2 1 }

-- ===============================================
-- Begin the table of ibIPsecTunnelV2Table.
-- ===============================================

    ibIPsecTunnelV2Table OBJECT-TYPE
        SYNTAX SEQUENCE OF IbIPsecTunnelV2Entry
        MAX-ACCESS not-accessible
        STATUS current
        DESCRIPTION
            "The IPsec Phase-2 Tunnel Table.  There is one entry in this
             table for each active IPsec Phase-2 Tunnel."
        ::= { ibIPsecObjectsV2 2 }

    ibIPsecTunnelV2Entry OBJECT-TYPE
        SYNTAX IbIPsecTunnelV2Entry
        MAX-ACCESS not-accessible
        STATUS current
        DESCRIPTION
            "Information about ibIPsecTunnelV2Table."
        INDEX { ibIPsecTunIndexV2 }
        ::= { ibIPsecTunnelV2Table 1 }

    IbIPsecTunnelV2Entry ::=
        SEQUENCE {
            ibIPsecTunIndexV2
                Integer32,
            ibIPsecTunIfIndexV2
                InterfaceIndex,
            ibIPsecTunIKETunnelIndexV2
                Integer32,
            ibIPsecTunIKETunLocalIDTypeV2
                IbIPsecIDTypeV2,
            ibIPsecTunIKETunLocalIDVal1V2
                DisplayString,
            ibIPsecTunIKETunLocalIDVal2V2
                DisplayString,
            ibIPsecTunIKETunRemoteIDTypeV2
                IbIPsecIDTypeV2,
            ibIPsecTunIKETunRemoteIDVal1V2
                DisplayString,
            ibIPsecTunIKETunRemoteIDVal2V2
                DisplayString,
            ibIPsecTunLocalAddrTypeV2
                InetAddressType,
            ibIPsecTunLocalAddrV2
                InetAddress,
            ibIPsecTunRemoteAddrTypeV2
                InetAddressType,
            ibIPsecTunRemoteAddrV2
                InetAddress,
            ibIPsecTunKeyTypeV2
                IbIPsecNegoTypeV2,
            ibIPsecTunEncapModeV2
                IbIPsecEncapModeV2,
            ibIPsecTunInitiatorV2
                INTEGER,
            ibIPsecTunLifeSizeV2
                Gauge32,
            ibIPsecTunLifeTimeV2
                Integer32,
            ibIPsecTunRemainTimeV2
                Integer32,
            ibIPsecTunActiveTimeV2
                Integer32,
            ibIPsecTunRemainSizeV2
                Gauge32,
            ibIPsecTunTotalRefreshesV2
                Counter32,
            ibIPsecTunCurrentSaInstancesV2
                Gauge32,
            ibIPsecTunInSaEncryptAlgoV2
                IbIPsecEncryptAlgoV2,
            ibIPsecTunInSaAhAuthAlgoV2
                IbIPsecAuthAlgoV2,
            ibIPsecTunInSaEspAuthAlgoV2
                IbIPsecAuthAlgoV2,
            ibIPsecTunDiffHellmanGrpV2
                IbIPsecDiffHellmanGrpV2,
            ibIPsecTunOutSaEncryptAlgoV2
                IbIPsecEncryptAlgoV2,
            ibIPsecTunOutSaAhAuthAlgoV2
                IbIPsecAuthAlgoV2,
            ibIPsecTunOutSaEspAuthAlgoV2
                IbIPsecAuthAlgoV2,
            ibIPsecTunPolicyNameV2
                OCTET STRING,
            ibIPsecTunPolicyNumV2
                Integer32,
            ibIPsecTunStatusV2
                INTEGER,
            ibIPsecTunPolicyDescriptionV2
                OCTET STRING,
            ibIPsecTunIKETunLocalIDVal3V2
                OCTET STRING,
            ibIPsecTunIKETunRemoteIDVal3V2
                OCTET STRING,
            ibIPsecTunProfileNameV2
                DisplayString
        }

    ibIPsecTunIndexV2 OBJECT-TYPE
        SYNTAX Integer32 (1..2147483647)
        MAX-ACCESS accessible-for-notify
        STATUS current
        DESCRIPTION
            "The index of IPsec Phase-2 Tunnel Table.  The value of
             the index is a number which begins at one and is
             incremented with each tunnel that is created.  The
             value of this object will wrap at 2147483647."
        ::= { ibIPsecTunnelV2Entry 1 }

    ibIPsecTunIfIndexV2 OBJECT-TYPE
        SYNTAX InterfaceIndex
        MAX-ACCESS read-only
        STATUS current
        DESCRIPTION
            "The interface index( the ifIndex of ifTable )."
        ::= { ibIPsecTunnelV2Entry 2 }

    ibIPsecTunIKETunnelIndexV2 OBJECT-TYPE
        SYNTAX Integer32 (1..2147483647)
        MAX-ACCESS read-only
        STATUS current
        DESCRIPTION
            "The index of the associated IPsec Phase-1 IKE Tunnel
             (IKETunIndex in the IKETunnelTable).  2147483647 is defined as
             invalid value."
        ::= { ibIPsecTunnelV2Entry 3 }

    ibIPsecTunIKETunLocalIDTypeV2 OBJECT-TYPE
        SYNTAX IbIPsecIDTypeV2
        MAX-ACCESS read-only
        STATUS current
        DESCRIPTION
            "The type of the local peer identity for the associated IPsec
             Phase-1 IKE Tunnel (IKETunLocalType in the IKETunnelTable)."
        ::= { ibIPsecTunnelV2Entry 4 }

    ibIPsecTunIKETunLocalIDVal1V2 OBJECT-TYPE
        SYNTAX DisplayString(SIZE(0..255))
        MAX-ACCESS read-only
        STATUS deprecated
        DESCRIPTION
            "The value of the local peer identity for the associated IPsec
             Phase-1 IKE Tunnel (IKETunLocalValue1 in the IKETunnelTable).

             If the local peer type is ipv4Addr/ipv6Addr, this is the IP address
             used to identify the local peer.

             If the local peer type is ipv4AddrSubnet/ipv6AddrSubnet, this is
             the subnet address.

             If the local peer type is ipv4AddrRange/ipv6AddrRange, this is
             the beginning IP address of the range.

             If the local peer type is fqdn/userFqdn, this is the host name
             used to identify the local peer.

             If the local peer type is derAsn1Dn, this is the binary DER
             encoding of an ASN.1 X.500 Distinguished Name [X.501] of the
             principal whose certificates are being exchanged to establish
             the SA.

             If the local peer type is derAsn1Gn, this is the binary DER
             encoding of an ASN.1 X.500 GeneralName [X.509] of the principal
             whose certificates are being exchanged to establish the SA.

             If the local peer type is keyId, this is an opaque byte
             stream which may be used to pass vendor-specific information
             necessary to identify which pre-shared key should be used to
             authenticate Aggressive mode negotiations.

             The local peer identity may not exceed 255 characters in length.
             The complete value will be displayed by ibIPsecTunIKETunLocalIDVal3V2"
        ::= { ibIPsecTunnelV2Entry 5 }

    ibIPsecTunIKETunLocalIDVal2V2 OBJECT-TYPE
        SYNTAX DisplayString(SIZE(0..255))
        MAX-ACCESS read-only
        STATUS current
        DESCRIPTION
            "The second specification of the local peer's IP address for the
             associated IPsec Phase-1 IKE Tunnel (IKETunLocalValue2 in the
             IKETunnelTable).

             If the local peer type is ipv4AddrSubnet/ipv6AddrSubnet, this
             is the subnet mask.

             If the local peer type is ipv4AddrRange/ipv6AddrRange, this is
             the ending IP address of the range.

             If the local peer type is others, this is a zero-length string."
        ::= { ibIPsecTunnelV2Entry 6 }

    ibIPsecTunIKETunRemoteIDTypeV2 OBJECT-TYPE
        SYNTAX IbIPsecIDTypeV2
        MAX-ACCESS read-only
        STATUS current
        DESCRIPTION
            "The type of the remote peer identity for the associated IPsec
             Phase-1 IKE Tunnel (IKETunRemoteType in the IKETunnelTable)."
        ::= { ibIPsecTunnelV2Entry 7 }

    ibIPsecTunIKETunRemoteIDVal1V2 OBJECT-TYPE
        SYNTAX DisplayString(SIZE(0..255))
        MAX-ACCESS read-only
        STATUS deprecated
        DESCRIPTION
            "The value of the remote peer identity for the associated IPsec
             Phase-1 IKE Tunnel (IKETunRemoteValue1 in the IKETunnelTable).

             If the remote peer type is ipv4Addr/ipv6Addr, this is the IP address
             used to identify the remote peer.

             If the remote peer type is ipv4AddrSubnet/ipv6AddrSubnet, this is
             the subnet address.

             If the remote peer type is ipv4AddrRange/ipv6AddrRange, this is
             the beginning IP address of the range.

             If the remote peer type is fqdn/userFqdn, this is the host name
             used to identify the remote peer.

             If the remote peer type is derAsn1Dn, this is the binary DER
             encoding of an ASN.1 X.500 Distinguished Name [X.501] of the
             principal whose certificates are being exchanged to establish
             the SA.

             If the remote peer type is derAsn1Gn, this is the binary DER
             encoding of an ASN.1 X.500 GeneralName [X.509] of the principal
             whose certificates are being exchanged to establish the SA.

             If the remote peer type is keyId, this is an opaque byte
             stream which may be used to pass vendor-specific information
             necessary to identify which pre-shared key should be used to
             authenticate Aggressive mode negotiations.

             The remote peer identity may not exceed 255 characters in length.
             The complete value will be displayed by ibIPsecTunIKETunRemoteIDVal3V2"
        ::= { ibIPsecTunnelV2Entry 8 }

    ibIPsecTunIKETunRemoteIDVal2V2 OBJECT-TYPE
        SYNTAX DisplayString(SIZE(0..255))
        MAX-ACCESS read-only
        STATUS current
        DESCRIPTION
            "The second specification of the remote peer's IP address for the
             associated IPsec Phase-1 IKE Tunnel(IKETunRemoteValue2 in the
             IKETunnelTable).

             If the remote peer type is ipv4AddrSubnet/ipv6AddrSubnet, this
             is the subnet mask.

             If the remote peer type is ipv4AddrRange/ipv6AddrRange, this is
             the ending IP address of the range.

             If the remote peer type is others, this is a zero-length string."
        ::= { ibIPsecTunnelV2Entry 9 }

    ibIPsecTunLocalAddrTypeV2 OBJECT-TYPE
        SYNTAX InetAddressType
        MAX-ACCESS read-only
        STATUS current
        DESCRIPTION
            "The type of the IP address for the local peer of the IPsec Phase-2
            Tunnel."
        ::= { ibIPsecTunnelV2Entry 10 }

    ibIPsecTunLocalAddrV2 OBJECT-TYPE
        SYNTAX InetAddress
        MAX-ACCESS read-only
        STATUS current
        DESCRIPTION
            "The IP address of the local peer for the IPsec Phase-2 Tunnel."
        ::= { ibIPsecTunnelV2Entry 11 }

    ibIPsecTunRemoteAddrTypeV2 OBJECT-TYPE
        SYNTAX InetAddressType
        MAX-ACCESS read-only
        STATUS current
        DESCRIPTION
            "The type of the IP address for the remote peer of the IPsec Phase-2
             Tunnel."
        ::= { ibIPsecTunnelV2Entry 12 }

    ibIPsecTunRemoteAddrV2 OBJECT-TYPE
        SYNTAX InetAddress
        MAX-ACCESS read-only
        STATUS current
        DESCRIPTION
            "The IP address of the remote peer for the IPsec Phase-2 Tunnel."
        ::= { ibIPsecTunnelV2Entry 13 }

    ibIPsecTunKeyTypeV2 OBJECT-TYPE
        SYNTAX IbIPsecNegoTypeV2
        MAX-ACCESS read-only
        STATUS current
        DESCRIPTION
            "The key negotiate mode used by the IPsec Phase-2 Tunnel."
        ::= { ibIPsecTunnelV2Entry 14 }

    ibIPsecTunEncapModeV2 OBJECT-TYPE
        SYNTAX IbIPsecEncapModeV2
        MAX-ACCESS read-only
        STATUS current
        DESCRIPTION
            "The encapsulation mode used by the IPsec Phase-2 Tunnel."
        ::= { ibIPsecTunnelV2Entry 15 }

    ibIPsecTunInitiatorV2 OBJECT-TYPE
        SYNTAX INTEGER
            {
                local(1),
                remote(2),
                none(2147483647)
            }
        MAX-ACCESS read-only
        STATUS current
        DESCRIPTION
            "The initiator of this IPsec tunnel.  Value none is used for manual
             IPsec tunnel, for there is no initiator or responder in this method."
        ::= { ibIPsecTunnelV2Entry 16 }

    ibIPsecTunLifeSizeV2 OBJECT-TYPE
        SYNTAX Gauge32
        MAX-ACCESS read-only
        STATUS current
        DESCRIPTION
            "The negotiated LifeSize of the IPsec Phase-2 Tunnel in kilobytes.
             0 is defined as invalid value."
        ::= { ibIPsecTunnelV2Entry 17 }

    ibIPsecTunLifeTimeV2 OBJECT-TYPE
        SYNTAX Integer32 (1..2147483647)
        MAX-ACCESS read-only
        STATUS current
        DESCRIPTION
            "The negotiated LifeTime of the IPsec Phase-2 Tunnel in seconds.
             2147483647 is defined as invalid value."
        ::= { ibIPsecTunnelV2Entry 18 }

    ibIPsecTunRemainTimeV2 OBJECT-TYPE
        SYNTAX Integer32 (0..2147483647)
        MAX-ACCESS read-only
        STATUS current
        DESCRIPTION
            "The remain time of SA in seconds.  2147483647 is defined as invalid
            value."
        ::= { ibIPsecTunnelV2Entry 19 }

    ibIPsecTunActiveTimeV2 OBJECT-TYPE
        SYNTAX Integer32 (0..2147483647)
        MAX-ACCESS read-only
        STATUS current
        DESCRIPTION
            "The duration the IPsec Phase-2 Tunnel has been active in
             hundredths of seconds.  2147483647 is defined as invalid value."
        ::= { ibIPsecTunnelV2Entry 20 }

    ibIPsecTunRemainSizeV2 OBJECT-TYPE
        SYNTAX Gauge32
        MAX-ACCESS read-only
        STATUS current
        DESCRIPTION
            "The remain LifeSize of SA in kilobytes.  0 is defined as
            invalid value."
        ::= { ibIPsecTunnelV2Entry 21 }

    ibIPsecTunTotalRefreshesV2 OBJECT-TYPE
        SYNTAX Counter32
        MAX-ACCESS read-only
        STATUS current
        DESCRIPTION
            "The total number of security association refreshing performed."
        ::= { ibIPsecTunnelV2Entry 22 }

    ibIPsecTunCurrentSaInstancesV2 OBJECT-TYPE
        SYNTAX Gauge32
        MAX-ACCESS read-only
        STATUS current
        DESCRIPTION
            "The number of security associations which are currently active
             or expiring."
        ::= { ibIPsecTunnelV2Entry 23 }

    ibIPsecTunInSaEncryptAlgoV2 OBJECT-TYPE
        SYNTAX IbIPsecEncryptAlgoV2
        MAX-ACCESS read-only
        STATUS current
        DESCRIPTION
            "The encryption algorithm used by the inbound security association
             of the IPsec Phase-2 Tunnel."
        ::= { ibIPsecTunnelV2Entry 24 }

    ibIPsecTunInSaAhAuthAlgoV2 OBJECT-TYPE
        SYNTAX IbIPsecAuthAlgoV2
        MAX-ACCESS read-only
        STATUS current
        DESCRIPTION
            "The authentication algorithm used by the inbound authentication
             header (AH) security association of the IPsec Phase-2 Tunnel."
        ::= { ibIPsecTunnelV2Entry 25 }

    ibIPsecTunInSaEspAuthAlgoV2 OBJECT-TYPE
        SYNTAX IbIPsecAuthAlgoV2
        MAX-ACCESS read-only
        STATUS current
        DESCRIPTION
            "The authentication algorithm used by the inbound encapsulation
             security protocol(ESP) security association of the IPsec
             Phase-2 Tunnel."
        ::= { ibIPsecTunnelV2Entry 26 }

    ibIPsecTunDiffHellmanGrpV2 OBJECT-TYPE
        SYNTAX IbIPsecDiffHellmanGrpV2
        MAX-ACCESS read-only
        STATUS current
        DESCRIPTION
            "The Diffie Hellman Group used by the security association of the
             IPsec Phase-2 Tunnel."
        ::= { ibIPsecTunnelV2Entry 27 }

    ibIPsecTunOutSaEncryptAlgoV2 OBJECT-TYPE
        SYNTAX IbIPsecEncryptAlgoV2
        MAX-ACCESS read-only
        STATUS current
        DESCRIPTION
            "The encryption algorithm used by the outbound security
             association of the IPsec Phase-2 Tunnel."
        ::= { ibIPsecTunnelV2Entry 28 }

    ibIPsecTunOutSaAhAuthAlgoV2 OBJECT-TYPE
        SYNTAX IbIPsecAuthAlgoV2
        MAX-ACCESS read-only
        STATUS current
        DESCRIPTION
            "The authentication algorithm used by the outbound
             authentication header (AH) security association of
             the IPsec Phase-2 Tunnel."
        ::= { ibIPsecTunnelV2Entry 29 }

    ibIPsecTunOutSaEspAuthAlgoV2 OBJECT-TYPE
        SYNTAX IbIPsecAuthAlgoV2
        MAX-ACCESS read-only
        STATUS current
        DESCRIPTION
            "The authentication algorithm used by the outbound encapsulation
             security protocol(ESP) security association of the IPsec
             Phase-2 Tunnel."
        ::= { ibIPsecTunnelV2Entry 30 }

    ibIPsecTunPolicyNameV2 OBJECT-TYPE
        SYNTAX OCTET STRING (SIZE(1..63))
        MAX-ACCESS read-only
        STATUS current
        DESCRIPTION
            "The policy name used by this IPsec tunnel."
        ::= { ibIPsecTunnelV2Entry 31 }

    ibIPsecTunPolicyNumV2 OBJECT-TYPE
        SYNTAX Integer32 (1..2147483647)
        MAX-ACCESS read-only
        STATUS current
        DESCRIPTION
            "The sequence number of policy used by this IPsec tunnel."
        ::= { ibIPsecTunnelV2Entry 32 }

    ibIPsecTunStatusV2 OBJECT-TYPE
        SYNTAX INTEGER
            {
                initial(1),
                ready(2),
                rekeyed(3),
                closed(4)
            }
        MAX-ACCESS read-only
        STATUS current
        DESCRIPTION
            "The status of the IPsec Tunnel."
        ::= { ibIPsecTunnelV2Entry 33 }

    ibIPsecTunPolicyDescriptionV2 OBJECT-TYPE
        SYNTAX OCTET STRING (SIZE(1..80))
        MAX-ACCESS  read-only
        STATUS      current
        DESCRIPTION
            "IPsec policy description of an IPsec tunne."
        ::= { ibIPsecTunnelV2Entry 34 }

    ibIPsecTunIKETunLocalIDVal3V2 OBJECT-TYPE
        SYNTAX OCTET STRING (SIZE(0..2047))
        MAX-ACCESS read-only
        STATUS current
        DESCRIPTION
            "The value of the local peer identity for the associated IPsec
             Phase-1 IKE Tunnel (IKETunLocalValue1 in the IKETunnelTable).

             If the local peer type is ipv4Addr/ipv6Addr, this is the IP address
             used to identify the local peer.

             If the local peer type is ipv4AddrSubnet/ipv6AddrSubnet, this is
             the subnet address.

             If the local peer type is ipv4AddrRange/ipv6AddrRange, this is
             the beginning IP address of the range.

             If the local peer type is fqdn/userFqdn, this is the host name
             used to identify the local peer.

             If the local peer type is derAsn1Dn, this is the binary DER
             encoding of an ASN.1 X.500 Distinguished Name [X.501] of the
             principal whose certificates are being exchanged to establish
             the SA.

             If the local peer type is derAsn1Gn, this is the binary DER
             encoding of an ASN.1 X.500 GeneralName [X.509] of the principal
             whose certificates are being exchanged to establish the SA.

             If the local peer type is keyId, this is an opaque byte
             stream which may be used to pass vendor-specific information
             necessary to identify which pre-shared key should be used to
             authenticate Aggressive mode negotiations."
        ::= { ibIPsecTunnelV2Entry 35 }

    ibIPsecTunIKETunRemoteIDVal3V2 OBJECT-TYPE
        SYNTAX OCTET STRING (SIZE(0..2047))
        MAX-ACCESS read-only
        STATUS current
        DESCRIPTION
            "The value of the remote peer identity for the associated IPsec
             Phase-1 IKE Tunnel (IKETunRemoteValue1 in the IKETunnelTable).

             If the remote peer type is ipv4Addr/ipv6Addr, this is the IP address
             used to identify the remote peer.

             If the remote peer type is ipv4AddrSubnet/ipv6AddrSubnet, this is
             the subnet address.

             If the remote peer type is ipv4AddrRange/ipv6AddrRange, this is
             the beginning IP address of the range.

             If the remote peer type is fqdn/userFqdn, this is the host name
             used to identify the remote peer.

             If the remote peer type is derAsn1Dn, this is the binary DER
             encoding of an ASN.1 X.500 Distinguished Name [X.501] of the
             principal whose certificates are being exchanged to establish
             the SA.

             If the remote peer type is derAsn1Gn, this is the binary DER
             encoding of an ASN.1 X.500 GeneralName [X.509] of the principal
             whose certificates are being exchanged to establish the SA.

             If the remote peer type is keyId, this is an opaque byte
             stream which may be used to pass vendor-specific information
             necessary to identify which pre-shared key should be used to
             authenticate Aggressive mode negotiations."
        ::= { ibIPsecTunnelV2Entry 36 }

    ibIPsecTunProfileNameV2 OBJECT-TYPE
        SYNTAX DisplayString(SIZE(0..255))
        MAX-ACCESS read-only
        STATUS current
        DESCRIPTION
            "The profile name used by this IPsec tunnel."
        ::= { ibIPsecTunnelV2Entry 37 }

-- ===============================================
-- Begin the table of ibIPsecTunnelStatV2Table.
-- ===============================================

    ibIPsecTunnelStatV2Table OBJECT-TYPE
        SYNTAX SEQUENCE OF IbIPsecTunnelStatV2Entry
        MAX-ACCESS not-accessible
        STATUS current
        DESCRIPTION
            "The IPsec Phase-2 Tunnel Statistics Table."
        ::= { ibIPsecObjectsV2 3 }

    ibIPsecTunnelStatV2Entry OBJECT-TYPE
        SYNTAX IbIPsecTunnelStatV2Entry
        MAX-ACCESS not-accessible
        STATUS current
        DESCRIPTION
            "Information about ibIPsecTunnelStatV2Table."
        INDEX { ibIPsecTunIndexV2 }
        ::= { ibIPsecTunnelStatV2Table 1 }

    IbIPsecTunnelStatV2Entry ::=
        SEQUENCE {
            ibIPsecTunInOctetsV2
                Counter64,
            ibIPsecTunInDecompOctetsV2
                Counter64,
            ibIPsecTunInPktsV2
                Counter64,
            ibIPsecTunInDropPktsV2
                Counter64,
            ibIPsecTunInReplayDropPktsV2
                Counter64,
            ibIPsecTunInAuthFailsV2
                Counter64,
            ibIPsecTunInDecryptFailsV2
                Counter64,
            ibIPsecTunOutOctetsV2
                Counter64,
            ibIPsecTunOutUncompOctetsV2
                Counter64,
            ibIPsecTunOutPktsV2
                Counter64,
            ibIPsecTunOutDropPktsV2
                Counter64,
            ibIPsecTunOutEncryptFailsV2
                Counter64,
            ibIPsecTunNoMemoryDropPktsV2
                Counter64,
            ibIPsecTunQueueFullDropPktsV2
                Counter64,
            ibIPsecTunInvalidLenDropPktsV2
                Counter64,
            ibIPsecTunTooLongDropPktsV2
                Counter64,
            ibIPsecTunInvalidSaDropPktsV2
                Counter64
        }

    ibIPsecTunInOctetsV2 OBJECT-TYPE
        SYNTAX Counter64
        MAX-ACCESS read-only
        STATUS current
        DESCRIPTION
            "The total number of octets received by this IPsec Phase-2 Tunnel.
             This value is accumulated BEFORE determining whether or not the
             packet should be decompressed."
        ::= { ibIPsecTunnelStatV2Entry 1 }

    ibIPsecTunInDecompOctetsV2 OBJECT-TYPE
        SYNTAX Counter64
        MAX-ACCESS read-only
        STATUS current
        DESCRIPTION
            "The total number of decompressed octets received by this IPsec
             Phase-2 Tunnel.  This value is accumulated AFTER the packet
             is decompressed."
        ::= { ibIPsecTunnelStatV2Entry 2 }

    ibIPsecTunInPktsV2 OBJECT-TYPE
        SYNTAX Counter64
        MAX-ACCESS read-only
        STATUS current
        DESCRIPTION
            "The total number of packets received by this IPsec Phase-2 Tunnel."
        ::= { ibIPsecTunnelStatV2Entry 3 }

    ibIPsecTunInDropPktsV2 OBJECT-TYPE
        SYNTAX Counter64
        MAX-ACCESS read-only
        STATUS current
        DESCRIPTION
            "The total number of packets dropped during receiving process
             by this IPsec Phase-2 Tunnel."
        ::= { ibIPsecTunnelStatV2Entry 4 }

    ibIPsecTunInReplayDropPktsV2 OBJECT-TYPE
        SYNTAX Counter64
        MAX-ACCESS read-only
        STATUS current
        DESCRIPTION
            "The total number of packets dropped during
             receiving process due to Anti-Replay process
             by this IPsec Phase-2 Tunnel."
        ::= { ibIPsecTunnelStatV2Entry 5 }

    ibIPsecTunInAuthFailsV2 OBJECT-TYPE
        SYNTAX Counter64
        MAX-ACCESS read-only
        STATUS current
        DESCRIPTION
            "The total number of inbound authentication's
             which ended in failure by this IPsec Phase-2 Tunnel."
        ::= { ibIPsecTunnelStatV2Entry 6 }

    ibIPsecTunInDecryptFailsV2 OBJECT-TYPE
        SYNTAX Counter64
        MAX-ACCESS read-only
        STATUS current
        DESCRIPTION
            "The total number of inbound decryption's
             which ended in failure by this IPsec Phase-2 Tunnel."
        ::= { ibIPsecTunnelStatV2Entry 7 }

    ibIPsecTunOutOctetsV2 OBJECT-TYPE
        SYNTAX Counter64
        MAX-ACCESS read-only
        STATUS current
        DESCRIPTION
            "The total number of octets sent by this IPsec Phase-2 Tunnel.
             This value is accumulated AFTER determining whether or not
             the packet should be compressed."
        ::= { ibIPsecTunnelStatV2Entry 8 }

    ibIPsecTunOutUncompOctetsV2 OBJECT-TYPE
        SYNTAX Counter64
        MAX-ACCESS read-only
        STATUS current
        DESCRIPTION
            "The total number of uncompressed octets sent by this IPsec Phase-2
             Tunnel.  This value is accumulated BEFORE the packet is compressed."
        ::= { ibIPsecTunnelStatV2Entry 9 }

    ibIPsecTunOutPktsV2 OBJECT-TYPE
        SYNTAX Counter64
        MAX-ACCESS read-only
        STATUS current
        DESCRIPTION
            "The total number of packets sent by this IPsec Phase-2 Tunnel."
        ::= { ibIPsecTunnelStatV2Entry 10 }

    ibIPsecTunOutDropPktsV2 OBJECT-TYPE
        SYNTAX Counter64
        MAX-ACCESS read-only
        STATUS current
        DESCRIPTION
            "The total number of packets dropped during sending process
             by this IPsec Phase-2 Tunnel."
        ::= { ibIPsecTunnelStatV2Entry 11 }

    ibIPsecTunOutEncryptFailsV2 OBJECT-TYPE
        SYNTAX Counter64
        MAX-ACCESS read-only
        STATUS current
        DESCRIPTION
            "The total number of outbound encryption's which ended in failure
             by this IPsec Phase-2 Tunnel."
        ::= { ibIPsecTunnelStatV2Entry 12 }

    ibIPsecTunNoMemoryDropPktsV2 OBJECT-TYPE
        SYNTAX Counter64
        MAX-ACCESS read-only
        STATUS current
        DESCRIPTION
            "The total number of packets dropped due to no enough memory by this
             IPsec Phase-2 Tunnel."
        ::= { ibIPsecTunnelStatV2Entry 13 }

    ibIPsecTunQueueFullDropPktsV2 OBJECT-TYPE
        SYNTAX Counter64
        MAX-ACCESS read-only
        STATUS current
        DESCRIPTION
            "The total number of packets dropped due to queue full by this
             IPsec Phase-2 Tunnel."
        ::= { ibIPsecTunnelStatV2Entry 14 }

    ibIPsecTunInvalidLenDropPktsV2 OBJECT-TYPE
        SYNTAX Counter64
        MAX-ACCESS read-only
        STATUS current
        DESCRIPTION
            "The total number of packets dropped due to invalid length packet
             by this IPsec Phase-2 Tunnel."
        ::= { ibIPsecTunnelStatV2Entry 15 }

    ibIPsecTunTooLongDropPktsV2 OBJECT-TYPE
        SYNTAX Counter64
        MAX-ACCESS read-only
        STATUS current
        DESCRIPTION
            "The total number of packets dropped due to too long packet by this
             IPsec Phase-2 Tunnel."
        ::= { ibIPsecTunnelStatV2Entry 16 }

    ibIPsecTunInvalidSaDropPktsV2 OBJECT-TYPE
        SYNTAX Counter64
        MAX-ACCESS read-only
        STATUS current
        DESCRIPTION
            "The total number of packets dropped due to invalid SA by this
             IPsec Phase-2 Tunnel."
        ::= { ibIPsecTunnelStatV2Entry 17 }

-- ===============================================
-- Begin the table of ibIPsecSaV2Table.
-- ===============================================

    ibIPsecSaV2Table OBJECT-TYPE
        SYNTAX SEQUENCE OF IbIPsecSaV2Entry
        MAX-ACCESS not-accessible
        STATUS current
        DESCRIPTION
            "The IPsec Phase-2 Security Protection Index Table.  This table
             contains an entry for each active and expiring security association."
        ::= { ibIPsecObjectsV2 4 }

    ibIPsecSaV2Entry OBJECT-TYPE
        SYNTAX IbIPsecSaV2Entry
        MAX-ACCESS not-accessible
        STATUS current
        DESCRIPTION
            "Information about ibIPsecSaV2Table."
        INDEX { ibIPsecTunIndexV2,ibIPsecSaIndexV2 }
        ::= { ibIPsecSaV2Table 1 }

    IbIPsecSaV2Entry ::=
        SEQUENCE {
            ibIPsecSaIndexV2
                Integer32,
            ibIPsecSaDirectionV2
                INTEGER,
            ibIPsecSaSpiValueV2
                Unsigned32,
            ibIPsecSaSecProtocolV2
                IbIPsecSaProtocolV2,
            ibIPsecSaEncryptAlgoV2
                IbIPsecEncryptAlgoV2,
            ibIPsecSaAuthAlgoV2
                IbIPsecAuthAlgoV2,
            ibIPsecSaStatusV2
                INTEGER
        }

    ibIPsecSaIndexV2 OBJECT-TYPE
        SYNTAX Integer32 (1..2147483647)
        MAX-ACCESS accessible-for-notify
        STATUS current
        DESCRIPTION
            "The number of the Sa associated with the Phase-2 Tunnel
             Table.  The value of this index is a number which begins
             at one and is incremented with each Sa associated with
             an IPsec Phase-2 Tunnel.  The value of this object will
             wrap at 2,147,483,647."
        ::= { ibIPsecSaV2Entry 1 }

    ibIPsecSaDirectionV2 OBJECT-TYPE
        SYNTAX INTEGER {
            in(1),
            out(2)
        }
        MAX-ACCESS read-only
        STATUS current
        DESCRIPTION
            "The direction of the SA."
        ::= { ibIPsecSaV2Entry 2 }

    ibIPsecSaSpiValueV2 OBJECT-TYPE
        SYNTAX Unsigned32 (1..4294967295)
        MAX-ACCESS read-only
        STATUS current
        DESCRIPTION
            "The value of the SPI."
        ::= { ibIPsecSaV2Entry 3 }

    ibIPsecSaSecProtocolV2 OBJECT-TYPE
        SYNTAX IbIPsecSaProtocolV2
        MAX-ACCESS read-only
        STATUS current
        DESCRIPTION
            "The security protocol of the SA."
        ::= { ibIPsecSaV2Entry 4 }

    ibIPsecSaEncryptAlgoV2 OBJECT-TYPE
        SYNTAX IbIPsecEncryptAlgoV2
        MAX-ACCESS read-only
        STATUS current
        DESCRIPTION
            "The encryption algorithm used by the security association
             of the IPsec Phase-2 Tunnel."
        ::= { ibIPsecSaV2Entry 5 }

    ibIPsecSaAuthAlgoV2 OBJECT-TYPE
        SYNTAX IbIPsecAuthAlgoV2
        MAX-ACCESS read-only
        STATUS current
        DESCRIPTION
            "The authentication algorithm used by the SA."
        ::= { ibIPsecSaV2Entry 6 }

    ibIPsecSaStatusV2 OBJECT-TYPE
        SYNTAX INTEGER {
            active(1),
            expiring(2)
        }
        MAX-ACCESS read-only
        STATUS current
        DESCRIPTION
            "The status of the SA."
        ::= { ibIPsecSaV2Entry 7 }

-- ===============================================
-- Begin the table of ibIPsecTrafficV2Table.
-- ===============================================

    ibIPsecTrafficV2Table OBJECT-TYPE
        SYNTAX SEQUENCE OF IbIPsecTrafficV2Entry
        MAX-ACCESS not-accessible
        STATUS current
        DESCRIPTION
            "The IPsec Phase-2 Tunnel Traffic Table."
        ::= { ibIPsecObjectsV2 5 }

    ibIPsecTrafficV2Entry OBJECT-TYPE
        SYNTAX IbIPsecTrafficV2Entry
        MAX-ACCESS not-accessible
        STATUS current
        DESCRIPTION
            "Information about ibIPsecTrafficV2Table."
        INDEX { ibIPsecTunIndexV2 }
        ::= { ibIPsecTrafficV2Table 1 }

    IbIPsecTrafficV2Entry ::=
        SEQUENCE {
            ibIPsecTrafficLocalTypeV2
                IbIPsecTrafficTypeV2,
            ibIPsecTrafficLocalAddr1TypeV2
                InetAddressType,
            ibIPsecTrafficLocalAddr1V2
                InetAddress,
            ibIPsecTrafficLocalAddr2TypeV2
                InetAddressType,
            ibIPsecTrafficLocalAddr2V2
                InetAddress,
            ibIPsecTrafficLocalProtocol1V2
                Integer32,
            ibIPsecTrafficLocalProtocol2V2
                Integer32,
            ibIPsecTrafficLocalPort1V2
                Integer32,
            ibIPsecTrafficLocalPort2V2
                Integer32,
            ibIPsecTrafficRemoteTypeV2
                IbIPsecTrafficTypeV2,
            ibIPsecTrafficRemAddr1TypeV2
                InetAddressType,
            ibIPsecTrafficRemAddr1V2
                InetAddress,
            ibIPsecTrafficRemAddr2TypeV2
                InetAddressType,
            ibIPsecTrafficRemAddr2V2
                InetAddress,
            ibIPsecTrafficRemoPro1V2
                Integer32,
            ibIPsecTrafficRemoPro2V2
                Integer32,
            ibIPsecTrafficRemPort1V2
                Integer32,
            ibIPsecTrafficRemPort2V2
                Integer32
    }

    ibIPsecTrafficLocalTypeV2 OBJECT-TYPE
        SYNTAX IbIPsecTrafficTypeV2
        MAX-ACCESS read-only
        STATUS current
        DESCRIPTION
            "The type of the local peer's traffic.  Possible values are:
            1) A single IP address
            2) An IP address range
            3) An IP subnet"
        ::= { ibIPsecTrafficV2Entry 1 }

    ibIPsecTrafficLocalAddr1TypeV2 OBJECT-TYPE
        SYNTAX InetAddressType
        MAX-ACCESS read-only
        STATUS current
        DESCRIPTION
            "The type of the first IP address specification for the local peer's
             traffic."
        ::= { ibIPsecTrafficV2Entry 2 }

    ibIPsecTrafficLocalAddr1V2 OBJECT-TYPE
        SYNTAX InetAddress
        MAX-ACCESS read-only
        STATUS current
        DESCRIPTION
            "The first IP address specification of the local peer's traffic.

            If the local peer's traffic type is single IP address, this is the
            IP address.

            If the local peer's traffic type is IP subnet, this is the subnet address.

            If the local peer's traffic type is IP address range, this is the
            beginning IP address of the range."
        ::= { ibIPsecTrafficV2Entry 3 }

    ibIPsecTrafficLocalAddr2TypeV2 OBJECT-TYPE
        SYNTAX InetAddressType
        MAX-ACCESS read-only
        STATUS current
        DESCRIPTION
            "The type of the second IP address specification for the local peer's
             traffic."
        ::= { ibIPsecTrafficV2Entry 4 }

    ibIPsecTrafficLocalAddr2V2 OBJECT-TYPE
        SYNTAX InetAddress
        MAX-ACCESS read-only
        STATUS current
        DESCRIPTION
            "The second IP address specification of the local peer's traffic.

            If the local peer's traffic type is single IP address, this is the
            IP address.

            If the local peer's traffic type is IP subnet, this is the subnet mask.

            If the local peer's traffic type is IP address range, this is the
            ending IP address of the range."
        ::= { ibIPsecTrafficV2Entry 5 }

    ibIPsecTrafficLocalProtocol1V2 OBJECT-TYPE
        SYNTAX Integer32 (0..255)
        MAX-ACCESS read-only
        STATUS current
        DESCRIPTION
            "The first protocol number specification of the local peer's traffic.

            If the protocol type of the local peer's traffic is single protocol,
            this is the protocol number.

            If the protocol type of the local peer's traffic is protocol range,
            this is the beginning protocol number of the range."
        ::= { ibIPsecTrafficV2Entry 6 }

    ibIPsecTrafficLocalProtocol2V2 OBJECT-TYPE
        SYNTAX Integer32 (0..255)
        MAX-ACCESS read-only
        STATUS current
        DESCRIPTION
            "The second protocol number specification of the local peer's traffic.

            If the protocol type of the local peer's traffic is single protocol,
            this is the protocol number.

            If the protocol type of the local peer's traffic is protocol range,
            this is the ending protocol number of the range."
        ::= { ibIPsecTrafficV2Entry 7 }

    ibIPsecTrafficLocalPort1V2 OBJECT-TYPE
        SYNTAX Integer32 (0..65535)
        MAX-ACCESS read-only
        STATUS current
        DESCRIPTION
            "The first port number specification of the local peer's traffic.

            If the port type of the local peer's traffic is single port, this is
            the port number.

            If the port type of the local peer's traffic is port range, this is
            the beginning port number of the range."
        ::= { ibIPsecTrafficV2Entry 8 }

    ibIPsecTrafficLocalPort2V2 OBJECT-TYPE
        SYNTAX Integer32 (0..65535)
        MAX-ACCESS read-only
        STATUS current
        DESCRIPTION
            "The second port number specification of the local peer's traffic.

            If the port type of the local peer's traffic is single port, this is
            the port number.

            If the port type of the local peer's traffic is port range, this is
            the ending port number of the range."
        ::= { ibIPsecTrafficV2Entry 9 }

    ibIPsecTrafficRemoteTypeV2 OBJECT-TYPE
        SYNTAX IbIPsecTrafficTypeV2
        MAX-ACCESS read-only
        STATUS current
        DESCRIPTION
            "The type of the remote peer's traffic.  Possible values are:
            1) A single IP address
            2) An IP address range
            3) An IP subnet"
        ::= { ibIPsecTrafficV2Entry 10 }

    ibIPsecTrafficRemAddr1TypeV2 OBJECT-TYPE
        SYNTAX InetAddressType
        MAX-ACCESS read-only
        STATUS current
        DESCRIPTION
            "The type of the first IP address specification for the remote peer's
             traffic."
        ::= { ibIPsecTrafficV2Entry 11 }

    ibIPsecTrafficRemAddr1V2 OBJECT-TYPE
        SYNTAX InetAddress
        MAX-ACCESS read-only
        STATUS current
        DESCRIPTION
            "The first IP address specification of the remote peer's traffic.

            If the remote traffic type is single IP address, this is the IP address.

            If the remote traffic type is IP subnet, this is the subnet address.

            If the remote traffic type is IP address range, this is the beginning
            IP address of the range."
        ::= { ibIPsecTrafficV2Entry 12 }

    ibIPsecTrafficRemAddr2TypeV2 OBJECT-TYPE
        SYNTAX InetAddressType
        MAX-ACCESS read-only
        STATUS current
        DESCRIPTION
            "The type of the second IP address specification for the remote peer's
             traffic."
        ::= { ibIPsecTrafficV2Entry 13 }

    ibIPsecTrafficRemAddr2V2 OBJECT-TYPE
        SYNTAX InetAddress
        MAX-ACCESS read-only
        STATUS current
        DESCRIPTION
            "The second IP address specification of the remote peer's traffic.

            If the remote traffic type is single IP address, this is the IP address.

            If the remote traffic type is IP subnet, this is the subnet mask.

            If the remote traffic type is IP address range, this is the ending IP
            address of the range."
        ::= { ibIPsecTrafficV2Entry 14 }

    ibIPsecTrafficRemoPro1V2 OBJECT-TYPE
        SYNTAX Integer32 (0..255)
        MAX-ACCESS read-only
        STATUS current
        DESCRIPTION
            "The first protocol number specification of the remote peer's traffic.

            If the protocol type of the remote peer's traffic is single protocol,
            this is the protocol number.

            If the protocol type of the remote peer's traffic is protocol range,
            this is the beginning protocol number of the range."
        ::= { ibIPsecTrafficV2Entry 15 }

    ibIPsecTrafficRemoPro2V2 OBJECT-TYPE
        SYNTAX Integer32 (0..255)
        MAX-ACCESS read-only
        STATUS current
        DESCRIPTION
            "The second protocol number specification of the remote peer's traffic.

            If the protocol type of the remote peer's traffic is single protocol,
            this is the protocol number.

            If the protocol type of the remote peer's traffic is protocol range,
            this is the ending protocol number of the range."
        ::= { ibIPsecTrafficV2Entry 16 }

    ibIPsecTrafficRemPort1V2 OBJECT-TYPE
        SYNTAX Integer32 (0..65535)
        MAX-ACCESS read-only
        STATUS current
        DESCRIPTION
            "The first port number specification of the remote peer's traffic.

            If the port type of the remote peer's traffic is single port,
            this is the port number.

            If the port type of the remote peer's traffic is port range,
            this is the beginning port number of the range."
        ::= { ibIPsecTrafficV2Entry 17 }

    ibIPsecTrafficRemPort2V2 OBJECT-TYPE
        SYNTAX Integer32 (0..65535)
        MAX-ACCESS read-only
        STATUS current
        DESCRIPTION
            "The second port number specification of the remote peer's traffic.

            If the port type of the remote peer's traffic is single port,
            this is the port number.

            If the port type of the remote peer's traffic is port range,
            this is the ending port number of the range."
        ::= { ibIPsecTrafficV2Entry 18 }

-- ===============================================
-- Begin the ibIPsecGlobalStatsV2.
-- ===============================================

    ibIPsecGlobalStatsV2 OBJECT IDENTIFIER ::= { ibIPsecObjectsV2 6 }

    ibIPsecGlobalActiveTunnelsV2 OBJECT-TYPE
        SYNTAX Gauge32
        MAX-ACCESS read-only
        STATUS current
        DESCRIPTION
            "The total number of currently active IPsec Phase-2 Tunnels."
        ::= { ibIPsecGlobalStatsV2 1 }

    ibIPsecGlobalActiveSasV2 OBJECT-TYPE
        SYNTAX Gauge32
        MAX-ACCESS read-only
        STATUS current
        DESCRIPTION
            "The total number of currently active or expiring IPsec Phase-2 SA."
        ::= { ibIPsecGlobalStatsV2 2 }

    ibIPsecGlobalInOctetsV2 OBJECT-TYPE
        SYNTAX Counter64
        MAX-ACCESS read-only
        STATUS current
        DESCRIPTION
            "The total number of octets received by all current and previous
             IPsec Phase-2 Tunnels.  This value is accumulated BEFORE determining
             whether or not the packet should be decompressed."
        ::= { ibIPsecGlobalStatsV2 3 }

    ibIPsecGlobalInDecompOctetsV2 OBJECT-TYPE
        SYNTAX Counter64
        MAX-ACCESS read-only
        STATUS current
        DESCRIPTION
            "The total number of decompressed octets received by all current
             and previous IPsec Phase-2 Tunnels.  This value is accumulated
             AFTER the packet is decompressed."
        ::= { ibIPsecGlobalStatsV2 4 }

    ibIPsecGlobalInPktsV2 OBJECT-TYPE
        SYNTAX Counter64
        MAX-ACCESS read-only
        STATUS current
        DESCRIPTION
            "The total number of packets received by all current and
             previous IPsec Phase-2 Tunnels."
        ::= { ibIPsecGlobalStatsV2 5 }

    ibIPsecGlobalInDropsV2 OBJECT-TYPE
        SYNTAX Counter64
        MAX-ACCESS read-only
        STATUS current
        DESCRIPTION
            "The total number of packets dropped during receiving
             process by all current and previous IPsec Phase-2
             Tunnels."
        ::= { ibIPsecGlobalStatsV2 6 }

    ibIPsecGlobalInReplayDropsV2 OBJECT-TYPE
        SYNTAX Counter64
        MAX-ACCESS read-only
        STATUS current
        DESCRIPTION
            "The total number of packets dropped during receiving
             process due to Anti-Replay process by all
             current and previous IPsec Phase-2 Tunnels."
        ::= { ibIPsecGlobalStatsV2 7 }

    ibIPsecGlobalInAuthFailsV2 OBJECT-TYPE
        SYNTAX Counter64
        MAX-ACCESS read-only
        STATUS current
        DESCRIPTION
            "The total number of inbound authentication's which ended
             in failure by all current and previous IPsec Phase-2 Tunnels."
        ::= { ibIPsecGlobalStatsV2 8 }

    ibIPsecGlobalInDecryptFailsV2 OBJECT-TYPE
        SYNTAX Counter64
        MAX-ACCESS read-only
        STATUS current
        DESCRIPTION
            "The total number of inbound decryption's which ended in
             failure by all current and previous IPsec Phase-2 Tunnels."
        ::= { ibIPsecGlobalStatsV2 9 }

    ibIPsecGlobalOutOctetsV2 OBJECT-TYPE
        SYNTAX Counter64
        MAX-ACCESS read-only
        STATUS current
        DESCRIPTION
            "The total number of octets sent by all current and previous
             IPsec Phase-2 Tunnels.  This value is accumulated AFTER
             determining whether or not the packet should be compressed."
        ::= { ibIPsecGlobalStatsV2 10 }

    ibIPsecGlobalOutUncompOctetsV2 OBJECT-TYPE
        SYNTAX Counter64
        MAX-ACCESS read-only
        STATUS current
        DESCRIPTION
            "The total number of uncompressed octets sent by all current
             and previous IPsec Phase-2 Tunnels.  This value is accumulated
             BEFORE the packet is compressed."
        ::= { ibIPsecGlobalStatsV2 11 }

    ibIPsecGlobalOutPktsV2 OBJECT-TYPE
        SYNTAX Counter64
        MAX-ACCESS read-only
        STATUS current
        DESCRIPTION
            "The total number of packets sent by all current and previous
             IPsec Phase-2 Tunnels."
        ::= { ibIPsecGlobalStatsV2 12 }

    ibIPsecGlobalOutDropsV2 OBJECT-TYPE
        SYNTAX Counter64
        MAX-ACCESS read-only
        STATUS current
        DESCRIPTION
            "The total number of packets dropped during sending process
             by all current and previous IPsec Phase-2 Tunnels."
        ::= { ibIPsecGlobalStatsV2 13 }

    ibIPsecGlobalOutEncryptFailsV2 OBJECT-TYPE
        SYNTAX Counter64
        MAX-ACCESS read-only
        STATUS current
        DESCRIPTION
            "The total number of outbound encryption's which ended in failure
             by all current and previous IPsec Phase-2 Tunnels."
        ::= { ibIPsecGlobalStatsV2 14 }

    ibIPsecGlobalNoMemoryDropsV2 OBJECT-TYPE
        SYNTAX Counter64
        MAX-ACCESS read-only
        STATUS current
        DESCRIPTION
            "The total number of packets dropped due to no enough memory
             by all current and previous IPsec Phase-2 Tunnels."
        ::= { ibIPsecGlobalStatsV2 15 }

    ibIPsecGlobalNoFindSaDropsV2 OBJECT-TYPE
        SYNTAX Counter64
        MAX-ACCESS read-only
        STATUS current
        DESCRIPTION
            "The total number of packets dropped due to not find SA by
             all current and previous IPsec Phase-2 Tunnels."
        ::= { ibIPsecGlobalStatsV2 16 }

    ibIPsecGlobalQueueFullDropsV2 OBJECT-TYPE
        SYNTAX Counter64
        MAX-ACCESS read-only
        STATUS current
        DESCRIPTION
            "The total number of packets dropped due to queue full by
             all current and previous IPsec Phase-2 Tunnels."
        ::= { ibIPsecGlobalStatsV2 17 }

    ibIPsecGlobalInvalidLenDropsV2 OBJECT-TYPE
        SYNTAX Counter64
        MAX-ACCESS read-only
        STATUS current
        DESCRIPTION
            "The total number of packets dropped due to invalid packet
             length by all current and previous IPsec Phase-2 Tunnels."
        ::= { ibIPsecGlobalStatsV2 18 }

    ibIPsecGlobalTooLongDropsV2 OBJECT-TYPE
        SYNTAX Counter64
        MAX-ACCESS read-only
        STATUS current
        DESCRIPTION
            "The total number of packets dropped due to too long packet by
             all current and previous IPsec Phase-2 Tunnels."
        ::= { ibIPsecGlobalStatsV2 19 }

    ibIPsecGlobalInvalidSaDropsV2 OBJECT-TYPE
        SYNTAX Counter64
        MAX-ACCESS read-only
        STATUS current
        DESCRIPTION
            "The total number of packets dropped due to invalid SA by all
             current and previous IPsec Phase-2 Tunnels."
        ::= { ibIPsecGlobalStatsV2 20 }

-- ===============================================
-- Begin the ibIPsecTrapObjectV2.
-- ===============================================

    ibIPsecTrapObjectV2 OBJECT IDENTIFIER ::= { ibIPsecObjectsV2 7 }

    ibIPsecPolicyNameV2 OBJECT-TYPE
        SYNTAX OCTET STRING (SIZE(1..63))
        MAX-ACCESS accessible-for-notify
        STATUS current
        DESCRIPTION
            "The IPsec policy name with a trap."
        ::= { ibIPsecTrapObjectV2 1 }

    ibIPsecPolicySeqNumV2 OBJECT-TYPE
        SYNTAX Integer32
        MAX-ACCESS accessible-for-notify
        STATUS current
        DESCRIPTION
            "The IPsec policy sequence number with a trap."
        ::= { ibIPsecTrapObjectV2 2 }

    ibIPsecPolicySizeV2 OBJECT-TYPE
        SYNTAX Integer32
        MAX-ACCESS accessible-for-notify
        STATUS current
        DESCRIPTION
            "The number of IPsec policies with a trap."
        ::= { ibIPsecTrapObjectV2 3 }

    ibIPsecTunStopReasonV2 OBJECT-TYPE
        SYNTAX IbIPsecTunnelErrorCodeV2
        MAX-ACCESS accessible-for-notify
        STATUS current
        DESCRIPTION
            "The reason of ipsec tunnel deleted due to dpd failure."
        ::= { ibIPsecTrapObjectV2 4 }

-- ===============================================
-- Begin the ibIPsecTrapCntlV2.
-- ===============================================


    ibIPsecTrapCntlV2 OBJECT IDENTIFIER ::= { ibIPsecObjectsV2 8 }

    ibIPsecTrapGlobalCntlV2 OBJECT-TYPE
        SYNTAX TruthValue
        MAX-ACCESS read-write
        STATUS current
        DESCRIPTION
            "Indicates whether all IPsec traps should be generated."
        ::= { ibIPsecTrapCntlV2 1 }

    ibIPsecTunnelStartTrapCntlV2 OBJECT-TYPE
        SYNTAX TruthValue
        MAX-ACCESS read-write
        STATUS current
        DESCRIPTION
            "Indicates whether ibIPsecTunnelStartV2 traps should be generated."
        ::= { ibIPsecTrapCntlV2 2 }

    ibIPsecTunnelStopTrapCntlV2 OBJECT-TYPE
        SYNTAX TruthValue
        MAX-ACCESS read-write
        STATUS current
        DESCRIPTION
            "Indicates whether ibIPsecTunnelStopV2 traps should be generated."
        ::= { ibIPsecTrapCntlV2 3 }

    ibIPsecNoSaTrapCntlV2 OBJECT-TYPE
        SYNTAX TruthValue
        MAX-ACCESS read-write
        STATUS current
        DESCRIPTION
            "Indicates whether ibIPsecNoSaFailureV2 traps should be generated."
        ::= { ibIPsecTrapCntlV2 4 }

    ibIPsecAuthFailureTrapCntlV2 OBJECT-TYPE
        SYNTAX TruthValue
        MAX-ACCESS read-write
        STATUS current
        DESCRIPTION
            "Indicates whether ibIPsecAuthFailFailureV2 traps should be generated."
        ::= { ibIPsecTrapCntlV2 5 }

    ibIPsecEncryFailureTrapCntlV2 OBJECT-TYPE
        SYNTAX TruthValue
        MAX-ACCESS read-write
        STATUS current
        DESCRIPTION
            "Indicates whether ibIPsecEncryFailFailureV2 traps should be generated."
        ::= { ibIPsecTrapCntlV2 6 }

    ibIPsecDecryFailureTrapCntlV2 OBJECT-TYPE
        SYNTAX TruthValue
        MAX-ACCESS read-write
        STATUS current
        DESCRIPTION
            "Indicates whether ibIPsecDecryFailFailureV2 traps should be generated."
        ::= { ibIPsecTrapCntlV2 7 }

    ibIPsecInvalidSaTrapCntlV2 OBJECT-TYPE
        SYNTAX TruthValue
        MAX-ACCESS read-write
        STATUS current
        DESCRIPTION
            "Indicates whether ibIPsecInvalidSaFailureV2 traps should be generated."
        ::= { ibIPsecTrapCntlV2 8 }

    ibIPsecPolicyAddTrapCntlV2 OBJECT-TYPE
        SYNTAX TruthValue
        MAX-ACCESS read-write
        STATUS current
        DESCRIPTION
            "Indicates whether ibIPsecPolicyAddV2 traps should be generated."
        ::= { ibIPsecTrapCntlV2 9 }

    ibIPsecPolicyDelTrapCntlV2 OBJECT-TYPE
        SYNTAX TruthValue
        MAX-ACCESS read-write
        STATUS current
        DESCRIPTION
            "Indicates whether ibIPsecPolicyDelV2 traps should be generated."
        ::= { ibIPsecTrapCntlV2 10 }

    ibIPsecPolicyAttachTrapCntlV2 OBJECT-TYPE
        SYNTAX TruthValue
        MAX-ACCESS read-write
        STATUS current
        DESCRIPTION
            "Indicates whether ibIPsecPolicyAttachV2 traps should be generated."
        ::= { ibIPsecTrapCntlV2 11 }

    ibIPsecPolicyDetachTrapCntlV2 OBJECT-TYPE
        SYNTAX TruthValue
        MAX-ACCESS read-write
        STATUS current
        DESCRIPTION
            "Indicates whether ibIPsecPolicyDetachV2 traps should be generated."
        ::= { ibIPsecTrapCntlV2 12 }

    ibIPsecConnectionStartCntlV2 OBJECT-TYPE
        SYNTAX TruthValue
        MAX-ACCESS read-write
        STATUS current
        DESCRIPTION
            "Indicates whether ibIPsecConnectionStartV2 traps should be generated."
        ::= { ibIPsecTrapCntlV2 13 }

    ibIPsecConnectionStopCntlV2 OBJECT-TYPE
        SYNTAX TruthValue
        MAX-ACCESS read-write
        STATUS current
        DESCRIPTION
            "Indicates whether ibIPsecConnectionStopV2 traps should be generated."
        ::= { ibIPsecTrapCntlV2 14 }

-- ===============================================
-- definition of traps.
-- ===============================================

    ibIPsecTrapV2 OBJECT IDENTIFIER ::= { ibIPsecObjectsV2 9 }

    ibIPsecNotificationsV2 OBJECT IDENTIFIER ::= { ibIPsecTrapV2 0 }

    ibIPsecTunnelStartV2 NOTIFICATION-TYPE
        OBJECTS {
                    ibIPsecTunIndexV2,
                    ibIPsecTunLocalAddrTypeV2,
                    ibIPsecTunLocalAddrV2,
                    ibIPsecTunRemoteAddrTypeV2,
                    ibIPsecTunRemoteAddrV2,
                    ibIPsecTunLifeTimeV2,
                    ibIPsecTunLifeSizeV2
                }
        STATUS     current
        DESCRIPTION
            "This notification is generated when an IPsec Phase-2
             Tunnel is created."
        ::= { ibIPsecNotificationsV2 1 }

    ibIPsecTunnelStopV2 NOTIFICATION-TYPE
        OBJECTS {
                    ibIPsecTunIndexV2,
                    ibIPsecTunLocalAddrTypeV2,
                    ibIPsecTunLocalAddrV2,
                    ibIPsecTunRemoteAddrTypeV2,
                    ibIPsecTunRemoteAddrV2,
                    ibIPsecTunActiveTimeV2,
                    ibIPsecTunStopReasonV2
                }
        STATUS     current
        DESCRIPTION
            "This notification is generated when an IPsec Phase-2
             Tunnel is deleted."
        ::= { ibIPsecNotificationsV2 2 }

    ibIPsecNoSaFailureV2 NOTIFICATION-TYPE
        OBJECTS {
                    ibIPsecTunIndexV2,
                    ibIPsecTunLocalAddrTypeV2,
                    ibIPsecTunLocalAddrV2,
                    ibIPsecTunRemoteAddrTypeV2,
                    ibIPsecTunRemoteAddrV2
                }
        STATUS     current
        DESCRIPTION
            "This notification is generated when an IPsec Phase-2
             non-existent SA error occurs."
        ::= { ibIPsecNotificationsV2 3 }

    ibIPsecAuthFailFailureV2 NOTIFICATION-TYPE
        OBJECTS {
                    ibIPsecTunIndexV2,
                    ibIPsecTunLocalAddrTypeV2,
                    ibIPsecTunLocalAddrV2,
                    ibIPsecTunRemoteAddrTypeV2,
                    ibIPsecTunRemoteAddrV2
                  }
        STATUS     current
        DESCRIPTION
            "This notification is generated when the IPsec phase-2
             authentication failure occurs."
        ::= { ibIPsecNotificationsV2 4 }

    ibIPsecEncryFailFailureV2 NOTIFICATION-TYPE
        OBJECTS {
                    ibIPsecTunIndexV2,
                    ibIPsecTunLocalAddrTypeV2,
                    ibIPsecTunLocalAddrV2,
                    ibIPsecTunRemoteAddrTypeV2,
                    ibIPsecTunRemoteAddrV2
                }
        STATUS     current
        DESCRIPTION
            "This notification is generated when the IPsec phase-2
             tunnel has an encrypting failure."
        ::= { ibIPsecNotificationsV2 5 }

    ibIPsecDecryFailFailureV2 NOTIFICATION-TYPE
        OBJECTS {
                    ibIPsecTunIndexV2,
                    ibIPsecTunLocalAddrTypeV2,
                    ibIPsecTunLocalAddrV2,
                    ibIPsecTunRemoteAddrTypeV2,
                    ibIPsecTunRemoteAddrV2
                }
        STATUS     current
        DESCRIPTION
            "This notification is generated when the IPsec phase-2
             tunnel has a decrypting failure."
        ::= { ibIPsecNotificationsV2 6 }

    ibIPsecInvalidSaFailureV2 NOTIFICATION-TYPE
        OBJECTS {
                    ibIPsecTunIndexV2,
                    ibIPsecSaIndexV2,
                    ibIPsecTunLocalAddrTypeV2,
                    ibIPsecTunLocalAddrV2,
                    ibIPsecTunRemoteAddrTypeV2,
                    ibIPsecTunRemoteAddrV2,
                    ibIPsecSaSpiValueV2
                }
        STATUS     current
        DESCRIPTION
            "This notification is generated when the IPsec phase-2
             invalid SA failure occurs."
        ::= { ibIPsecNotificationsV2 7 }

    ibIPsecPolicyAddV2 NOTIFICATION-TYPE
        OBJECTS { ibIPsecPolicyNameV2,
                  ibIPsecPolicySeqNumV2,
                  ibIPsecPolicySizeV2
                }
        STATUS     current
        DESCRIPTION
            "This notification is generated when an IPsec policy is added."
        ::= { ibIPsecNotificationsV2 8 }

    ibIPsecPolicyDelV2 NOTIFICATION-TYPE
        OBJECTS { ibIPsecPolicyNameV2,
                  ibIPsecPolicySeqNumV2,
                  ibIPsecPolicySizeV2
                }
        STATUS     current
        DESCRIPTION
            "This notification is generated when an IPsec policy is deleted."
        ::= { ibIPsecNotificationsV2 9 }

    ibIPsecPolicyAttachV2 NOTIFICATION-TYPE
        OBJECTS { ibIPsecPolicyNameV2,
                  ibIPsecPolicySizeV2,
                  ifIndex
                }
        STATUS     current
        DESCRIPTION
            "This notification is generated when an IPsec policy is attached
             with one interface."
        ::= { ibIPsecNotificationsV2 10 }

    ibIPsecPolicyDetachV2 NOTIFICATION-TYPE
        OBJECTS { ibIPsecPolicyNameV2,
                  ibIPsecPolicySizeV2,
                  ifIndex
                }
        STATUS     current
        DESCRIPTION
            "This notification is generated when an IPsec policy is detached
             with one interface."
        ::= { ibIPsecNotificationsV2 11 }

    ibIPsecConnectionStartV2 NOTIFICATION-TYPE
        OBJECTS {
                    ibIPsecPolicyDescripV2
                }
        STATUS     current
        DESCRIPTION
            "This notification is generated when an IPsec connection
             is created."
        ::= { ibIPsecNotificationsV2 12 }

    ibIPsecConnectionStopV2 NOTIFICATION-TYPE
        OBJECTS {
                    ibIPsecPolicyDescripV2
                }
        STATUS     current
        DESCRIPTION
            "This notification is generated when an IPsec connection
             is terminated."
        ::= { ibIPsecNotificationsV2 13 }

-- ===============================================
-- Begin the table of ibIPsecTunnelStatByDescripV2Table.
-- ===============================================

    ibIPsecTunnelStatByDescripV2Table OBJECT-TYPE
        SYNTAX SEQUENCE OF IbIPsecTunnelStatByDescripV2Entry
        MAX-ACCESS not-accessible
        STATUS current
        DESCRIPTION
            "This table contains IPsec phase-2 tunnel statistics by description."
        ::= { ibIPsecObjectsV2 10 }

    ibIPsecTunnelStatByDescripV2Entry OBJECT-TYPE
        SYNTAX IbIPsecTunnelStatByDescripV2Entry
        MAX-ACCESS not-accessible
        STATUS current
        DESCRIPTION
            "An entry of IPsec phase-2 tunnels statistics by description table."
        INDEX { ibIPsecPolicyDescripV2 }
        ::= { ibIPsecTunnelStatByDescripV2Table 1 }

    IbIPsecTunnelStatByDescripV2Entry ::=
        SEQUENCE {
            ibIPsecPolicyDescripV2
                OCTET STRING,
            ibIPsecTunInOctetsByDescripV2
                Counter64,
            ibIPsecTunInDecompOctetsByDescripV2
                Counter64,
            ibIPsecTunInPktsByDescripV2
                Counter64,
            ibIPsecTunInDropPktsByDescripV2
                Counter64,
            ibIPsecTunInReplayDropPktsByDescripV2
                Counter64,
            ibIPsecTunInAuthFailsByDescripV2
                Counter64,
            ibIPsecTunInDecryptFailsByDescripV2
                Counter64,
            ibIPsecTunOutOctetsByDescripV2
                Counter64,
            ibIPsecTunOutUncompOctetsByDescripV2
                Counter64,
            ibIPsecTunOutPktsByDescripV2
                Counter64,
            ibIPsecTunOutDropPktsByDescripV2
                Counter64,
            ibIPsecTunOutEncryptFailsByDescripV2
                Counter64,
            ibIPsecTunNoMemoryDropPktsByDescripV2
                Counter64,
            ibIPsecTunQueueFullDropPktsByDescripV2
                Counter64,
            ibIPsecTunInvalidLenDropPktsByDescripV2
                Counter64,
            ibIPsecTunTooLongDropPktsByDescripV2
                Counter64,
            ibIPsecTunInvalidSaDropPktsByDescripV2
                Counter64
        }

    ibIPsecPolicyDescripV2 OBJECT-TYPE
        SYNTAX OCTET STRING (SIZE(1..80))
        MAX-ACCESS accessible-for-notify
        STATUS current
        DESCRIPTION
            "The IPsec policy's description."
        ::= { ibIPsecTunnelStatByDescripV2Entry 1 }

    ibIPsecTunInOctetsByDescripV2 OBJECT-TYPE
        SYNTAX Counter64
        MAX-ACCESS read-only
        STATUS current
        DESCRIPTION
            "The total number of octets received by IPsec phase-2 tunnels.
             This value is accumulated BEFORE determining whether or not the
             packet should be decompressed."
        ::= { ibIPsecTunnelStatByDescripV2Entry 2 }

    ibIPsecTunInDecompOctetsByDescripV2 OBJECT-TYPE
        SYNTAX Counter64
        MAX-ACCESS read-only
        STATUS current
        DESCRIPTION
            "The total number of decompressed octets received by IPsec
             phase-2 tunnels.  This value is accumulated AFTER the packet
             is decompressed."
        ::= { ibIPsecTunnelStatByDescripV2Entry 3 }

    ibIPsecTunInPktsByDescripV2 OBJECT-TYPE
        SYNTAX Counter64
        MAX-ACCESS read-only
        STATUS current
        DESCRIPTION
            "The total number of packets received by IPsec phase-2 tunnels."
        ::= { ibIPsecTunnelStatByDescripV2Entry 4 }

    ibIPsecTunInDropPktsByDescripV2 OBJECT-TYPE
        SYNTAX Counter64
        MAX-ACCESS read-only
        STATUS current
        DESCRIPTION
            "The total number of packets dropped by IPsec phase-2 tunnels during receiving process."
        ::= { ibIPsecTunnelStatByDescripV2Entry 5 }

    ibIPsecTunInReplayDropPktsByDescripV2 OBJECT-TYPE
        SYNTAX Counter64
        MAX-ACCESS read-only
        STATUS current
        DESCRIPTION
            "The total number of receive  packets dropped by IPsec phase-2 tunnels
            due to Anti-Replay processing."
        ::= { ibIPsecTunnelStatByDescripV2Entry 6 }

    ibIPsecTunInAuthFailsByDescripV2 OBJECT-TYPE
        SYNTAX Counter64
        MAX-ACCESS read-only
        STATUS current
        DESCRIPTION
            "The total number of inbound authentication
             failures on IPsec phase-2 tunnels."
        ::= { ibIPsecTunnelStatByDescripV2Entry 7 }

    ibIPsecTunInDecryptFailsByDescripV2 OBJECT-TYPE
        SYNTAX Counter64
        MAX-ACCESS read-only
        STATUS current
        DESCRIPTION
            "The total number of inbound decryption
             failures on IPsec phase-2 tunnels."
        ::= { ibIPsecTunnelStatByDescripV2Entry 8 }

    ibIPsecTunOutOctetsByDescripV2 OBJECT-TYPE
        SYNTAX Counter64
        MAX-ACCESS read-only
        STATUS current
        DESCRIPTION
            "The total number of octets sent by IPsec phase-2 tunnels.
             This value is accumulated AFTER determining whether or not
             the packet should be compressed."
        ::= { ibIPsecTunnelStatByDescripV2Entry 9 }

    ibIPsecTunOutUncompOctetsByDescripV2 OBJECT-TYPE
        SYNTAX Counter64
        MAX-ACCESS read-only
        STATUS current
        DESCRIPTION
            "The total number of uncompressed octets sent by IPsec phase-2
             tunnels.  This value is accumulated BEFORE the packet is compressed."
        ::= { ibIPsecTunnelStatByDescripV2Entry 10 }

    ibIPsecTunOutPktsByDescripV2 OBJECT-TYPE
        SYNTAX Counter64
        MAX-ACCESS read-only
        STATUS current
        DESCRIPTION
            "The total number of packets sent by IPsec phase-2 tunnels."
        ::= { ibIPsecTunnelStatByDescripV2Entry 11 }

    ibIPsecTunOutDropPktsByDescripV2 OBJECT-TYPE
        SYNTAX Counter64
        MAX-ACCESS read-only
        STATUS current
        DESCRIPTION
            "The total number of packets dropped by IPsec phase-2 tunnels during sending process."
        ::= { ibIPsecTunnelStatByDescripV2Entry 12 }

    ibIPsecTunOutEncryptFailsByDescripV2 OBJECT-TYPE
        SYNTAX Counter64
        MAX-ACCESS read-only
        STATUS current
        DESCRIPTION
            "The total number of outbound encryption failures
             on IPsec Phase-2 Tunnels."
        ::= { ibIPsecTunnelStatByDescripV2Entry 13 }

    ibIPsecTunNoMemoryDropPktsByDescripV2 OBJECT-TYPE
        SYNTAX Counter64
        MAX-ACCESS read-only
        STATUS current
        DESCRIPTION
            "The total number of packets dropped by IPsec phase-2 tunnels due to no enough memory."
        ::= { ibIPsecTunnelStatByDescripV2Entry 14 }

    ibIPsecTunQueueFullDropPktsByDescripV2 OBJECT-TYPE
        SYNTAX Counter64
        MAX-ACCESS read-only
        STATUS current
        DESCRIPTION
            "The total number of packets dropped by
             IPsec phase-2 tunnels due to queue full."
        ::= { ibIPsecTunnelStatByDescripV2Entry 15 }

    ibIPsecTunInvalidLenDropPktsByDescripV2 OBJECT-TYPE
        SYNTAX Counter64
        MAX-ACCESS read-only
        STATUS current
        DESCRIPTION
            "The total number of packets dropped by IPsec phase-2 tunnels due to invalid length packet."
        ::= { ibIPsecTunnelStatByDescripV2Entry 16 }

    ibIPsecTunTooLongDropPktsByDescripV2 OBJECT-TYPE
        SYNTAX Counter64
        MAX-ACCESS read-only
        STATUS current
        DESCRIPTION
            "The total number of packets dropped by IPsec phase-2 tunnels due to packet."
        ::= { ibIPsecTunnelStatByDescripV2Entry 17 }

    ibIPsecTunInvalidSaDropPktsByDescripV2 OBJECT-TYPE
        SYNTAX Counter64
        MAX-ACCESS read-only
        STATUS current
        DESCRIPTION
            "The total number of packets dropped by IPsec phase-2 tunnels due to invalid SA."
        ::= { ibIPsecTunnelStatByDescripV2Entry 18 }

-- ===============================================
-- Conformance Information
-- ===============================================
    ibIPsecConformanceV2   OBJECT IDENTIFIER
        ::= { ibIPsecMonitorV2 2 }
    ibIPsecCompliancesV2   OBJECT IDENTIFIER
        ::= { ibIPsecConformanceV2 1 }
    ibIPsecGroupsV2        OBJECT IDENTIFIER
        ::= { ibIPsecConformanceV2 2 }

-- ===============================================
-- Compliance Statements
-- ===============================================
    ibIPsecComplianceV2 MODULE-COMPLIANCE
        STATUS current
        DESCRIPTION
            " "
        MODULE -- this module
        MANDATORY-GROUPS
            {
                ibIPsecScalarObjectsGroupV2,
                ibIPsecTunnelTableGroupV2,
                ibIPsecTunnelStatGroupV2,
                ibIPsecSaGroupV2,
                ibIPsecTrafficTableGroupV2,
                ibIPsecGlobalStatsGroupV2,
                ibIPsecTrapObjectGroupV2,
                ibIPsecTrapCntlGroupV2,
                ibIPsecTrapGroupV2
            }
        ::= { ibIPsecCompliancesV2 1 }

    ibIPsecScalarObjectsGroupV2 OBJECT-GROUP
        OBJECTS {
                    ibIPsecMIBVersion
                }
        STATUS current
        DESCRIPTION
            "The group contains all of scalar objects of the MIB."
        ::= { ibIPsecGroupsV2 1 }

    ibIPsecTunnelTableGroupV2 OBJECT-GROUP
        OBJECTS {
                    ibIPsecTunIfIndexV2,
                    ibIPsecTunIKETunnelIndexV2,
                    ibIPsecTunIKETunLocalIDTypeV2,
                    ibIPsecTunIKETunLocalIDVal1V2,
                    ibIPsecTunIKETunLocalIDVal2V2,
                    ibIPsecTunIKETunRemoteIDTypeV2,
                    ibIPsecTunIKETunRemoteIDVal1V2,
                    ibIPsecTunIKETunRemoteIDVal2V2,
                    ibIPsecTunLocalAddrTypeV2,
                    ibIPsecTunLocalAddrV2,
                    ibIPsecTunRemoteAddrTypeV2,
                    ibIPsecTunRemoteAddrV2,
                    ibIPsecTunKeyTypeV2,
                    ibIPsecTunEncapModeV2,
                    ibIPsecTunInitiatorV2,
                    ibIPsecTunLifeSizeV2,
                    ibIPsecTunLifeTimeV2,
                    ibIPsecTunRemainTimeV2,
                    ibIPsecTunActiveTimeV2,
                    ibIPsecTunRemainSizeV2,
                    ibIPsecTunTotalRefreshesV2,
                    ibIPsecTunCurrentSaInstancesV2,
                    ibIPsecTunInSaEncryptAlgoV2,
                    ibIPsecTunInSaAhAuthAlgoV2,
                    ibIPsecTunInSaEspAuthAlgoV2,
                    ibIPsecTunDiffHellmanGrpV2,
                    ibIPsecTunOutSaEncryptAlgoV2,
                    ibIPsecTunOutSaAhAuthAlgoV2,
                    ibIPsecTunOutSaEspAuthAlgoV2,
                    ibIPsecTunPolicyNameV2,
                    ibIPsecTunPolicyNumV2,
                    ibIPsecTunStatusV2,
                    ibIPsecTunPolicyDescriptionV2,
                    ibIPsecTunIKETunLocalIDVal3V2,
                    ibIPsecTunIKETunRemoteIDVal3V2,
                    ibIPsecTunProfileNameV2
                }
        STATUS current
        DESCRIPTION
            "The group contains the IPsec tunnel's property information."
        ::= { ibIPsecGroupsV2 2 }

    ibIPsecTunnelStatGroupV2 OBJECT-GROUP
        OBJECTS {
                    ibIPsecTunInOctetsV2,
                    ibIPsecTunInDecompOctetsV2,
                    ibIPsecTunInPktsV2,
                    ibIPsecTunInDropPktsV2,
                    ibIPsecTunInReplayDropPktsV2,
                    ibIPsecTunInAuthFailsV2,
                    ibIPsecTunInDecryptFailsV2,
                    ibIPsecTunOutOctetsV2,
                    ibIPsecTunOutUncompOctetsV2,
                    ibIPsecTunOutPktsV2,
                    ibIPsecTunOutDropPktsV2,
                    ibIPsecTunOutEncryptFailsV2,
                    ibIPsecTunNoMemoryDropPktsV2,
                    ibIPsecTunQueueFullDropPktsV2,
                    ibIPsecTunInvalidLenDropPktsV2,
                    ibIPsecTunTooLongDropPktsV2,
                    ibIPsecTunInvalidSaDropPktsV2
                }
        STATUS current
        DESCRIPTION
            "The group contains the IPsec tunnel's statistic information."
        ::= { ibIPsecGroupsV2 3 }

    ibIPsecSaGroupV2 OBJECT-GROUP
        OBJECTS {
                    ibIPsecSaDirectionV2,
                    ibIPsecSaSpiValueV2,
                    ibIPsecSaSecProtocolV2,
                    ibIPsecSaEncryptAlgoV2,
                    ibIPsecSaAuthAlgoV2,
                    ibIPsecSaStatusV2
                }
        STATUS current
        DESCRIPTION
            "The group contains the SA's property information."
        ::= { ibIPsecGroupsV2 4 }

    ibIPsecTrafficTableGroupV2 OBJECT-GROUP
        OBJECTS {
            ibIPsecTrafficLocalTypeV2,
            ibIPsecTrafficLocalAddr1TypeV2,
            ibIPsecTrafficLocalAddr1V2,
            ibIPsecTrafficLocalAddr2TypeV2,
            ibIPsecTrafficLocalAddr2V2,
            ibIPsecTrafficLocalProtocol1V2,
            ibIPsecTrafficLocalProtocol2V2,
            ibIPsecTrafficLocalPort1V2,
            ibIPsecTrafficLocalPort2V2,
            ibIPsecTrafficRemoteTypeV2,
            ibIPsecTrafficRemAddr1TypeV2,
            ibIPsecTrafficRemAddr1V2,
            ibIPsecTrafficRemAddr2TypeV2,
            ibIPsecTrafficRemAddr2V2,
            ibIPsecTrafficRemoPro1V2,
            ibIPsecTrafficRemoPro2V2,
            ibIPsecTrafficRemPort1V2,
            ibIPsecTrafficRemPort2V2
        }
        STATUS current
        DESCRIPTION
            "The group contains the property information of the
             data flow protected by IPsec tunnel."
        ::= { ibIPsecGroupsV2 5 }

    ibIPsecGlobalStatsGroupV2 OBJECT-GROUP
        OBJECTS {
                    ibIPsecGlobalActiveTunnelsV2,
                    ibIPsecGlobalActiveSasV2,
                    ibIPsecGlobalInOctetsV2,
                    ibIPsecGlobalInDecompOctetsV2,
                    ibIPsecGlobalInPktsV2,
                    ibIPsecGlobalInDropsV2,
                    ibIPsecGlobalInReplayDropsV2,
                    ibIPsecGlobalInAuthFailsV2,
                    ibIPsecGlobalInDecryptFailsV2,
                    ibIPsecGlobalOutOctetsV2,
                    ibIPsecGlobalOutUncompOctetsV2,
                    ibIPsecGlobalOutPktsV2,
                    ibIPsecGlobalOutDropsV2,
                    ibIPsecGlobalOutEncryptFailsV2,
                    ibIPsecGlobalNoMemoryDropsV2,
                    ibIPsecGlobalNoFindSaDropsV2,
                    ibIPsecGlobalQueueFullDropsV2,
                    ibIPsecGlobalInvalidLenDropsV2,
                    ibIPsecGlobalTooLongDropsV2,
                    ibIPsecGlobalInvalidSaDropsV2
                }
        STATUS current
        DESCRIPTION
            "The group contains all of the IPsec tunnel's statistic
             information."
        ::= { ibIPsecGroupsV2 6 }

    ibIPsecTrapObjectGroupV2 OBJECT-GROUP
        OBJECTS {
                    ibIPsecPolicyNameV2,
                    ibIPsecPolicySeqNumV2,
                    ibIPsecPolicySizeV2,
                    ibIPsecTunStopReasonV2
                }
        STATUS current
        DESCRIPTION
            "The group contains all of trap objects of IPsec tunnels."
        ::= { ibIPsecGroupsV2 7 }

    ibIPsecTrapCntlGroupV2 OBJECT-GROUP
        OBJECTS {
                    ibIPsecTrapGlobalCntlV2,
                    ibIPsecTunnelStartTrapCntlV2,
                    ibIPsecTunnelStopTrapCntlV2,
                    ibIPsecNoSaTrapCntlV2,
                    ibIPsecAuthFailureTrapCntlV2,
                    ibIPsecEncryFailureTrapCntlV2,
                    ibIPsecDecryFailureTrapCntlV2,
                    ibIPsecInvalidSaTrapCntlV2,
                    ibIPsecPolicyAddTrapCntlV2,
                    ibIPsecPolicyDelTrapCntlV2,
                    ibIPsecPolicyAttachTrapCntlV2,
                    ibIPsecPolicyDetachTrapCntlV2
                }
        STATUS current
        DESCRIPTION
            "The group contains all of trap switches of IPsec tunnels."
        ::= { ibIPsecGroupsV2 8 }

    ibIPsecTrapGroupV2 NOTIFICATION-GROUP
        NOTIFICATIONS {
                          ibIPsecTunnelStartV2,
                          ibIPsecTunnelStopV2,
                          ibIPsecNoSaFailureV2,
                          ibIPsecAuthFailFailureV2,
                          ibIPsecEncryFailFailureV2,
                          ibIPsecDecryFailFailureV2,
                          ibIPsecInvalidSaFailureV2,
                          ibIPsecPolicyAddV2,
                          ibIPsecPolicyDelV2,
                          ibIPsecPolicyAttachV2,
                          ibIPsecPolicyDetachV2,
                          ibIPsecConnectionStartV2,
                          ibIPsecConnectionStopV2
                      }
        STATUS current
        DESCRIPTION
            "The group contains all of trap of IPsec tunnels."
        ::= { ibIPsecGroupsV2 9 }


END
