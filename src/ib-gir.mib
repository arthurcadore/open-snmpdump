-- =====================================================================
-- Copyright (C) 2023 Intelbras S.A. All rights reserved.
--
-- Description: GIR MIB
-- Reference:
-- Version: V1.1
-- History:
--   V1.0 Initial version, created by wangmeng
--   V1.1 Add ibGirMainSysmodeChangeFailed trap by zhengjun, 2023-06-01.
-- =====================================================================
IB-GIR-MIB DEFINITIONS ::= BEGIN

IMPORTS
    ibCommon
        FROM IB-OID-MIB
    Integer32, OBJECT-TYPE, MODULE-IDENTITY, NOTIFICATION-TYPE
        FROM SNMPv2-SMI
    DisplayString
            FROM SNMPv2-TC;

ibGir MODULE-IDENTITY
    LAST-UPDATED "202306011035Z"    -- June 01, 2023 at 10:35 GMT
    ORGANIZATION
        "Intelbras S.A. Industria de Telecomunicacao Eletronica Brasileria."
    CONTACT-INFO
        ""
    DESCRIPTION
        "
        Graceful insertion and removal (GIR) enables you to gracefully isolate
        the device from the network for device maintenance or upgrade.
        "
    REVISION "202306011035Z"
    DESCRIPTION
        "Add trap for maintenance system mode change failed."
    REVISION "202107011126Z"
    DESCRIPTION
        "The initial revision of this MIB module."
    ::= { ibCommon 205 }

--
-- Node definitions
--

ibGirObjects OBJECT IDENTIFIER ::= { ibGir 1 }


ibGirSystemGroup OBJECT IDENTIFIER ::= { ibGirObjects 1 }


ibGirSystemMode OBJECT-TYPE
    SYNTAX INTEGER
        {
        normal(1),
        isolation(2),
        shutdown(3)
        }
    MAX-ACCESS read-write
    STATUS current
    DESCRIPTION
        "
        Change system mode.
        normal-Normal mode(Default).
        isolation-Maintenance mode by isolation.
        shutdown-Maintenance mode by shutdown.
        "
    ::= { ibGirSystemGroup 1 }

ibGirRevertDelayTime OBJECT-TYPE
    SYNTAX Integer32 (0 | 5..65535)
    UNITS "minutes"
    MAX-ACCESS read-write
    STATUS current
    DESCRIPTION
        "
        Auto change to normal mode after the specified amount of time in
        minutes.  If 0 is set, no switchback will be performed.
        "
    DEFVAL { 0 }
    ::= { ibGirSystemGroup 2 }

-- trap --
ibGirTrap OBJECT IDENTIFIER ::= { ibGir 2 }


ibGirTrapPrex OBJECT IDENTIFIER ::= { ibGirTrap 0 }

ibGirMainSysmodeChangeFailed NOTIFICATION-TYPE
    OBJECTS
        {
            ibGirSystemMode,
            ibGirCmd
        }
    STATUS       current
    DESCRIPTION
        "This trap indicates that the system change mode failed
        due to a specific command line."
    ::= { ibGirTrapPrex 1 }

-- All objects used for trap only are defined here.
ibGirTrapObjects OBJECT IDENTIFIER ::= { ibGirTrap 1 }


ibGirCmd OBJECT-TYPE
    SYNTAX      DisplayString (SIZE(0..512))
    MAX-ACCESS accessible-for-notify
    STATUS current
    DESCRIPTION
        "This value is the gir command line info."
    ::= { ibGirTrapObjects 1 }

END
