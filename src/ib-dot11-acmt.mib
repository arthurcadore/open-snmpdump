-- =============================================================================
-- Copyright (C) 2023 Intelbras S.A. All rights reserved.
--
-- Description:
--   The file defines a MIB to provide wireless switch object and CAPWAP
--   tunnel information.
-- Reference:
-- Version: V2.8
-- History:
--   V1.0 created by shiyang (Richard)
--     Initial version 2006-05-10
--   V1.1 2007-04-27 modified by shiyang(Richard)
--        Add apCfgChange(6) for ibDot11ACMtTrapTunlDwnInfo.
--        Delete ibDot11ACPhysicalIndex,ibDot11ACGlobalCountryCode,
--        ibDot11ACCtrlTunnelSecSupport and ibDot11ACDataTunnelSecSupport
--        nodes.
--   V1.2 2007-06-19 modified by Vikas K.
--        Add ibDot11WLANAssocStatisInfo for ibDot11ACObjectGroup.
--        Add ibDot11MaxAPNumPermitted and ibDot11MaxStationNumPermitted
--        nodes.
--   V1.3 2007-12-21 modified by wanghao (Kumar)
--        Add ibDot11StationExDeAuthenSum and ibDot11StationCurAssocSum
--        for ibDot11WLANAssocStatisInfo.
--   V1.4 2008-07-09 modified by ChangHuifeng
--        Add ibDot11ACMtBackupSwtTrap and ibDot11ACMtTrapBackupSwitchInfo
--        for ibDot11ACMtNotifyGroup.
--        Change description of ibDot11ACMtTunnelSetupTrap.
--   V1.5 2008-12-03 modified by Wang Lu
--        Add new variable bindings ibDot11ACMtTrapTnlAPName and
--        ibDot11ACMtTrapTnlAPIPAddr to ibDot11ACMtTunnelSetupTrap and
--        ibDot11ACMtTunnelDownTrap.
--   V1.6 2009-05-07 modified by Wang Shaojie
--        Add new trap ibDot11ACLoadBalanceTrap.
--        Add new variable bindings ibDot11LoadBalanceType,
--        ibDot11LoadBalanceThreshold for ibDot11ACLoadBalanceTrap.
--        Add ibDot11ACIFLoadInfoTable to ibDot11ACIFLoadInfoTable.
--   V1.7 2009-07-29 modified by Heziqi
--        Add new variable bindings ibDot11ACMtTrapAPIPv6Addr
--        to ibDot11ACMtTunnelSetupTrap and ibDot11ACMtTunnelDownTrap.
--        Add ibDot11MasterAPCount, ibDot11SlaveAPCount,
--        ibDot11ConnectAutoAPCount and ibDot11PersistentAPCount to
--        ibDot11ACLoadInfo.
--   V1.8 2009-08-07 modified by Wang Shaojie, Qi Kai
--        Add new variable bindings ibDot11ACMtTrapTunlDwnCount
--        to ibDot11ACMtTrapVarObjects
--        Add ibDot11ACIfStaNum, ibDot11ACIfName to ibDot11ACIFLoadInfoTable
--   V1.9 2009-12-01 modified by Wang Shaojie
--        Add ibDot11ACStaFullTrap to ibDot11ACMtTraps and variable bindings
--        ibDot11ACMaxStaNum for ibDot11ACStaFullTrap.
--        Add ibDot11CtrlTunnelUpTimeTicks to ibDot11CAPWAPTunnelTable
--        Add ibDot11AcDownloadFrameCnt, ibDot11AcUploadFrameCnt,
--        ibDot11AcDownloadFrameBytes, ibDot11AcUploadFrameBytes to
--        ibDot11ACLoadInfo.
--        2010-06-10 added ibDot11ACBASIfTable by jinyi
--        2010-08-04 modified by yin junjie
--        Add new table ibDot11ACStaUserSecAuthStatis
--        Add ibDot11ACStaUserAuthCurNumber, ibDot11ACStaUserConnFailCnt,
--        ibDot11ACStaUserAuthReqCnt, ibDot11ACStaUserAuthSuccCnt,
--        ibDot11ACStaUserAuthFailCnt to ibDot11ACStaUserSecAuthStatis.
--   V2.0 2011-09-30 modified by Dong Laqi
--        Add ibDot11ACMtTrapTnlAPSysName,ibDot11ACMtFirstTrapTime
--        to ibDot11ACMtTrapVarObjects
--        and variable bindings ibDot11ACMtFirstTrapTime for
--        ibDot11ACMtTunnelSetupTrap,ibDot11ACMtTunnelDownTrap,
--        ibDot11ACMtBackupSwtTrap.
--        2012-02-14 modified by Dong Laqi
--        Add ibDot11BackupACRole,ibDot11BackupACNMSIP,ibDot11ACBackupMode,
--        ibDot11ACBackupStatus and ibDot11ACSwitchCnt to ibDot11ACLoadInfo
--        Add ibDot11ACStatusSwitchTrap to ibDot11ACMtTraps
--        and binding ibDot11ACMtTrapACStatusSwitchInfo and ibDot11MasterACNmsIP
--        for ibDot11ACMtTrapVarObjects
--   V2.1 2012-05-08 modified by Liu Xuping
--        Add new table ibDot11ACStaSecAuthTypeStatis
--        Add ibDot11ACStaUserPortalOnlineNum,ibDot11ACStaUserFreeAuthOnlineNum,
--        ibDot11ACStaUserAssociateAuthOnlineNum,ibDot11ACStaUserMacAuthOnlineNum,
--        ibDot11ACStaUserPortalLostConnectionCnt,
--        ibDot11ACStaUserFreeAuthLostConnectionCnt,
--        ibDot11ACStaUserAssociateAuthLostConnectionCnt,
--        ibDot11ACStaUserMacAuthLostConnectionCnt,
--        ibDot11ACStaPortalAuthReqCnt,ibDot11ACStaAssociateAuthReqCnt,
--        ibDot11ACStaMacAuthReqCnt,
--        ibDot11ACStaPortalAuthSuccCnt,ibDot11ACStaAssociateAuthSuccCnt,
--        ibDot11ACStaMacAuthSuccCnt,
--        ibDot11ACStaPortalAuthReqFailCnt,ibDot11ACStaAssociateAuthReqFailCnt,
--        ibDot11ACStaMacAuthReqFailCnt to ibDot11ACStaSecAuthTypeStatis.
--        2012-05-16 modified by lihonghao
--        Add ibDot11ACSouthifPacketOutputCount,ibDot11ACSouthifPacketOutputBytes
--        ibDot11ACSouthifPacketInputCount and ibDot11ACSouthifPacketInputBytes
--        to ibDot11ACLoadInfo
--        2012-08-17 modified Zhang Congcong & LiXin
--        Add new node   ibDot11RunAPNumThreshold       to ibDot11ACObject
--        Add new node   ibDot11RunAPNumOverload        to ibDot11ACMtTraps
--        Add new node   ibDot11RunAPNumOverloadRecover to ibDot11ACMtTraps
--        Add new object ibDot11ACMtTrapAPMacAddress    to ibDot11ACMtTunnelSetupTrap
--        Add new object ibDot11ACMtTrapAPMacAddress    to ibDot11ACMtTunnelDownTrap
--        Add new node   ibDot11ACMtTrapAPMacAddress    to ibDot11ACMtTrapVarObjects
--   V2.2 2013-07-08 modified by Chen Guoxi
--        Add new node   ibDot11StationAssocReqSum      to ibDot11WLANAssocStatisInfo
--        Add new node   ibDot11StationReassocReqSum    to ibDot11WLANAssocStatisInfo
--        Add new node   ibDot11StationReassocFailSum   to ibDot11WLANAssocStatisInfo
--   v2.3 2013-07-08 modified by Xiao Min
--        Add new node   ibDot11TotalAPconnected        to ibDot11ACLoadInfo
--        Add new node   ibDot11RemainingAPcapacity     to ibDot11ACLoadInfo
--   v2.4 2014-02-14 modified by Zhou Weichao
--        Add new node ibDot11ACStaUserAutoAuthOnlineNumCM,
--        ibDot11ACStaUserAutoAuthLostConnectionCntCM,
--        ibDot11ACStaAutoAuthReqCntCM,
--        ibDot11ACStaAutoAuthSuccCntCM,
--        ibDot11ACStaAutoAuthReqFailCntCM to ibDot11ACStaSecAuthTypeStatis
--        Modify node ibDot11ACStaUserPortalOnlineNum,
--        ibDot11ACStaUserAssociateAuthOnlineNum from ibDot11ACStaSecAuthTypeStatis
--        Add ibDot11ACStaUserAllAuthCntCM to ibDot11ACStaUserSecAuthStatis
--        Add new table ibDot11ACPortalStatisticCMTable
--        Add ibDot11ACPortalStatisticCMEntry, ibDot11PortalStatisticSSIDCM,
--        ibACPortalStatAuthReqCM and
--        ibACPortalStatAuthRespCM to ibDot11ACPortalStatisticCMTable
--   v2.5 2016-03-11 modified by yubo 04460
--        Add new node   ibDot11MaxNewConnCntPerSecCM to ibDot11ACObject
--        Add new node   ibDot11IFNumberCM to ibDot11ACObject
--        Add new node   ibDot11ACStaUserAuthRespCntCM to ibDot11ACStaUserSecAuthStatis
--        2016-06-15 modified by zhouwenshuai kf6157
--        Add new table   ibDot11LocalACModelTable
--        Add IbDot11LocalACModelEntry, ibDot11LocalACModelAlias
--        ibDot11LocalACModelName,
--        ibDot11LocalACManufacturer, ibDot11LocalACCPUType
--        ibDot11LocalACCPUClockSpeed, ibDot11LocalACMemoryType
--        ibDot11LocalACMemorySize, ibDot11LocalACFlashType
--        ibDot11LocalACFlashSize, ibDot11LocalACMemSize
--        ibDot11LocalACFlashSizeInBytes to ibDot11LocalACModelTable
--        2016-09-05 modified by yangxiaobin ykf4651
--        Add new node   ibDot11APLicenseWeight to ibDot11ACObject
--   v2.6 2018-06-04 modified by wangshujuan w13748
--        Add new node   ibDot11ACTotalRebootCnt to ibDot11ACObject
--        Add new node   ibDot11APInvalidCertificateTrap  to ibDot11ACMtTraps
--   v2.7 2021-06-18 modified by liyapeng
--        Add new object ibDot11ACMtTrapACMacAddress to ibDot11ACMtBackupSwtTrap
--   v2.8 2023-01-06 modified by fanwenyang
--        Add new object ibDot11Secretkey to ibDot11ACLoadInfo
-- =============================================================================
IB-DOT11-ACMT-MIB DEFINITIONS ::= BEGIN

IMPORTS
        MODULE-IDENTITY,
        OBJECT-TYPE,
        NOTIFICATION-TYPE,
        Integer32,
        Counter32,
        IpAddress,
        Counter64,
        TimeTicks,
        Unsigned32
    FROM SNMPv2-SMI
        IANAifType
    FROM IANAifType-MIB
        ibDot11,
        IbDot11MACModeType,
        IbDot11TunnelSecSchemType,
        IbDot11ObjectIDType
    FROM IB-DOT11-REF-MIB
        MacAddress
    FROM SNMPv2-TC;

ibDot11ACMT MODULE-IDENTITY
    LAST-UPDATED "202301061100Z"        -- Jan 6, 2023 at 11:00 GMT
    ORGANIZATION
        "Intelbras S.A. Industria de Telecomunicacao Eletronica Brasileria."
    CONTACT-INFO
        ""
    DESCRIPTION
        "This MIB defines information as per wireless AC and tunnel between
        AP and AC.
        If NMS intends to get more detailed information for the AP and AC,
        it could refer entPhysicalIndex in the Entity MIB to get entity
        information.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Radio
        The chip set to receive and send wireless signal.

        Fat AP
        Applied in the home, SOHO and so on, and it could
        independently work without help from AC.

        Fit AP
        Applied in the enterprise environment, it will work
        under the control and management from AC.

        Control And Provisioning of Wireless Access Points Protocol
        The short name of protocol is CAPWAP. AC will control
        and manage AP by CAPWAP tunnel protocol defined by IETF.
        Also, a data tunnel will be set up between AC and AP.

        Basic Service Set
        The IEEE 802.11 BSS of an AP comprises of the
        stations directly associating with the AP. It will
        be identified by BSSID."
    REVISION "202301061100Z"        -- Jan 6, 2023 at 11:00 GMT
    DESCRIPTION
        "Add new nodes."
    REVISION "202106181800Z"        -- Jun 18, 2021 at 18:00 GMT
    DESCRIPTION
        " Modify the OBJECTS of the trap node "
    REVISION "201806041800Z"        -- Jun 04, 2018 at 18:00 GMT
    DESCRIPTION
        "Add new nodes."
    REVISION "201603111800Z"        -- Mar 11, 2016 at 18:00 GMT
    DESCRIPTION
        "Add new nodes."
    REVISION "201008041800Z"        -- Aug 04, 2010 at 18:00 GMT
    DESCRIPTION
        "Add new nodes."
    REVISION "200908071800Z"        -- Aug 07, 2009 at 18:00 GMT
    DESCRIPTION
        "Modified to add new nodes."
    REVISION "200907291800Z"        -- Jul 29, 2009 at 18:00 GMT
    DESCRIPTION
        "Modified to add new nodes."
    REVISION "200905072000Z"        -- May 7, 2009 at 20:00 GMT
    DESCRIPTION
        "Modified to add new nodes."
    REVISION "200807091800Z"        -- July 09, 2008 at 18:00 GMT
    DESCRIPTION
        "Modified to add new nodes."
    REVISION "200712211800Z"        -- Dec 21, 2007 at 18:00 GMT
    DESCRIPTION
        "Modified to add new nodes."
    REVISION "200706191800Z"        -- June 19, 2007 at 18:00 GMT
    DESCRIPTION
        "Modified to add new table and new nodes."
    REVISION "200704272000Z"        -- Apr 27, 2007 at 20:00 GMT
    DESCRIPTION
        "Modified to fix some issue."
    REVISION "200605101900Z"        -- May 10, 2006 at 19:00 GMT
    DESCRIPTION
        "The initial revision of this MIB module."
    ::= { ibDot11 1 }

-- *****************************************************************************
-- *  Major sections
-- *****************************************************************************

--  AC Object Group Attributes
--  DEFINED AS " The group provides AC information like MAC Mode and so on,
--  also could refer to software version and hardware version kept
--  by Entity MIB by Physical index"

ibDot11ACObjectGroup OBJECT IDENTIFIER     ::= { ibDot11ACMT 1 }
ibDot11ACObject OBJECT IDENTIFIER          ::= { ibDot11ACObjectGroup 1 }
ibDot11ACLoadInfo OBJECT IDENTIFIER        ::= { ibDot11ACObjectGroup 2 }
ibDot11WLANAssocStatisInfo OBJECT IDENTIFIER  ::= { ibDot11ACObjectGroup 3 }
ibDot11ACBASInfo OBJECT IDENTIFIER  ::= { ibDot11ACObjectGroup 4 }
ibDot11ACStaUserSecAuthStatis OBJECT IDENTIFIER    ::= { ibDot11ACObjectGroup 5 }
ibDot11ACStaSecAuthTypeStatis OBJECT IDENTIFIER    ::= { ibDot11ACObjectGroup 6 }

--  AC CAPWAP tunnel Group Attributes
--  DEFINED AS "The group provides CAPWAP tunnel information"

ibDot11CAPWAPTunnelGroup OBJECT IDENTIFIER  ::= { ibDot11ACMT 2 }

--  AC CAPWAP Notification
--  DEFINED AS "The notification for AC Management"

ibDot11ACMtNotifyGroup OBJECT IDENTIFIER    ::= { ibDot11ACMT 3 }

-- *****************************************************************************
-- *  ibDot11ACObject element Definition
-- *****************************************************************************
ibDot11CurrentACMACMode OBJECT-TYPE
    SYNTAX      IbDot11MACModeType
    MAX-ACCESS  read-only
    STATUS      current
    DESCRIPTION
        "Represents which MAC mode defined in the CAPWAP draft is in use
        for the AC."
    DEFVAL      { split }
    ::= { ibDot11ACObject 1 }

ibDot11MaxAPNumPermitted OBJECT-TYPE
    SYNTAX      Integer32
    MAX-ACCESS  read-only
    STATUS      current
    DESCRIPTION
        "Represents the maximum number of AP connection permitted
        for one AC."
    ::= { ibDot11ACObject 2 }

ibDot11MaxStationNumPermitted OBJECT-TYPE
    SYNTAX      Integer32
    MAX-ACCESS  read-only
    STATUS      current
    DESCRIPTION
        "Represents the maximum number of station connection
        permitted for one AC."
    ::= { ibDot11ACObject 3 }
ibDot11RunAPNumThreshold OBJECT-TYPE
    SYNTAX      Integer32(30..100)
    UNITS       "percent"
    MAX-ACCESS  read-write
    STATUS      current
        DESCRIPTION
        "When the percentage of run AP number is larger than this
        threshold, a notification will be sent."
    DEFVAL      { 100 }
    ::= { ibDot11ACObject 4 }

ibDot11MaxNewConnCntPerSecCM OBJECT-TYPE
    SYNTAX      Integer32
    MAX-ACCESS  read-write
    STATUS      current
    DESCRIPTION
        "Represents the maximum count of station connected to AC per second."
    DEFVAL      { 300 }
    ::= { ibDot11ACObject 5 }

ibDot11IFNumberCM OBJECT-TYPE
    SYNTAX      Integer32
    MAX-ACCESS  read-write
    STATUS      current
    DESCRIPTION
        "All intface in AC except console."
    DEFVAL      { 24 }
    ::= { ibDot11ACObject 6 }

ibDot11APLicenseWeight OBJECT-TYPE
    SYNTAX      OCTET STRING
    MAX-ACCESS  read-only
    STATUS      current
    DESCRIPTION
        "Represents the license weight of AP connection for one AC."
    ::= { ibDot11ACObject 7 }

ibDot11ACTotalRebootCnt OBJECT-TYPE
    SYNTAX      Integer32
    MAX-ACCESS  read-only
    STATUS      current
    DESCRIPTION
        "Represents the total number of AC restarts."
    ::= { ibDot11ACObject 8 }

-- *****************************************************************************
-- *  End of ibDot11ACObject element Definition
-- *****************************************************************************

-- *****************************************************************************
-- *  ibDot11ACLoadInfo element Definition
-- *****************************************************************************
ibDot11APConnectCount OBJECT-TYPE
    SYNTAX      Integer32
    MAX-ACCESS  read-only
    STATUS      current
    DESCRIPTION
        "Represents the total number of APs which are connecting to AC."
    ::= { ibDot11ACLoadInfo 1 }

ibDot11StationConnectCount OBJECT-TYPE
    SYNTAX      Integer32
    MAX-ACCESS  read-only
    STATUS      current
    DESCRIPTION
        "Represents the total number of stations which are accessing the
        WLAN service through AC."
    ::= { ibDot11ACLoadInfo 2 }

-- *****************************************************************************
-- *  ibDot11ACIFLoadInfoTable Definition
-- *****************************************************************************
ibDot11ACIFLoadInfoTable OBJECT-TYPE
    SYNTAX      SEQUENCE OF IbDot11ACIFLoadInfoEntry
    MAX-ACCESS  not-accessible
    STATUS      current
    DESCRIPTION
        "Represents AP number information of interface."
    ::= { ibDot11ACLoadInfo 3 }

ibDot11ACIFLoadInfoEntry OBJECT-TYPE
    SYNTAX      IbDot11ACIFLoadInfoEntry
    MAX-ACCESS  not-accessible
    STATUS      current
    DESCRIPTION
        "Each entry represents AP number information of an interface"
    INDEX
        {
            ibDot11ACIfIndex
        }
    ::= { ibDot11ACIFLoadInfoTable 1 }

IbDot11ACIFLoadInfoEntry ::= SEQUENCE
    {
        ibDot11ACIfIndex       Integer32,
        ibDot11ACIfApNum       Integer32,
        ibDot11ACIfStaNum      Integer32,
        ibDot11ACIfName        OCTET STRING
    }

ibDot11ACIfIndex OBJECT-TYPE
    SYNTAX      Integer32
    MAX-ACCESS  accessible-for-notify
    STATUS      current
    DESCRIPTION
        "Represents index of AC interface."
    ::= { ibDot11ACIFLoadInfoEntry 1 }

ibDot11ACIfApNum OBJECT-TYPE
    SYNTAX      Integer32
    MAX-ACCESS  read-only
    STATUS      current
    DESCRIPTION
        "Represents AP number connected to the AC interface."
    ::= { ibDot11ACIFLoadInfoEntry 2 }

ibDot11ACIfStaNum OBJECT-TYPE
    SYNTAX      Integer32
    MAX-ACCESS  read-only
    STATUS      current
    DESCRIPTION
        "Represents Station number connected to the AC interface."
    ::= { ibDot11ACIFLoadInfoEntry 3 }

ibDot11ACIfName OBJECT-TYPE
    SYNTAX      OCTET STRING
    MAX-ACCESS  read-only
    STATUS      current
    DESCRIPTION
        "Represents InterfaceName AP number connected to AC interface."
    ::= { ibDot11ACIFLoadInfoEntry 4 }

-- *****************************************************************************
-- *  End of ibDot11ACIFLoadInfoTable element Definition
-- *****************************************************************************
ibDot11MasterAPCount OBJECT-TYPE
    SYNTAX      Integer32
    MAX-ACCESS  read-only
    STATUS      current
    DESCRIPTION
        "Represents the total number of AP which have established the
        master tunnel with AC."
    ::= { ibDot11ACLoadInfo 4 }

ibDot11SlaveAPCount OBJECT-TYPE
    SYNTAX      Integer32
    MAX-ACCESS  read-only
    STATUS      current
    DESCRIPTION
        "Represents the total number of AP which have established the
        slave tunnel with AC."
    ::= { ibDot11ACLoadInfo 5 }

ibDot11ConnectAutoAPCount OBJECT-TYPE
    SYNTAX      Integer32
    MAX-ACCESS  read-only
    STATUS      current
    DESCRIPTION
        "Represents the total number of auto APs that are connecting to AC."
    ::= { ibDot11ACLoadInfo 6 }

ibDot11PersistentAPCount OBJECT-TYPE
    SYNTAX      Integer32
    MAX-ACCESS  read-only
    STATUS      current
    DESCRIPTION
        "Represents the total number of persistent AP."
    ::= { ibDot11ACLoadInfo 7 }

ibDot11AcUploadFrameCnt OBJECT-TYPE
    SYNTAX      Counter64
    MAX-ACCESS  read-only
    STATUS      current
    DESCRIPTION
        "Represents the number of frames that AP sends to AC through LWAPP tunnel."
    ::= { ibDot11ACLoadInfo 8 }

ibDot11AcDownloadFrameCnt OBJECT-TYPE
    SYNTAX      Counter64
    MAX-ACCESS  read-only
    STATUS      current
    DESCRIPTION
        "Represents the number of frames that AC sends to AP through LWAPP tunnel."
    ::= { ibDot11ACLoadInfo 9 }

ibDot11AcUploadFrameBytes OBJECT-TYPE
    SYNTAX      Counter64
    MAX-ACCESS  read-only
    STATUS      current
    DESCRIPTION
        "Represents the bytes of frames that AP sends to AC through LWAPP tunnel."
    ::= { ibDot11ACLoadInfo 10 }

ibDot11AcDownloadFrameBytes OBJECT-TYPE
    SYNTAX      Counter64
    MAX-ACCESS  read-only
    STATUS      current
    DESCRIPTION
        "Represents the bytes of frames that AC sends to AP through LWAPP tunnel."
    ::= { ibDot11ACLoadInfo 11 }

ibDot11BackupACRole OBJECT-TYPE
    SYNTAX      INTEGER
        {
            null(1),
            master(2),
            slave(3)
        }
    MAX-ACCESS  read-only
    STATUS      current
    DESCRIPTION
        "This object represents the Identity of the AC
         null:   Not configured
         master: Master AC
         slave:  Slave AC."
    DEFVAL      { null }
    ::= { ibDot11ACLoadInfo 12 }

ibDot11BackupACNMSIP OBJECT-TYPE
        SYNTAX      IpAddress
        MAX-ACCESS  read-only
        STATUS      current
        DESCRIPTION
            "This object represents the manger IP address of the slave ac."
    ::= { ibDot11ACLoadInfo 13 }

ibDot11ACBackupMode OBJECT-TYPE
        SYNTAX      INTEGER
        {
            null(1),
            hotBackup(2),
            coldBackup(3)
        }
        MAX-ACCESS  read-only
        STATUS      current
        DESCRIPTION
            "This object represents the ac backup mode."
        DEFVAL      { null }
    ::= { ibDot11ACLoadInfo 14 }

ibDot11ACBackupStatus OBJECT-TYPE
        SYNTAX      INTEGER
        {
            active(1),
            standby(2)
        }
        MAX-ACCESS  read-only
        STATUS      current
        DESCRIPTION
            "This object represents the ac backup status."
    ::= { ibDot11ACLoadInfo 15 }

ibDot11ACSwitchCnt OBJECT-TYPE
        SYNTAX      Integer32
        MAX-ACCESS  read-only
        STATUS      current
        DESCRIPTION
            "This object represents the ac switch times."
    ::= { ibDot11ACLoadInfo 16 }

ibDot11ACSouthifPacketOutputCount OBJECT-TYPE
        SYNTAX      Counter64
        MAX-ACCESS  read-only
        STATUS      current
        DESCRIPTION
            "Represents the count of output packets with the down-link interface."
    ::= { ibDot11ACLoadInfo 17 }

ibDot11ACSouthifPacketOutputBytes OBJECT-TYPE
        SYNTAX      Counter64
        MAX-ACCESS  read-only
        STATUS      current
        DESCRIPTION
            "Represents the bytes of output packets with the down-link interface."
    ::= { ibDot11ACLoadInfo 18 }

ibDot11ACSouthifPacketInputCount OBJECT-TYPE
        SYNTAX      Counter64
        MAX-ACCESS  read-only
        STATUS      current
        DESCRIPTION
            "Represents the count of input packets with the down-link interface."
    ::= { ibDot11ACLoadInfo 19 }

ibDot11ACSouthifPacketInputBytes OBJECT-TYPE
        SYNTAX      Counter64
        MAX-ACCESS  read-only
        STATUS      current
        DESCRIPTION
            "Represents the bytes of input packets with the down-link interface."
    ::= { ibDot11ACLoadInfo 20 }

ibDot11TotalAPconnected OBJECT-TYPE
    SYNTAX      Integer32
    MAX-ACCESS  read-only
    STATUS      current
    DESCRIPTION
        "Represents the total number of AP which are connected to AC."
    ::= { ibDot11ACLoadInfo 21 }

ibDot11RemainingAPcapacity OBJECT-TYPE
    SYNTAX      Integer32
    MAX-ACCESS  read-only
    STATUS      current
    DESCRIPTION
        "Represents the remaining AP capacity of the AC."
    ::= { ibDot11ACLoadInfo 22 }

ibDot11Secretkey OBJECT-TYPE
    SYNTAX      OCTET STRING(SIZE(0..16))
    MAX-ACCESS  read-write
    STATUS      current
    DESCRIPTION
        "Save the secret key for the SM4 algorithm."
    ::= { ibDot11ACLoadInfo 33 }

-- *****************************************************************************
-- *  End of ibDot11ACLoad element Definition
-- *****************************************************************************

-- *****************************************************************************
-- *  ibDot11WLANAssocStatisInfo Definition
-- *****************************************************************************
ibDot11StationAssocSum OBJECT-TYPE
    SYNTAX      Counter32
    MAX-ACCESS  read-only
    STATUS      current
    DESCRIPTION
        "Represents the total number of station association."
    ::= { ibDot11WLANAssocStatisInfo 1 }

ibDot11StationAssocFailSum OBJECT-TYPE
    SYNTAX      Counter32
    MAX-ACCESS  read-only
    STATUS      current
    DESCRIPTION
        "Represents the total number of station association failure."
    ::= { ibDot11WLANAssocStatisInfo 2 }

ibDot11StationReassocSum OBJECT-TYPE
    SYNTAX      Counter32
    MAX-ACCESS  read-only
    STATUS      current
    DESCRIPTION
        "Represents the total number of station reassociation."
    ::= { ibDot11WLANAssocStatisInfo 3 }

ibDot11StationAssocRejectedSum OBJECT-TYPE
    SYNTAX      Counter32
    MAX-ACCESS  read-only
    STATUS      current
    DESCRIPTION
        "Represents the total number of station association rejected on
        account of resource limit."
    ::= { ibDot11WLANAssocStatisInfo 4 }

ibDot11StationExDeAuthenSum OBJECT-TYPE
    SYNTAX      Counter32
    MAX-ACCESS  read-only
    STATUS      current
    DESCRIPTION
        "Represents the total number of exceptional station deauthentication
        (Without sending a deauthentication to AP)."
    ::= { ibDot11WLANAssocStatisInfo 5 }

ibDot11StationCurAssocSum OBJECT-TYPE
    SYNTAX      Integer32
    MAX-ACCESS  read-only
    STATUS      current
    DESCRIPTION
        "Represents the total number of current associated stations."
    ::= { ibDot11WLANAssocStatisInfo 6 }

ibDot11StationAssocReqSum OBJECT-TYPE
    SYNTAX      Counter32
    MAX-ACCESS  read-only
    STATUS      current
    DESCRIPTION
        "Represents the total number of station association request."
    ::= { ibDot11WLANAssocStatisInfo 7 }

ibDot11StationReassocReqSum OBJECT-TYPE
    SYNTAX      Counter32
    MAX-ACCESS  read-only
    STATUS      current
    DESCRIPTION
        "Represents the total number of station reassociation request."
    ::= { ibDot11WLANAssocStatisInfo 8 }

ibDot11StationReassocFailSum OBJECT-TYPE
    SYNTAX      Counter32
    MAX-ACCESS  read-only
    STATUS      current
    DESCRIPTION
        "Represents the total number of station reassociation failure."
    ::= { ibDot11WLANAssocStatisInfo 9 }
-- *****************************************************************************
-- *  End of ibDot11WLANAssocStatisInfo Definition
-- *****************************************************************************

-- *****************************************************************************
-- * ibDot11ACBASInfo Definition
-- *****************************************************************************
ibDot11ACBASSysObjects OBJECT IDENTIFIER  ::= { ibDot11ACBASInfo 1 }
ibDot11ACBASTableObjects OBJECT IDENTIFIER  ::= { ibDot11ACBASInfo 2 }

ibDot11ACBASIfTable OBJECT-TYPE
    SYNTAX      SEQUENCE OF IbDot11ACBASIfEntry
    MAX-ACCESS  not-accessible
    STATUS      current
    DESCRIPTION
        "Represents the BAS information of interfaces."
    ::= { ibDot11ACBASTableObjects 3 }

ibDot11ACBASIfEntry OBJECT-TYPE
    SYNTAX      IbDot11ACBASIfEntry
    MAX-ACCESS  not-accessible
    STATUS      current
    DESCRIPTION
        "Each entry represents the BAS information of an interface"
    INDEX
        {
            ibDot11ACBASIfIndex
        }
    ::= { ibDot11ACBASIfTable 1 }

IbDot11ACBASIfEntry ::= SEQUENCE
    {
        ibDot11ACBASIfIndex       Integer32,
        ibDot11ACBASIfDescr       OCTET STRING,
        ibDot11ACBASIfType        IANAifType
    }

ibDot11ACBASIfIndex OBJECT-TYPE
    SYNTAX      Integer32
    MAX-ACCESS  not-accessible
    STATUS      current
    DESCRIPTION
            "The ifIndex of the BAS interface. "
    ::= { ibDot11ACBASIfEntry 1 }

ibDot11ACBASIfDescr OBJECT-TYPE
    SYNTAX      OCTET STRING (SIZE (0..255))
    MAX-ACCESS  read-only
    STATUS      current
    DESCRIPTION
            "A textual string containing information about the BAS interface. "
    ::= { ibDot11ACBASIfEntry 2 }

ibDot11ACBASIfType OBJECT-TYPE
    SYNTAX      IANAifType
    MAX-ACCESS  read-only
    STATUS      current
    DESCRIPTION
            "The type of the BAS interface. "
    ::= { ibDot11ACBASIfEntry 3 }

-- *****************************************************************************
-- *  End of ibDot11ACBASInfo Definition
-- *****************************************************************************

-- *****************************************************************************
-- *  ibDot11ACStaUserSecAuthStatis element Definition
-- *****************************************************************************
ibDot11ACStaUserAuthCurNumber OBJECT-TYPE
    SYNTAX      Integer32
    MAX-ACCESS  read-only
    STATUS      current
    DESCRIPTION
        "Represents the current number of user authenticated with this AC."
    ::= { ibDot11ACStaUserSecAuthStatis 1 }

ibDot11ACStaUserConnFailCnt OBJECT-TYPE
    SYNTAX      Counter32
    MAX-ACCESS  read-only
    STATUS      current
    DESCRIPTION
        "Represents the total number of user disconnected with this AC."
    ::= { ibDot11ACStaUserSecAuthStatis 2 }

ibDot11ACStaUserAuthReqCnt OBJECT-TYPE
    SYNTAX      Counter32
    MAX-ACCESS  read-only
    STATUS      current
    DESCRIPTION
        "Represents the total number of user authenticate request with this AC."
    ::= { ibDot11ACStaUserSecAuthStatis 3 }

ibDot11ACStaUserAuthSuccCnt OBJECT-TYPE
    SYNTAX      Counter32
    MAX-ACCESS  read-only
    STATUS      current
    DESCRIPTION
        "Represents the total number of users authenticated successful with this AC."
    ::= { ibDot11ACStaUserSecAuthStatis 4 }

ibDot11ACStaUserAuthFailCnt OBJECT-TYPE
    SYNTAX      Counter32
    MAX-ACCESS  read-only
    STATUS      current
    DESCRIPTION
        "Represents the total number of user authenticated failed with this AC."
    ::= { ibDot11ACStaUserSecAuthStatis 5 }

ibDot11ACStaUserAllAuthCntCM OBJECT-TYPE
    SYNTAX      Counter32
    MAX-ACCESS  read-only
    STATUS      current
    DESCRIPTION
        "Represents the total number of users authenticated with this AC."
    ::= { ibDot11ACStaUserSecAuthStatis 6 }

ibDot11ACStaUserAuthRespCntCM OBJECT-TYPE
    SYNTAX      Counter32
    MAX-ACCESS  read-only
    STATUS      current
    DESCRIPTION
        "Represents the total number of user authenticate response with this AC."
    ::= { ibDot11ACStaUserSecAuthStatis 7 }

-- *****************************************************************************
-- *  End of ibDot11StaUserSecAuthStatis element Definition
-- *****************************************************************************

-- *****************************************************************************
-- *  ibDot11ACStaSecAuthTypeStatis element Definition
-- *****************************************************************************
ibDot11ACStaUserPortalOnlineNum OBJECT-TYPE
    SYNTAX      Integer32
    MAX-ACCESS  read-only
    STATUS      current
    DESCRIPTION
        "Represents the number of online portal users authenticated by RADIUS,
        including MAC-trigger and IMSIAuth users."
    ::= { ibDot11ACStaSecAuthTypeStatis 1 }

ibDot11ACStaUserFreeAuthOnlineNum OBJECT-TYPE
    SYNTAX      Integer32
    MAX-ACCESS  read-only
    STATUS      current
    DESCRIPTION
        "Numbers of online user is no need authenticated."
    ::= { ibDot11ACStaSecAuthTypeStatis 2 }

ibDot11ACStaUserAssociateAuthOnlineNum OBJECT-TYPE
    SYNTAX      Integer32
    MAX-ACCESS  read-only
    STATUS      current
    DESCRIPTION
        "Represents the number of online users authenticated by associated authentication,
        excluding AutoAuth users."
    ::= { ibDot11ACStaSecAuthTypeStatis 3 }

ibDot11ACStaUserMacAuthOnlineNum OBJECT-TYPE
    SYNTAX      Integer32
    MAX-ACCESS  read-only
    STATUS      current
    DESCRIPTION
        "The numbers of online user which is launched authentication by MAC address and
        authenticated by Radius."
    ::= { ibDot11ACStaSecAuthTypeStatis 4 }

ibDot11ACStaUserPortalLostConnectionCnt OBJECT-TYPE
    SYNTAX      Counter32
    MAX-ACCESS  read-only
    STATUS      current
    DESCRIPTION
        "For PortalAuth user, represents disconnection count but voluntarily disconnect,
        it should not delete authenticated user when client roamed."
    ::= { ibDot11ACStaSecAuthTypeStatis 5 }

ibDot11ACStaUserFreeAuthLostConnectionCnt OBJECT-TYPE
    SYNTAX      Counter32
    MAX-ACCESS  read-only
    STATUS      current
    DESCRIPTION
        "For FreeAuth user, represents disconnection count but voluntarily disconnect,
        it should not delete authenticated user when client roamed."
    ::= { ibDot11ACStaSecAuthTypeStatis 6 }

ibDot11ACStaUserAssociateAuthLostConnectionCnt OBJECT-TYPE
    SYNTAX      Counter32
    MAX-ACCESS  read-only
    STATUS      current
    DESCRIPTION
        "For AssociateAuth user, represents disconnection count but voluntarily disconnect,
        it should not delete authenticated user when client roamed."
    ::= { ibDot11ACStaSecAuthTypeStatis 7 }

ibDot11ACStaUserMacAuthLostConnectionCnt OBJECT-TYPE
    SYNTAX      Counter32
    MAX-ACCESS  read-only
    STATUS      current
    DESCRIPTION
        "For MacAuth user, represents disconnection count but voluntarily disconnect,
        it should not delete authenticated user when client roamed."
    ::= { ibDot11ACStaSecAuthTypeStatis 8 }

ibDot11ACStaPortalAuthReqCnt OBJECT-TYPE
    SYNTAX      Counter32
    MAX-ACCESS  read-only
    STATUS      current
    DESCRIPTION
        "Represents PortalAuth request count after AP up."
    ::= { ibDot11ACStaSecAuthTypeStatis 9 }

ibDot11ACStaAssociateAuthReqCnt OBJECT-TYPE
    SYNTAX      Counter32
    MAX-ACCESS  read-only
    STATUS      current
    DESCRIPTION
        "Represents AssociateAuth request count after AP up."
    ::= { ibDot11ACStaSecAuthTypeStatis 10 }

ibDot11ACStaMacAuthReqCnt OBJECT-TYPE
    SYNTAX      Counter32
    MAX-ACCESS  read-only
    STATUS      current
    DESCRIPTION
        "Represents MacAuth request count after AP up."
    ::= { ibDot11ACStaSecAuthTypeStatis 11 }

ibDot11ACStaPortalAuthSuccCnt OBJECT-TYPE
    SYNTAX      Counter32
    MAX-ACCESS  read-only
    STATUS      current
    DESCRIPTION
        "Represents count of PortalAuth authenticated successfully after AP up."
    ::= { ibDot11ACStaSecAuthTypeStatis 12 }

ibDot11ACStaAssociateAuthSuccCnt OBJECT-TYPE
    SYNTAX      Counter32
    MAX-ACCESS  read-only
    STATUS      current
    DESCRIPTION
        "Represents count of AssociateAuth authenticated successfully after AP up."
    ::= { ibDot11ACStaSecAuthTypeStatis 13 }

ibDot11ACStaMacAuthSuccCnt OBJECT-TYPE
    SYNTAX      Counter32
    MAX-ACCESS  read-only
    STATUS      current
    DESCRIPTION
        "Represents count of MacAuth authenticated successfully after AP up."
    ::= { ibDot11ACStaSecAuthTypeStatis 14 }

ibDot11ACStaPortalAuthReqFailCnt OBJECT-TYPE
    SYNTAX      Counter32
    MAX-ACCESS  read-only
    STATUS      current
    DESCRIPTION
        "Represents count of PortalAuth failure in request after AP up."
    ::= { ibDot11ACStaSecAuthTypeStatis 15 }

ibDot11ACStaAssociateAuthReqFailCnt OBJECT-TYPE
    SYNTAX      Counter32
    MAX-ACCESS  read-only
    STATUS      current
    DESCRIPTION
        "Represents count of AssociateAuth failure in request after AP up."
    ::= { ibDot11ACStaSecAuthTypeStatis 16 }

ibDot11ACStaMacAuthReqFailCnt OBJECT-TYPE
    SYNTAX      Counter32
    MAX-ACCESS  read-only
    STATUS      current
    DESCRIPTION
        "Represents count of MacAuth failure in request after AP up."
    ::= { ibDot11ACStaSecAuthTypeStatis 17 }

ibDot11ACStaUserAutoAuthOnlineNumCM OBJECT-TYPE
    SYNTAX      Integer32
    MAX-ACCESS  read-only
    STATUS      current
    DESCRIPTION
        "Represents the number of online users authenticated by auto authentication."
    ::= { ibDot11ACStaSecAuthTypeStatis 18 }

ibDot11ACStaUserAutoAuthLostConnectionCntCM OBJECT-TYPE
    SYNTAX      Counter32
    MAX-ACCESS  read-only
    STATUS      current
    DESCRIPTION
        "Represents the disconnection count of AutoAuth users, excluding the ones
        who disconnect AP by themselves."
    ::= { ibDot11ACStaSecAuthTypeStatis 19 }

ibDot11ACStaAutoAuthReqCntCM OBJECT-TYPE
    SYNTAX      Counter32
    MAX-ACCESS  read-only
    STATUS      current
    DESCRIPTION
        "Represents the count of AutoAuth requests after AP up."
    ::= { ibDot11ACStaSecAuthTypeStatis 20 }

ibDot11ACStaAutoAuthSuccCntCM OBJECT-TYPE
    SYNTAX      Counter32
    MAX-ACCESS  read-only
    STATUS      current
    DESCRIPTION
        "Represents the count of successful AutoAuth authentications after AP up."
    ::= { ibDot11ACStaSecAuthTypeStatis 21 }

ibDot11ACStaAutoAuthReqFailCntCM OBJECT-TYPE
    SYNTAX      Counter32
    MAX-ACCESS  read-only
    STATUS      current
    DESCRIPTION
        "Represents the count of failed AutoAuth requests after AP is up."
    ::= { ibDot11ACStaSecAuthTypeStatis 22 }
-- *****************************************************************************
-- *  End of ibDot11ACStaSecAuthTypeStatis element Definition
-- *****************************************************************************

-- *****************************************************************************
-- *  ibDot11ACPortalStatisticCMTable Definition
-- *****************************************************************************
ibDot11ACPortalStatisticCMTable OBJECT-TYPE
    SYNTAX      SEQUENCE OF IbDot11ACPortalStatisticCMEntry
    MAX-ACCESS  not-accessible
    STATUS      current
    DESCRIPTION
        "The table describes portal statistics information."
    ::= { ibDot11ACObjectGroup 7 }

ibDot11ACPortalStatisticCMEntry OBJECT-TYPE
    SYNTAX      IbDot11ACPortalStatisticCMEntry
    MAX-ACCESS  not-accessible
    STATUS      current
    DESCRIPTION
        "Each entry contains the portal statistics information of an SSID."
    INDEX
        {
            ibDot11ACPortalStatisticSSIDCM
        }
    ::= { ibDot11ACPortalStatisticCMTable 1 }

IbDot11ACPortalStatisticCMEntry ::= SEQUENCE
    {
        ibDot11ACPortalStatisticSSIDCM             OCTET STRING,
        ibDot11ACPortalStatAuthReqCM                  Counter32,
        ibDot11ACPortalStatAuthRespCM                 Counter32
    }

ibDot11ACPortalStatisticSSIDCM OBJECT-TYPE
    SYNTAX      OCTET STRING (SIZE (1..32))
    MAX-ACCESS  not-accessible
    STATUS      current
    DESCRIPTION
        "Represents the service policy name."
    ::= { ibDot11ACPortalStatisticCMEntry 1 }

ibDot11ACPortalStatAuthReqCM OBJECT-TYPE
    SYNTAX      Counter32
    MAX-ACCESS  read-only
    STATUS      current
    DESCRIPTION
        "Represents the total number of portal authentication requests from
        portal server to AC."
    ::= { ibDot11ACPortalStatisticCMEntry 2 }

ibDot11ACPortalStatAuthRespCM OBJECT-TYPE
    SYNTAX      Counter32
    MAX-ACCESS  read-only
    STATUS      current
    DESCRIPTION
        "Represents the total number of portal authentication responses from
        AC to portal server."
    ::= { ibDot11ACPortalStatisticCMEntry 3 }

-- *****************************************************************************
-- *  End of ibDot11ACPortalStatisticCMTable Definition
-- *****************************************************************************

-- *****************************************************************************
-- *  ibDot11LocalACModelTable Definition
-- *****************************************************************************
ibDot11LocalACModelTable OBJECT-TYPE
    SYNTAX      SEQUENCE OF IbDot11LocalACModelEntry
    MAX-ACCESS  not-accessible
    STATUS      current
    DESCRIPTION
        "The table defines the capability information for a specific
        kind of local AC."
    ::= { ibDot11ACObjectGroup 8 }

ibDot11LocalACModelEntry OBJECT-TYPE
    SYNTAX      IbDot11LocalACModelEntry
    MAX-ACCESS  not-accessible
    STATUS      current
    DESCRIPTION
        "Each entry contains capability information for a specific kind
        of local AC."
    INDEX
        {
            ibDot11LocalACModelAlias
        }
    ::= { ibDot11LocalACModelTable 1 }

IbDot11LocalACModelEntry ::= SEQUENCE
    {
        ibDot11LocalACModelAlias         OCTET STRING,
        ibDot11LocalACModelName          OCTET STRING,
        ibDot11LocalACManufacturer       OCTET STRING,
        ibDot11LocalACCPUType            OCTET STRING,
        ibDot11LocalACCPUClockSpeed      Unsigned32,
        ibDot11LocalACMemoryType         OCTET STRING,
        ibDot11LocalACMemorySize         Unsigned32,
        ibDot11LocalACFlashType          OCTET STRING,
        ibDot11LocalACFlashSize          Unsigned32,
        ibDot11LocalACMemSize            Counter64,
        ibDot11LocalACFlashSizeInBytes   Counter64
    }

ibDot11LocalACModelAlias OBJECT-TYPE
    SYNTAX      OCTET STRING(SIZE(0..127))
    MAX-ACCESS  not-accessible
    STATUS      current
    DESCRIPTION
        "Represents alias of local AC model name."
    ::= { ibDot11LocalACModelEntry 1 }

ibDot11LocalACModelName OBJECT-TYPE
    SYNTAX      OCTET STRING
    MAX-ACCESS  read-only
    STATUS      current
    DESCRIPTION
        "Represents local AC model name."
    ::= { ibDot11LocalACModelEntry 2 }

ibDot11LocalACManufacturer OBJECT-TYPE
    SYNTAX      OCTET STRING
    MAX-ACCESS  read-only
    STATUS      current
    DESCRIPTION
        "'SMI Network Management Private Enterprise Codes'
        assigned by the IANA, which means the vendor of local AC."
    ::= { ibDot11LocalACModelEntry 3 }

ibDot11LocalACCPUType OBJECT-TYPE
    SYNTAX      OCTET STRING
    MAX-ACCESS  read-only
    STATUS      current
    DESCRIPTION
        "Represents the CPU type of local AC."
    ::= { ibDot11LocalACModelEntry 4 }

ibDot11LocalACCPUClockSpeed OBJECT-TYPE
    SYNTAX      Unsigned32
    UNITS       "Hz"
    MAX-ACCESS  read-only
    STATUS      current
    DESCRIPTION
        "Represents the clock speed of CPU."
    ::= { ibDot11LocalACModelEntry 5 }

ibDot11LocalACMemoryType OBJECT-TYPE
    SYNTAX      OCTET STRING
    MAX-ACCESS  read-only
    STATUS      current
    DESCRIPTION
        "Represents the memory card type of local AC."
    ::= { ibDot11LocalACModelEntry 6 }

ibDot11LocalACMemorySize OBJECT-TYPE
    SYNTAX      Unsigned32
    UNITS       "kbytes"
    MAX-ACCESS  read-only
    STATUS      current
    DESCRIPTION
        "Represents the size of local AC memory card."
    ::= { ibDot11LocalACModelEntry 7 }

ibDot11LocalACFlashType OBJECT-TYPE
    SYNTAX      OCTET STRING
    MAX-ACCESS  read-only
    STATUS      current
    DESCRIPTION
        "Represents the flash card type of local AC."
    ::= { ibDot11LocalACModelEntry 8 }

ibDot11LocalACFlashSize OBJECT-TYPE
    SYNTAX      Unsigned32
    UNITS       "kbytes"
    MAX-ACCESS  read-only
    STATUS      current
    DESCRIPTION
        "Represents the size of local AC flash card."
    ::= { ibDot11LocalACModelEntry 9 }

ibDot11LocalACMemSize OBJECT-TYPE
    SYNTAX      Counter64
    UNITS       "bytes"
    MAX-ACCESS  read-only
    STATUS      current
    DESCRIPTION
        "Represents the size of local AC memory card."
    ::= { ibDot11LocalACModelEntry 10 }

ibDot11LocalACFlashSizeInBytes OBJECT-TYPE
    SYNTAX      Counter64
    UNITS       "bytes"
    MAX-ACCESS  read-only
    STATUS      current
    DESCRIPTION
        "This object represents the size of local AC flash card in bytes."
    ::= { ibDot11LocalACModelEntry 11 }

-- *****************************************************************************
-- *  End of ibDot11LocalACModelTable Definition
-- *****************************************************************************

-- *****************************************************************************
-- *  ibDot11CAPWAPTunnelTable Definition
-- *****************************************************************************
ibDot11CAPWAPTunnelTable OBJECT-TYPE
    SYNTAX      SEQUENCE OF IbDot11CAPWAPTunnelEntry
    MAX-ACCESS  not-accessible
    STATUS      current
    DESCRIPTION
        "The table will list all the APs which are connecting to the AC
        by the CAPWAP tunnel protocol."
    ::= { ibDot11CAPWAPTunnelGroup 1 }

ibDot11CAPWAPTunnelEntry OBJECT-TYPE
    SYNTAX      IbDot11CAPWAPTunnelEntry
    MAX-ACCESS  not-accessible
    STATUS      current
    DESCRIPTION
        "Each entry contains information of data tunnel and control
        tunnel of AP which is connecting to AC."
    INDEX
        {
            ibDot11CurrTunnelAPID
        }
    ::= { ibDot11CAPWAPTunnelTable 1 }

IbDot11CAPWAPTunnelEntry ::= SEQUENCE
    {
        ibDot11CurrTunnelAPID         IbDot11ObjectIDType,
        ibDot11CtrlTunnelCurrSec      IbDot11TunnelSecSchemType,
        ibDot11CtrlTunnelUpTime       Integer32,
        ibDot11DataTunnelCurrSec      IbDot11TunnelSecSchemType,
        ibDot11DataTunnelUpTime       Integer32,
        ibDot11CtrlTunnelUpTimeTicks  TimeTicks
    }

ibDot11CurrTunnelAPID OBJECT-TYPE
    SYNTAX      IbDot11ObjectIDType
    MAX-ACCESS  accessible-for-notify
    STATUS      current
    DESCRIPTION
        "To uniquely identify the CAPWAP tunnel set up between the AP
        identified by APID and a specific AC."
    ::= { ibDot11CAPWAPTunnelEntry 1 }

ibDot11CtrlTunnelCurrSec OBJECT-TYPE
    SYNTAX      IbDot11TunnelSecSchemType
    MAX-ACCESS  read-only
    STATUS      current
    DESCRIPTION
        "Represents what security scheme is in use for
        control tunnel."
    DEFVAL      { cleartxt }
    ::= { ibDot11CAPWAPTunnelEntry 2 }

ibDot11CtrlTunnelUpTime OBJECT-TYPE
    SYNTAX      Integer32
    UNITS       "second"
    MAX-ACCESS  read-only
    STATUS      current
    DESCRIPTION
        "Represents how long for control tunnel up. If the value is zero,
        then tunnel is not set up."
    ::= { ibDot11CAPWAPTunnelEntry 3 }

ibDot11DataTunnelCurrSec OBJECT-TYPE
    SYNTAX      IbDot11TunnelSecSchemType
    MAX-ACCESS  read-only
    STATUS      current
    DESCRIPTION
        "Represents what security scheme is in use for
        data tunnel."
    DEFVAL      { cleartxt }
    ::= { ibDot11CAPWAPTunnelEntry 4 }

ibDot11DataTunnelUpTime OBJECT-TYPE
    SYNTAX      Integer32
    UNITS       "second"
    MAX-ACCESS  read-only
    STATUS      current
    DESCRIPTION
        "Represents how long for data tunnel up.
        If the value is zero, then tunnel is not set up."
    ::= { ibDot11CAPWAPTunnelEntry 5 }

ibDot11CtrlTunnelUpTimeTicks OBJECT-TYPE
    SYNTAX      TimeTicks
    MAX-ACCESS  read-only
    STATUS      current
    DESCRIPTION
        "Represents how long control tunnel is up.
         If the value is zero, then tunnel is not set up."
    ::= { ibDot11CAPWAPTunnelEntry 6 }
-- *****************************************************************************
-- *    End of ibDot11CAPWAPTunnelTable  TABLE
-- *****************************************************************************

-- *****************************************************************************
-- *     Notifications OF ibDot11ACMtNotifyGroup
-- *****************************************************************************
-- AC Management Notification

        ibDot11ACMtTraps OBJECT IDENTIFIER
    ::= { ibDot11ACMtNotifyGroup 0 }

ibDot11ACMtTunnelSetupTrap NOTIFICATION-TYPE
    OBJECTS
        {
            ibDot11CurrTunnelAPID,
            ibDot11ACMtTrapTunlUpInfo,
            ibDot11ACMtTrapTnlAPName,
            ibDot11ACMtTrapTnlAPIPAddr,
            ibDot11ACMtTrapAPIPv6Addr,
            ibDot11ACMtFirstTrapTime,
            ibDot11ACMtTrapAPMacAddress
        }
    STATUS      current
    DESCRIPTION
        "This notification is sent by AC when CAPWAP tunnel becomes up.
        By this way, NMS will immediately know tunnel up event.
        It is unnecessary to identify whether it is control or data
        tunnel."
    ::= { ibDot11ACMtTraps 1 }

ibDot11ACMtTunnelDownTrap NOTIFICATION-TYPE
    OBJECTS
        {
            ibDot11CurrTunnelAPID,
            ibDot11ACMtTrapTunlDwnInfo,
            ibDot11ACMtTrapTnlAPName,
            ibDot11ACMtTrapTnlAPIPAddr,
            ibDot11ACMtTrapAPIPv6Addr,
            ibDot11ACMtTrapTunlDwnCount,
            ibDot11ACMtTrapTnlAPSysName,
            ibDot11ACMtFirstTrapTime,
            ibDot11ACMtTrapAPMacAddress
        }
    STATUS      current
    DESCRIPTION
        "This notification is sent by AC when CAPWAP tunnel becomes down.
        By this way, NMS will immediately know tunnel down event.
        It is unnecessary to identify whether it is control or data
        tunnel."
    ::= { ibDot11ACMtTraps 2 }

ibDot11ACMtBackupSwtTrap NOTIFICATION-TYPE
    OBJECTS
        {
            ibDot11ACMtTrapACMacAddress,
            ibDot11ACMtTrapBackupSwitchInfo,
            ibDot11ACMtFirstTrapTime
        }
    STATUS      current
    DESCRIPTION
        "This trap is sent by AC when AC switches from master to slave
        or from slave to master."
    ::= { ibDot11ACMtTraps 3 }

ibDot11ACLoadBalanceTrap NOTIFICATION-TYPE
    OBJECTS
        {
            ibDot11LoadBalanceType,
            ibDot11LoadBalanceThreshold
        }
    STATUS      current
    DESCRIPTION
        "This trap is sent by AC when load-balance is enabled on AC."
    ::= { ibDot11ACMtTraps 4 }

ibDot11ACStaFullTrap NOTIFICATION-TYPE
    OBJECTS
        {
            ibDot11ACMaxStaNum
        }
    STATUS current
    DESCRIPTION
        "This notification will be sent when STA is full on AC."
    ::={ ibDot11ACMtTraps 5 }

ibDot11ACStatusSwitchTrap NOTIFICATION-TYPE
    OBJECTS
        {
            ibDot11ACStatusSwitchInfo,
            ibDot11SourceACNmsIP
        }
    STATUS current
    DESCRIPTION
        "This notification will be sent when AC switches from standby to active
        or from standby to active."
    ::={ ibDot11ACMtTraps 6}

ibDot11RunAPNumOverload NOTIFICATION-TYPE
    OBJECTS
        {
            ibDot11MaxAPNumPermitted,
            ibDot11APConnectCount
        }
    STATUS current
    DESCRIPTION
        "The notification will be sent by AC when run AP number exceeds the threshold."
    ::= { ibDot11ACMtTraps 7}

ibDot11RunAPNumOverloadRecover NOTIFICATION-TYPE
    OBJECTS
        {
            ibDot11MaxAPNumPermitted,
            ibDot11APConnectCount
        }
    STATUS current
    DESCRIPTION
        "The notification will be sent by AC when run AP number
        recover normal from overload state."
    ::= { ibDot11ACMtTraps 8 }

ibDot11APInvalidCertificateTrap NOTIFICATION-TYPE
    OBJECTS
        {
            ibDot11ACMtTrapACMacAddress,
            ibDot11ACMtTrapAPMacAddress
        }
    STATUS current
    DESCRIPTION
        "The AC sends the notification once the certificate of an AP expires."
    ::= { ibDot11ACMtTraps 9 }

-- AC Management Notification Variable object

        ibDot11ACMtTrapVarObjects OBJECT IDENTIFIER
    ::= { ibDot11ACMtNotifyGroup 1 }

ibDot11ACMtTrapTunlDwnInfo OBJECT-TYPE
    SYNTAX      INTEGER
        {
            tunnelTimeout(1),
            keyUpdateFailure(2),
            apReset(3),
            apCrash(4),
            apDeleted(5),
            apCfgChange(6)
        }
    MAX-ACCESS  accessible-for-notify
    STATUS      current
    DESCRIPTION
        "Represents the reason for tunnel down.
        The following values are supported:
        tunnelTimeout     - When AC detects the tunnel is broken,
        - it will notify NMS.
        keyUpdateFailure  - rekey process is failed, tunnel will be broken.
        apReset           - Administrator reset AP.
        apCrash           - AP reboot for system crash.
        apDeleted         - Delete AP from AC and trigger tunnel down.
        apCfgChange       - The configuration for AP was changed."
    ::= { ibDot11ACMtTrapVarObjects 1 }

ibDot11ACMtTrapTunlUpInfo OBJECT-TYPE
    SYNTAX      INTEGER
        {
            up(1)
        }
    MAX-ACCESS  accessible-for-notify
    STATUS      current
    DESCRIPTION
        "Represents the reason for tunnel up.
        The following values are supported:
        up(1)  - The AP joined AC.
        "
    ::= { ibDot11ACMtTrapVarObjects 2 }

ibDot11ACMtTrapBackupSwitchInfo OBJECT-TYPE
    SYNTAX      INTEGER
        {
            masterToSlave(1),
            slaveToMaster(2)
        }
    MAX-ACCESS  accessible-for-notify
    STATUS      current
    DESCRIPTION
        "Represents status which the AC switches to.
        The following values are supported:
        masterToSlave  - The AC switches from master to slave.
        slaveToMaster  - The AC switches from slave to master.
        "
    ::= { ibDot11ACMtTrapVarObjects 3 }

ibDot11ACMtTrapTnlAPName OBJECT-TYPE
    SYNTAX      OCTET STRING
    MAX-ACCESS  accessible-for-notify
    STATUS      current
    DESCRIPTION
        "Represents name of the AP which sets up the tunnel with the AC.
        "
    ::= { ibDot11ACMtTrapVarObjects 4 }

ibDot11ACMtTrapTnlAPIPAddr OBJECT-TYPE
    SYNTAX      IpAddress
    MAX-ACCESS  accessible-for-notify
    STATUS      current
    DESCRIPTION
        "Represents IP address of the AP which sets up the tunnel with the AC.
        "
    ::= { ibDot11ACMtTrapVarObjects 5 }

ibDot11LoadBalanceType OBJECT-TYPE
    SYNTAX      INTEGER
        {
            traffic(1),
            session(2)
        }
    MAX-ACCESS  accessible-for-notify
    STATUS      current
    DESCRIPTION
        "Represents which kind load balance is enabled by AC.
         The following values are supported:
         traffic mode load-balancing: traffic snapshot is considered.
         session mode load-balancing: the number of users associated
                                      with the AP/radio is considered.
        "
    ::= { ibDot11ACMtTrapVarObjects 6 }

ibDot11LoadBalanceThreshold OBJECT-TYPE
    SYNTAX      Integer32
    MAX-ACCESS  accessible-for-notify
    STATUS      current
    DESCRIPTION
        "Represents the value of load balance threshold.
        "
    ::= { ibDot11ACMtTrapVarObjects 7 }

ibDot11ACMtTrapAPIPv6Addr OBJECT-TYPE
    SYNTAX      OCTET STRING
    MAX-ACCESS  accessible-for-notify
    STATUS      current
    DESCRIPTION
        "Represents IPv6 address of the AP which sets up the tunnel with
        the AC."
    ::= { ibDot11ACMtTrapVarObjects 8 }

ibDot11ACMtTrapTunlDwnCount OBJECT-TYPE
    SYNTAX      Integer32
    MAX-ACCESS  accessible-for-notify
    STATUS      current
    DESCRIPTION
        "Represents how many times that the tunnel between AC and AP has down."
    ::= { ibDot11ACMtTrapVarObjects 9 }

ibDot11ACMaxStaNum OBJECT-TYPE
    SYNTAX      Integer32
    MAX-ACCESS  accessible-for-notify
    STATUS      current
    DESCRIPTION
        "Represents the max number of STA on AC."
    ::= { ibDot11ACMtTrapVarObjects 10 }

ibDot11ACMtTrapTnlAPSysName OBJECT-TYPE
    SYNTAX      OCTET STRING
    MAX-ACCESS  accessible-for-notify
    STATUS      current
    DESCRIPTION
        "Represents system name of the AP which sets up the tunnel with the AC."
    ::= { ibDot11ACMtTrapVarObjects 11 }

ibDot11ACMtFirstTrapTime OBJECT-TYPE
    SYNTAX      TimeTicks
    MAX-ACCESS  accessible-for-notify
    STATUS      current
    DESCRIPTION
        "Represents the first trap time."
    ::= { ibDot11ACMtTrapVarObjects 12 }

ibDot11ACStatusSwitchInfo OBJECT-TYPE
    SYNTAX      INTEGER
        {
            activeToStandby(1),
            standbyToActive(2)
        }
    MAX-ACCESS  accessible-for-notify
    STATUS      current
    DESCRIPTION
        "Represents status which the AC switches to.
        The following values are supported:
        activeToStandby  - The AC switches from active to standby.
        standbyToActive  - The AC switches from standby to active.
        "
    ::= { ibDot11ACMtTrapVarObjects 13 }

ibDot11SourceACNmsIP OBJECT-TYPE
    SYNTAX      IpAddress
    MAX-ACCESS  accessible-for-notify
    STATUS      current
    DESCRIPTION
        "Represents the NMS IP address of master AC.
        "
    ::= { ibDot11ACMtTrapVarObjects 14 }

ibDot11ACMtTrapAPMacAddress OBJECT-TYPE
    SYNTAX      MacAddress
    MAX-ACCESS  accessible-for-notify
    STATUS      current
    DESCRIPTION
         "Represents the MAC address of an AP."
    ::= { ibDot11ACMtTrapVarObjects 15 }

ibDot11ACMtTrapACMacAddress OBJECT-TYPE
    SYNTAX      MacAddress
    MAX-ACCESS  accessible-for-notify
    STATUS      current
    DESCRIPTION
         "Represents the MAC address of the AC."
    ::= { ibDot11ACMtTrapVarObjects 16 }

-- *****************************************************************************
-- *     End OF NotifyGroup
-- *****************************************************************************
END
