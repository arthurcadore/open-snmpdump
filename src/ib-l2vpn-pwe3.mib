-- ==================================================================
-- Copyright (C) 2023 Intelbras S.A. All rights reserved.
--
-- Description: L2VPN PWE3(Pseudo Wire Emulation Edge-to-Edge) MIB
-- Reference:
-- Version: V1.0
-- History:
-- V1.0 2007-03-31 Created by Lixufu ID: 05023
-- ==================================================================
IB-L2VPN-PWE3-MIB DEFINITIONS ::= BEGIN

IMPORTS
        ibCommon
    FROM IB-OID-MIB
        IpAddress, Integer32, Unsigned32, OBJECT-TYPE, MODULE-IDENTITY, 
        NOTIFICATION-TYPE
    FROM SNMPv2-SMI
        TruthValue, RowStatus, TEXTUAL-CONVENTION
    FROM SNMPv2-TC;

ibL2VpnPwe3 MODULE-IDENTITY
    LAST-UPDATED "200703310000Z"       -- March 31, 2007 at 00:00 GMT
    ORGANIZATION
        "Intelbras S.A. Industria de Telecomunicacao Eletronica Brasileria."
    CONTACT-INFO
        ""
    DESCRIPTION
        "This MIB contains objects to manage PWE3."
    ::= { ibCommon 78 }

IbL2VpnVcEncapsType ::=  TEXTUAL-CONVENTION
    STATUS      current
    DESCRIPTION
        "An indication of the L2Vpn's VC encapsulation type:
        Frame Relay DLCI ( Martini Mode ) (1)
        ATM AAL5 SDU VCC transport (2)
        ATM transparent cell transport (3)
        Ethernet Tagged Mode (4)
        Ethernet (5)
        HDLC (6)
        PPP (7)
        SONET/SDH Circuit Emulation Service Over MPLS (CEM) (8)
        ATM n-to-one VCC cell transport (9)
        ATM n-to-one VPC cell transport (10)
        IP Layer2 Transport (11)
        ATM one-to-one VCC Cell Mode (12)
        ATM one-to-one VPC Cell Mode (13)
        ATM AAL5 PDU VCC transport (14)
        Frame-Relay Port mode (15)
        SONET/SDH Circuit Emulation over Packet (CEP) (16)
        Structure-agnostic E1 over Packet (SAE1oP)  (17)
        Structure-agnostic T1 (DS1) over Packet (SAT1oP)  (18)
        Structure-agnostic E3 over Packet (SAE3oP) (19)
        Structure-agnostic T3 (DS3) over Packet (SAT3oP) (20)
        CESoPSN basic mode (21)
        TDMoIP basic mode (22)
        CESoPSN TDM with CAS (23)
        TDMoIP TDM with CAS (24)
        Frame Relay DLCI (25)
        IP-interworking (64)
        unknown (255)
        "
    SYNTAX      INTEGER
        {
            frameRelayDlciMartini(1),
            atmAal5SduVccTransport(2),
            atmTransparentCellTransport(3),
            ethernetTagged(4),
            ethernet(5),
            hdlc(6),
            ppp(7),
            cem(8),
            atmN2OneVccCellTransport(9),
            atmN2OneVpcCellTransport(10),
            ipLayer2Transport(11),
            atmOne2OneVccCellMode(12),
            atmOne2OneVpcCellMode(13),
            atmAal5PduVccTransport(14),
            frameRelayPortMode(15),
            cep(16),
            saE1oP(17),
            saT1oP(18),
            saE3oP(19),
            saT3oP(20),
            cESoPsnBasicMode(21),
            tDMoIPbasicMode(22),
            l2VpnCESoPSNTDMwithCAS(23),
            l2VpnTDMoIPTDMwithCAS(24),
            frameRelayDlci(25),
            ipInterworking(64),
            unknown(255)
        }

-- ==================================================================
--
-- ======================= definition begin =========================
--
-- ==================================================================
ibL2VpnPwe3ScalarGroup OBJECT IDENTIFIER ::= { ibL2VpnPwe3 1 }

ibPwVcTrapOpen OBJECT-TYPE
    SYNTAX      TruthValue
    MAX-ACCESS  read-write
    STATUS      current
    DESCRIPTION
        "Whether pwe3 trap is globally enabled.
        false: disable;
        true: enable."
    DEFVAL  { false }
    ::= { ibL2VpnPwe3ScalarGroup 1 }

ibL2VpnPwe3Table OBJECT IDENTIFIER ::= { ibL2VpnPwe3 2 }

ibPwVcTable OBJECT-TYPE
    SYNTAX      SEQUENCE OF IbPwVcEntry
    MAX-ACCESS  not-accessible
    STATUS      current
    DESCRIPTION
        "This table is the VC configuration table. Users
        can create or delete a VC by it."
    ::= { ibL2VpnPwe3Table 1 }

ibPwVcEntry OBJECT-TYPE
    SYNTAX      IbPwVcEntry
    MAX-ACCESS  not-accessible
    STATUS      current
    DESCRIPTION
        "Provides the information of a VC entry."
    INDEX
        {
            ibPwVcIndex
        }
    ::= { ibPwVcTable 1 }

IbPwVcEntry ::= SEQUENCE
    {
        ibPwVcIndex            Integer32,
        ibPwVcID               Unsigned32,
        ibPwVcType             IbL2VpnVcEncapsType,
        ibPwVcPeerAddr         IpAddress,
        ibPwVcMtu              Unsigned32,
        ibPwVcCfgType           INTEGER,
        ibPwVcInboundLabel     Unsigned32,
        ibPwVcOutboundLabel    Unsigned32,
        ibPwVcIfIndex          Unsigned32,
        ibPwVcAcStatus         INTEGER,
        ibPwVcStatus           INTEGER,
        ibPwVcRowStatus        RowStatus
    }

ibPwVcIndex OBJECT-TYPE
    SYNTAX      Integer32
    MAX-ACCESS  not-accessible
    STATUS      current
    DESCRIPTION
        "Index for the conceptual row identifying a PW within
        this PW Emulation table."
    ::= { ibPwVcEntry 1 }

ibPwVcID OBJECT-TYPE
    SYNTAX      Unsigned32
    MAX-ACCESS  read-create
    STATUS      current
    DESCRIPTION
        "Used in the outgoing PW ID field within the 'Virtual
        Circuit FEC Element'."
    ::= { ibPwVcEntry 2 }

ibPwVcType OBJECT-TYPE
    SYNTAX      IbL2VpnVcEncapsType
    MAX-ACCESS  read-create
    STATUS      current
    DESCRIPTION
        "Indication of the L2Vpn's VC encapsulation type."
    ::= { ibPwVcEntry 3 }

ibPwVcPeerAddr OBJECT-TYPE
    SYNTAX      IpAddress
    MAX-ACCESS  read-create
    STATUS      current
    DESCRIPTION
        "This object contain the value of the peer ip address
        of the Martini VLL PW."
    ::= { ibPwVcEntry 4 }

ibPwVcMtu OBJECT-TYPE
    SYNTAX      Unsigned32
    MAX-ACCESS  read-create
    STATUS      current
    DESCRIPTION
        "If not equal zero, the optional Mtu object in the
        signaling protocol will be sent with this value,
        representing the locally supported MTU size over the
        interface (or the virtual interface) associated with the
        PW.
        The default value is 1500."
    ::= { ibPwVcEntry 5 }

ibPwVcCfgType OBJECT-TYPE
    SYNTAX      INTEGER
        {
            primary(1),
            backup(2),
            multiPort(3)
        }
    MAX-ACCESS  read-create
    STATUS      current
    DESCRIPTION
        "Indicates the type of the pw:
        1: primary;
        2: backup;
        3: multiPort."
    ::= { ibPwVcEntry 6 }

ibPwVcInboundLabel OBJECT-TYPE
    SYNTAX      Unsigned32
    MAX-ACCESS  read-only
    STATUS      current
    DESCRIPTION
        "For Martini VLL, the value will be created by system
        automatically."
    ::= { ibPwVcEntry 7 }

ibPwVcOutboundLabel OBJECT-TYPE
    SYNTAX      Unsigned32
    MAX-ACCESS  read-only
    STATUS      current
    DESCRIPTION
        "For Martini VLL, the value will be created by the peer
        automatically."
    ::= { ibPwVcEntry 8 }

ibPwVcIfIndex OBJECT-TYPE
    SYNTAX      Unsigned32
    MAX-ACCESS  read-create
    STATUS      current
    DESCRIPTION
        "Index of the interface (or the virtual interface)
        associated with the PW."
    ::= { ibPwVcEntry 9 }

ibPwVcAcStatus OBJECT-TYPE
    SYNTAX      INTEGER
        {
            down(1),
            up(2)
        }
    MAX-ACCESS  read-only
    STATUS      current
    DESCRIPTION
        "Local AC(Attachment Circuit) status:
        1: down;
        2: up."
    ::= { ibPwVcEntry 10 }

ibPwVcStatus OBJECT-TYPE
    SYNTAX      INTEGER
        {
            down(1),
            up(2)
        }
    MAX-ACCESS  read-only
    STATUS      current
    DESCRIPTION
        "Indicates the status of the PW in the local node.
        1: down;
        2: up."
    ::= { ibPwVcEntry 11 }

ibPwVcRowStatus OBJECT-TYPE
    SYNTAX      RowStatus
    MAX-ACCESS  read-create
    STATUS      current
    DESCRIPTION
        "This object is responsible for managing the creation,
        deletion and modification of rows, which support active
        status and CreatAndGo, destroy operation.
        To create a new row, ibPwVcID, ibPwVcType, ibPwVcPeerAddr
        ibPwVcMtu, ibPwVcCfgType and ibPwVcIfIndex
        must be specified."
    ::= { ibPwVcEntry 12 }

ibL2VpnPwe3Notifications OBJECT IDENTIFIER ::= { ibL2VpnPwe3 3 }

ibPwVcSwitchWtoP NOTIFICATION-TYPE
    OBJECTS
        {
            ibPwVcID,
            ibPwVcType,
            ibPwVcPeerAddr,
            ibPwVcID,
            ibPwVcType,
            ibPwVcPeerAddr
        }
    STATUS      current
    DESCRIPTION
        "This notification is generated when switch from working
        pw to protect pw happens. The first group of
        ibPwVcID/ibPwVcType/ibPwVcPeerAddr is parameter of the work PW , and
        the second group of ibPwVcID/ibPwVcType/ibPwVcPeerAddr is parameter
        of the protect PW."
    ::= { ibL2VpnPwe3Notifications 1 }

ibPwVcSwitchPtoW NOTIFICATION-TYPE
    OBJECTS
        {
            ibPwVcID,
            ibPwVcType,
            ibPwVcPeerAddr,
            ibPwVcID,
            ibPwVcType,
            ibPwVcPeerAddr
        }
    STATUS      current
    DESCRIPTION
        "This notification is generated when switch from protect
        pw to working pw happens. The first group of
        ibPwVcID/ibPwVcTypeibPwVcPeerAddr is parameter of the protect PW , and
        the second group of ibPwVcID/ibPwVcType/ibPwVcPeerAddr is parameter
        of the work PW."
    ::= { ibL2VpnPwe3Notifications 2 }

ibPwVcDown NOTIFICATION-TYPE
    OBJECTS
        {
            ibPwVcID,
            ibPwVcType,
            ibPwVcPeerAddr
        }
    STATUS      current
    DESCRIPTION
        "This notification indicates the VC's state changes to down."
    ::= { ibL2VpnPwe3Notifications 3 }

ibPwVcUp NOTIFICATION-TYPE
    OBJECTS
        {
            ibPwVcID,
            ibPwVcType,
            ibPwVcPeerAddr
        }
    STATUS      current
    DESCRIPTION
        "This notification indicates the VC's state changes to up."
    ::= { ibL2VpnPwe3Notifications 4 }

ibPwVcDeleted NOTIFICATION-TYPE
    OBJECTS
        {
            ibPwVcID,
            ibPwVcType,
            ibPwVcPeerAddr
        }
    STATUS      current
    DESCRIPTION
        "This notification indicates the VC is deleted."
    ::= { ibL2VpnPwe3Notifications 5 }

END
