-- ==========================================================
-- Copyright (C) 2023 Intelbras S.A. All rights reserved.
--
-- Description: This file describes the mib implementation of ISDN
-- Reference:
-- Version: V1.4
-- History:
--  V1.0 Initial version
--  V1.1 2004-10-27 updated by gaolong
--       Modify IMPORTS clause.
--       Remove object oid comments from MIB
--       Correct DEFVAL value of ibChanbIsdnPermit
--  V1.2 2005-03-22 updated by songjie
--       Add table: ibQ931IsdnTable.
--       Add traps: ibQ931IsdnCallSetup, ibQ931IsdnCallClear.
--  V1.3 2009-05-22 updated by chengtiesheng
--       Add table: ibLapdIsdnTable.
--  V1.4 2009-10-15 updated by chengtiesheng
--       Modify leaf node: ibLapdIsdnProtocol, add value ni(9).
--       Change MAX-ACCESS of ibLapdIsdnIf.
--       Add leaf node: ibLapdStatusTrapEnable.
--       Add trap:  ibLapdIsdnStatusChange.
-- ==============================================================
IB-ISDN-MIB DEFINITIONS ::= BEGIN

        IMPORTS
            ibmlsr
                FROM IB-OID-MIB
            Integer32, Counter32, OBJECT-TYPE, MODULE-IDENTITY,
            NOTIFICATION-TYPE
                FROM SNMPv2-SMI
            DisplayString, TimeStamp, DateAndTime, RowStatus
                FROM SNMPv2-TC;

--
-- Node definitions
--

        ibIsdnMib MODULE-IDENTITY
            LAST-UPDATED "200112200000Z"
            ORGANIZATION
                "Intelbras S.A. Industria de Telecomunicacao Eletronica Brasileria."
            CONTACT-INFO
                ""
            DESCRIPTION
                "This file describes the MIB implementation of ISDN"
            ::= { ibmlsr 9 }

--  Isdn Mib objects definitions
        ibIsdnMibObjects OBJECT IDENTIFIER ::= { ibIsdnMib 1 }

        ibisdnChannelB OBJECT IDENTIFIER ::= { ibIsdnMibObjects 1 }

        ibChanbIsdnTable OBJECT-TYPE
            SYNTAX SEQUENCE OF IBChanbIsdnEntry
            MAX-ACCESS not-accessible
            STATUS current
            DESCRIPTION
                "This table is used to describe the router's B Channels
                 infomation"
            ::= { ibisdnChannelB 1 }

        ibChanbIsdnEntry OBJECT-TYPE
            SYNTAX IBChanbIsdnEntry
            MAX-ACCESS not-accessible
            STATUS current
            DESCRIPTION
                " A single B channels"
            INDEX { ibChanbIsdnIf }
            ::= { ibChanbIsdnTable 1 }

        IBChanbIsdnEntry ::=
            SEQUENCE {
                ibChanbIsdnIf
                    INTEGER,
                ibChanbIsdnPermit
                    INTEGER,
                ibChanbIsdnAddr
                    DisplayString,
                ibChanbIsdnCallerAddr
                    DisplayString,
                ibChanbIsdnCallType
                    INTEGER,
                ibChanbIsdnInfoType
                    INTEGER,
                ibChanbIsdnState
                    INTEGER,
                ibChanbIsdnCallFreeReason
                    DisplayString,
                ibChanbIsdnCallFreeCode
                    INTEGER,
                ibChanbIsdnCallAccept
                    Counter32,
                ibChanbIsdnCallReject
                    Counter32,
                ibChanbIsdnCallSuccess
                    Counter32,
                ibChanbIsdnCallFailure
                    Counter32,
                ibChanbIsdnMaxKeepTime
                    Integer32,
                ibChanbIsdnLastKeepTime
                    Integer32,
                ibChanbIsdnLastCallTime
                    TimeStamp
             }

        ibChanbIsdnIf OBJECT-TYPE
            SYNTAX INTEGER
            MAX-ACCESS read-only
            STATUS current
            DESCRIPTION
                " this object is used to describe the virtual
                interface value associated with one neighbor.   "
            ::= { ibChanbIsdnEntry 1 }

        ibChanbIsdnPermit OBJECT-TYPE
            SYNTAX INTEGER
                {
                callOut(1),
                callIn(2),
                callBidirection(3)
                }
            MAX-ACCESS read-only
            STATUS current
            DESCRIPTION
                " this object is used to describe the call permissions."
            DEFVAL { callBidirection }
            ::= { ibChanbIsdnEntry 2 }

        ibChanbIsdnAddr OBJECT-TYPE
            SYNTAX DisplayString
            MAX-ACCESS read-only
            STATUS current
            DESCRIPTION
                "this object is used to descirbe the call address
                by which we call one nieghbor."
            ::= { ibChanbIsdnEntry 3 }

        ibChanbIsdnCallerAddr OBJECT-TYPE
            SYNTAX DisplayString
            MAX-ACCESS read-only
            STATUS current
            DESCRIPTION
                "this object is used to describe the callser address
                which will be known by B channels."
            ::= { ibChanbIsdnEntry 4 }

        ibChanbIsdnCallType OBJECT-TYPE
            SYNTAX INTEGER
                {
                nocall(0),
                call(1),
                answer(2)
                }
            MAX-ACCESS read-only
            STATUS current
            DESCRIPTION
                "this object is used to describe that whether it is an
                incoming call or an outging call."
            ::= { ibChanbIsdnEntry 5 }

        ibChanbIsdnInfoType OBJECT-TYPE
            SYNTAX INTEGER
                {
                unknown(1),
                speech(2),
                unrestrDigit(3),
                unrestrDigit56(4),
                restrictDigit(5),
                audio31(6),
                audio7(7),
                video(8),
                swithchedPacket(9)
                }
            MAX-ACCESS read-only
            STATUS current
            DESCRIPTION
                "this object is used to describe the information type
                on the call"
            ::= { ibChanbIsdnEntry 6 }

        ibChanbIsdnState OBJECT-TYPE
            SYNTAX INTEGER
                {
                idle(1),
                connecting(2),
                active(3)
                }
            MAX-ACCESS read-only
            STATUS current
            DESCRIPTION
                "this object is used to manage the call by NMS"
            ::= { ibChanbIsdnEntry 7 }

        ibChanbIsdnCallFreeReason OBJECT-TYPE
            SYNTAX DisplayString
            MAX-ACCESS read-only
            STATUS current
            DESCRIPTION
                "this object is used to describe the reason why last
                call is cleard"
            ::= { ibChanbIsdnEntry 8 }

        ibChanbIsdnCallFreeCode OBJECT-TYPE
            SYNTAX INTEGER
            MAX-ACCESS read-only
            STATUS current
            DESCRIPTION
                "this object is used to describe the reason code for
                the last call down."
            ::= { ibChanbIsdnEntry 9 }

        ibChanbIsdnCallAccept OBJECT-TYPE
            SYNTAX Counter32
            MAX-ACCESS read-only
            STATUS current
            DESCRIPTION
                "this object is used to describe the accepted call
                number from the B channels"
            ::= { ibChanbIsdnEntry 10 }

        ibChanbIsdnCallReject OBJECT-TYPE
            SYNTAX Counter32
            MAX-ACCESS read-only
            STATUS current
            DESCRIPTION
                "this object is used to describe the refused call
                number from B channels ."
            ::= { ibChanbIsdnEntry 11 }

        ibChanbIsdnCallSuccess OBJECT-TYPE
            SYNTAX Counter32
            MAX-ACCESS read-only
            STATUS current
            DESCRIPTION
                "this object is used to describe the successful call
                number to B channels after
                system restart."
            ::= { ibChanbIsdnEntry 12 }

        ibChanbIsdnCallFailure OBJECT-TYPE
            SYNTAX Counter32
            MAX-ACCESS read-only
            STATUS current
            DESCRIPTION
                "this object is used to describe the failing call number
                 to B channels after system restart"
            ::= { ibChanbIsdnEntry 13 }

        ibChanbIsdnMaxKeepTime OBJECT-TYPE
            SYNTAX Integer32
            UNITS "milliseconds"
            MAX-ACCESS read-only
            STATUS current
            DESCRIPTION
                "This object is used to descirbe the maximum duration
                time in milliseconds."
            DEFVAL { 2147483647 }
            ::= { ibChanbIsdnEntry 14 }

        ibChanbIsdnLastKeepTime OBJECT-TYPE
            SYNTAX Integer32
            UNITS "milliseconds"
            MAX-ACCESS read-only
            STATUS current
            DESCRIPTION
                "this object is used to describe the last call duration
                 time in milliseconds"
            ::= { ibChanbIsdnEntry 15 }

        ibChanbIsdnLastCallTime OBJECT-TYPE
            SYNTAX TimeStamp
            MAX-ACCESS read-only
            STATUS current
            DESCRIPTION
                "this object is used to describe the sysUpTime after
                last call attempt was made."
            ::= { ibChanbIsdnEntry 16 }

        ibChanbTrapEnable OBJECT-TYPE
            SYNTAX INTEGER { enabled(1), disabled(2) }
            MAX-ACCESS read-write
            STATUS current
            DESCRIPTION
                "This object is used to control  sending trap"
            ::= { ibisdnChannelB 2 }

        ibisdnQ931 OBJECT IDENTIFIER ::= { ibIsdnMibObjects 2 }

        ibQ931IsdnControl OBJECT IDENTIFIER ::= { ibisdnQ931 1 }

        ibQ931CallSetupTrapEnable OBJECT-TYPE
            SYNTAX INTEGER
            {
                enabled(1),
                disabled(2)
            }
            MAX-ACCESS read-write
            STATUS current
            DESCRIPTION
                "This object is used to control sending callsetup trap."
            ::= { ibQ931IsdnControl 1 }

        ibQ931CallClearTrapEnable OBJECT-TYPE
            SYNTAX INTEGER
            {
                enabled(1),
                disabled(2)
            }
            MAX-ACCESS read-write
            STATUS current
            DESCRIPTION
                "This object is used to control sending callclear trap"
            ::= { ibQ931IsdnControl 2 }

        ibQ931IsdnTable OBJECT-TYPE
            SYNTAX SEQUENCE OF IbQ931IsdnEntry
            MAX-ACCESS not-accessible
            STATUS current
            DESCRIPTION
                "This table describes B channel information for the
                use of Q931"
            ::= { ibisdnQ931 2 }

        ibQ931IsdnEntry OBJECT-TYPE
            SYNTAX IbQ931IsdnEntry
            MAX-ACCESS not-accessible
            STATUS current
            DESCRIPTION
                "A B channel entry in the Q931."
            INDEX {  ibQ931IsdnOpIndex }
            ::= { ibQ931IsdnTable 1 }

        IbQ931IsdnEntry ::=
            SEQUENCE
            {
                ibQ931IsdnOpIndex
                    Integer32,
                ibQ931IsdnLastCalled
                    DisplayString,
                ibQ931IsdnLastCalling
                    DisplayString,
                ibQ931IsdnLastCauseDisc
                    INTEGER,
                ibQ931IsdnCallDirection
                    INTEGER,
                ibQ931IsdnCallTimeOpen
                    DateAndTime,
                ibQ931IsdnCallTimeClose
                    DateAndTime
            }

        ibQ931IsdnOpIndex OBJECT-TYPE
            SYNTAX Integer32
            MAX-ACCESS accessible-for-notify
            STATUS current
            DESCRIPTION
                "Index of the B ISDN channel interface managed by Q93"
            ::= { ibQ931IsdnEntry 1 }

        ibQ931IsdnLastCalled OBJECT-TYPE
            SYNTAX DisplayString
            MAX-ACCESS read-only
            STATUS current
            DESCRIPTION
                "This object describes the called ISDN number.
                When an outgoing call is established successfully, the
                value of this node is the call number of this device,
                otherwise the value is null string"
            ::= { ibQ931IsdnEntry 2 }

        ibQ931IsdnLastCalling OBJECT-TYPE
            SYNTAX DisplayString
            MAX-ACCESS read-only
            STATUS current
            DESCRIPTION
                "This object describes the calling ISDN number.
                When an incoming call is established successfully, the
                value of this node is the call number of peer device,
                otherwise the value is null string."
            ::= { ibQ931IsdnEntry 3 }

        ibQ931IsdnLastCauseDisc OBJECT-TYPE
            SYNTAX INTEGER
            {
                unknown(1),
                normCallClr(2),
                noRouteToTransNet(3),
                noRouteToDest(4),
                switchEquCongest(5),
                netOutofOrder(6)
            }
            MAX-ACCESS read-only
            STATUS current
            DESCRIPTION
                "This object describes last cause of disconnection.
                In ibQ931IsdnCallClear trap, the value of this node is
                the reason of disconnection, this node is only valid
                for ibQ931IsdnCallClear trap, the value of this node
                is unknown in other situation.
                unknown:            unknown error.
                normCallClr:        normal call clearing.
                noRouteToTransNet:  no route to specified transit network.
                noRouteToDest:      no route to destination.
                switchEquCongest:   switching equipment congestion.
                netOutofOrder:      network out of order."
            ::= { ibQ931IsdnEntry 4 }

        ibQ931IsdnCallDirection OBJECT-TYPE
            SYNTAX INTEGER
            {
                incoming(1),
                outgoing(2)
            }
            MAX-ACCESS read-only
            STATUS current
            DESCRIPTION
                "This object describes the direction of the current call."
            ::= { ibQ931IsdnEntry 5 }

        ibQ931IsdnCallTimeOpen OBJECT-TYPE
            SYNTAX DateAndTime
            MAX-ACCESS read-only
            STATUS current
            DESCRIPTION
                "This object describes the start time of this call.
                start time is the time of an existent call that
                has just been established."
            ::= { ibQ931IsdnEntry 6 }

        ibQ931IsdnCallTimeClose OBJECT-TYPE
            SYNTAX DateAndTime
            MAX-ACCESS read-only
            STATUS current
            DESCRIPTION
                "This object describes the close time of this call.
                This node is only vaild for ibQ931IsdnCallClear trap.
                In other situation the value of this node is zero.
                In ibQ931IsdnCallClear trap, this node provides the
                time of an existent call that the call has just been
                cleared."
            ::= { ibQ931IsdnEntry 7 }

-- Define ibLapdIsdnTable

        ibIsdnLapd OBJECT IDENTIFIER ::= { ibIsdnMibObjects 3 }

        ibLapdIsdnTable OBJECT-TYPE
            SYNTAX SEQUENCE OF IbLapdIsdnEntry
            MAX-ACCESS not-accessible
            STATUS current
            DESCRIPTION
                "This table is used to describe the config of ISDN D channel."
            ::= { ibIsdnLapd 1 }

        ibLapdIsdnEntry OBJECT-TYPE
            SYNTAX IbLapdIsdnEntry
            MAX-ACCESS not-accessible
            STATUS current
            DESCRIPTION
                "ISDN D channel config"
            INDEX { ibLapdIsdnIf }
            ::= { ibLapdIsdnTable 1 }

        IbLapdIsdnEntry ::=
            SEQUENCE {
                ibLapdIsdnIf
                    Integer32,
                ibLapdIsdnProtocol
                    INTEGER,
                ibLapdIsdnIfMode
                    INTEGER,
                ibLapdIsdnLinkStatus
                    INTEGER
             }

        ibLapdIsdnIf OBJECT-TYPE
            SYNTAX Integer32
            MAX-ACCESS accessible-for-notify
            STATUS current
            DESCRIPTION
                "This object is used to describe the D channel
                interface value associated with one neighbor."
            ::= { ibLapdIsdnEntry 1 }

        ibLapdIsdnProtocol OBJECT-TYPE
            SYNTAX INTEGER
                {
                dss1(1),
                qsig(2),
                etsi(3),
                ess5(4),
                ansi(5),
                ni2(6),
                ntt(7),
                att(8),
                ni(9)
                }
            MAX-ACCESS read-write
            STATUS current
            DESCRIPTION
                "This object is used to describe the protocol D channel applied.
                For E1, the protocol may be dss1, qsig, etsi.
                For T1, the protocol may be ess5, ansi, att, dss1, etsi, ni2,
                ntt, qsig.
                For BRI, the protocol may be ansi, dss1, etsi, ni, ntt."
            DEFVAL { dss1 }
            ::= { ibLapdIsdnEntry 2 }

        ibLapdIsdnIfMode OBJECT-TYPE
            SYNTAX INTEGER
                {
                userSide(1),
                networkSide(2)
                }
            MAX-ACCESS read-write
            STATUS current
            DESCRIPTION
                "The physical interface mode.  For TE mode, the value
                of this object is userSide.  For NT mode, the value of this
                object is networkSide."
            ::= { ibLapdIsdnEntry 3 }

        ibLapdIsdnLinkStatus OBJECT-TYPE
            SYNTAX INTEGER
                {
                inactive(1),
                l1Active(2),
                l2Active(3)
                }
            MAX-ACCESS read-only
            STATUS current
            DESCRIPTION
                "The operational status of this interface:
                 inactive  all layers are inactive.
                 l1Active  layer 1 is activated,
                           layer 2 datalink not established.
                 l2Active  layer 1 is activated,
                           layer 2 datalink established.
               "
            ::= { ibLapdIsdnEntry 4 }

        ibLapdIsdnControl OBJECT IDENTIFIER ::= { ibIsdnLapd 2 }
        ibLapdStatusTrapEnable OBJECT-TYPE
            SYNTAX INTEGER
            {
                enabled(1),
                disabled(2)
            }
            MAX-ACCESS read-write
            STATUS current
            DESCRIPTION
                "This object is used to control sending ibLapdIsdnStatusChange
                trap."
            DEFVAL { enabled }
            ::= { ibLapdIsdnControl 1 }

--  Traps related to Connection management
        ibIsdnMibTraps OBJECT IDENTIFIER ::= { ibIsdnMib 2 }

        ibChanbIsdnCall NOTIFICATION-TYPE
        OBJECTS { ibChanbIsdnIf,
            ibChanbIsdnAddr,
            ibChanbIsdnCallType,
            ibChanbIsdnCallerAddr,
            ibChanbIsdnInfoType,
            ibChanbIsdnLastKeepTime,
            ibChanbIsdnCallFreeReason,
            ibChanbIsdnCallFreeCode
            }
        STATUS current
        DESCRIPTION
        "When one call is setup ,cleard or determined , the trap
        is sent to NMS"
        ::= { ibIsdnMibTraps 1 }

        ibQ931IsdnCallSetup NOTIFICATION-TYPE
            OBJECTS {
                ibQ931IsdnOpIndex,
                ibQ931IsdnLastCalled,
                ibQ931IsdnLastCalling,
                ibQ931IsdnCallDirection,
                ibQ931IsdnCallTimeOpen
            }
            STATUS      current
            DESCRIPTION
                "This trap/inform is sent to the manager whenever a call
                is established successfully."
            ::= { ibIsdnMibTraps 2 }

        ibQ931IsdnCallClear NOTIFICATION-TYPE
            OBJECTS {
                ibQ931IsdnOpIndex,
                ibQ931IsdnLastCalled,
                ibQ931IsdnLastCalling,
                ibQ931IsdnLastCauseDisc,
                ibQ931IsdnCallDirection,
                ibQ931IsdnCallTimeOpen,
                ibQ931IsdnCallTimeClose
            }
            STATUS current
            DESCRIPTION
                "This trap/inform is sent to the manager under the following
                conditions:
                - an existent call is normally cleared.
                - an existent call is determined to have ultimately
                  failed, and has been cleared.
                - the existent call is cleared when the BRI/PRI port is
                  down.
                - the existent call is cleared when the dialer rule is
                  down."
            ::= { ibIsdnMibTraps 3 }

        ibLapdIsdnStatusChange NOTIFICATION-TYPE
            OBJECTS {
                ibLapdIsdnIf,
                ibLapdIsdnLinkStatus
            }
            STATUS current
            DESCRIPTION
                "This trap/inform is sent to the manager whenever the
                 D-channel of an interface changes state."
            ::= { ibIsdnMibTraps 4 }

    END
