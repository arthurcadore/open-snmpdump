-- =============================================================================
-- Copyright (C) 2023 Intelbras S.A. All rights reserved.
--
-- Description:
--      This MIB module is for configuring and monitoring Fibre Channel
--      over Ethernet (FCoE) related entities.
-- Reference:
-- Version: V1.2
-- History:
--      V1.0 created by h06247
--      V1.1 Added ibFCoEFIPSnoopingTable by zhangchangjun 02876.
--           Modified the range of ibFCoECfgDATov by wangyuqiang 08530.
--      V1.2 Added ibFCoEVlanCfgTable by chengzhipeng 04378 2014-05-09
--           Modified the range of ibFCoECfgDATov by chengzhipeng 04378.
--           Added ibFCoEFIPSnoopingFCFTable, ibFCoEFIPSnoopingENodeTable,
--           ibFCoEFIPSnoopingVNTable and ibFCoEFIPSnoopingIfCfgTable by
--           h06247 2014-11-12
-- =============================================================================
IB-FCOE-MIB DEFINITIONS ::= BEGIN

IMPORTS
    ibCommon                   FROM IB-OID-MIB
    MODULE-IDENTITY, OBJECT-TYPE,
    Unsigned32                  FROM SNMPv2-SMI         -- [RFC2578]
    RowStatus, TimeStamp,
    TruthValue, MacAddress,
    TEXTUAL-CONVENTION          FROM SNMPv2-TC          -- [RFC2578]
    SnmpAdminString             FROM SNMP-FRAMEWORK-MIB -- [RFC3411]
    InterfaceIndex,
    InterfaceIndexOrZero        FROM IF-MIB             -- [RFC2863]
    VlanIndex                   FROM Q-BRIDGE-MIB       -- [RFC4363]
    T11FabricIndex              FROM T11-TC-MIB         -- [RFC4439]
    fcmInstanceIndex            FROM FC-MGMT-MIB        -- [RFC4044]
    IbFcNameId                FROM IB-FC-TC-MIB;

ibFCoE MODULE-IDENTITY
    LAST-UPDATED    "201411120000Z"
    ORGANIZATION
        "Intelbras S.A. Industria de Telecomunicacao Eletronica Brasileria."
    CONTACT-INFO
        ""
    DESCRIPTION
        "This MIB module is for configuring and monitoring Fibre Channel
        over Ethernet (FCoE) related entities.  This MIB defines a
        Virtual FC (VFC) Interface as an object that represents either
        a VF_Port or a VE_Port on an FCoE Forwarder (FCF).  VFC
        interfaces can be created either statically (by management
        request) or dynamically (at the time of FIP based FLOGI or ELP
        request).
        Other terminologies used in this MIB are defined by the
        Ib FCoE standard, as defined in the FC-BB-5 specification.
        This MIB also supports configuration of the following objects:
        - Mapping of FCoE VLAN-ID used to carry traffic for a Fabric
        - FC-MAP value used by the FCF operating in FPMA mode
        - FIP snooping related objects"
    REVISION        "201411120000Z"
    DESCRIPTION
        "Added ibFCoEFIPSnoopingFCFTable, ibFCoEFIPSnoopingENodeTable
        ibFCoEFIPSnoopingVNTable and ibFCoEFIPSnoopingIfCfgTable."
    REVISION        "201203280000Z"
    DESCRIPTION
        "Initial version of this MIB module."
    ::= { ibCommon 120 }

ibFCoEObjects  OBJECT  IDENTIFIER
    ::= { ibFCoE 1 }
ibFCoEConfig   OBJECT  IDENTIFIER
    ::= { ibFCoEObjects 1 }

IbFCoEVfcBindType ::= TEXTUAL-CONVENTION
    STATUS          current
    DESCRIPTION
        "Defines the different methods to identify (or bind to)
            - the ENode associated with a particular VF_Port VFC
            - the remote-FCF associated with a particular VE_Port VFC
            interfaceIndex(1) - This type is used only when an ENode
                or remote-FCF is directly connected to the local FCF
                via one of the local Ethernet interfaces, in which
                case the value contains the ifIndex of said Ethernet
                interface.
            macAddress(2) - This type is used when an ENode or
                remote-FCF is reachable from the local FCF over a
                (Layer-2) Ethernet network.  A FIP frame from an
                ENode or remote-FCF is associated to a VFC only if
                the frame's source MAC address is the same as the
                MAC Address bound on that VFC."
    SYNTAX INTEGER  {
                        interfaceIndex(1),
                        macAddress(2)
                    }
--
-- FCoE Globals per Switch in a Fibre Channel Management Instance
-- Fibre Channel Management instance is defined in [RFC4044] as a
-- separable managed instance of Fibre Channel functionality.
-- Fibre Channel functionality may be grouped into Fibre
-- Channel management instances in whatever way is most
-- convenient for the implementation(s).
--
-- RFC4044 also defines the fcmSwitchTable as a table of
-- information about Fibre Channel switches which are managed
-- by Fibre Channel management instances.  Each Fibre Channel
-- management instance can manage one or more Fibre Channel
-- switches.  The Switch Index, fcmSwitchIndex, is
-- IMPORTed from the FC-MGMT-MIB as the index value
-- to uniquely identify a Fibre Channel switch amongst
-- those (one or more) managed by the same Fibre
-- Channel management instance.
-- In this MIB, the same fcmSwitchIndex is used to
-- identify each FCF and to distinguish it from other
-- FCFs and from other Fibre Channel switches.
--
--

ibFCoECfgTable OBJECT-TYPE
    SYNTAX          SEQUENCE OF IbFCoECfgEntry
    MAX-ACCESS      not-accessible
    STATUS          current
    DESCRIPTION
        "This table facilitates configuration of FCoE parameters
        on a per Fibre Channel management instance."
    ::= { ibFCoEConfig 1 }

ibFCoECfgEntry OBJECT-TYPE
    SYNTAX          IbFCoECfgEntry
    MAX-ACCESS      not-accessible
    STATUS          current
    DESCRIPTION
        "There is one entry in this table for each
        Fibre Channel management instance."
    INDEX           {
                        fcmInstanceIndex
                    }
    ::= { ibFCoECfgTable 1 }

IbFCoECfgEntry ::= SEQUENCE {
    ibFCoECfgFcmap                    OCTET STRING,
    ibFCoECfgDynamicVfcCreation       TruthValue,
    ibFCoECfgDefaultFCFPriority       Unsigned32,
    ibFCoECfgDATov                    Unsigned32,
    ibFCoECfgAddressingMode           INTEGER
}

ibFCoECfgFcmap OBJECT-TYPE
    SYNTAX          OCTET STRING (SIZE (3))
    MAX-ACCESS      read-write
    STATUS          current
    DESCRIPTION
        "This object configures the FC-MAP value used by the FCF
        when operating in FPMA mode.  The default value is 0EFC00h,
        as written in the standard."
    REFERENCE
        "Fibre Channel - Backbone - 5 (FC-BB-5),
        section 7.6 and table 47"
    DEFVAL { '0EFC00'h }
    ::= { ibFCoECfgEntry 1 }

ibFCoECfgDynamicVfcCreation OBJECT-TYPE
    SYNTAX          TruthValue
    MAX-ACCESS      read-write
    STATUS          current
    DESCRIPTION
        "This object is set to 'true' to enable, or 'false' to
        disable, the dynamic creation of VFC interfaces on this FCF.
        When set to 'true', VFC interfaces are dynamically created
        as and when a FIP-based FLOGI or ELP request is received."
    DEFVAL { false }
    ::= { ibFCoECfgEntry 2 }

ibFCoECfgDefaultFCFPriority OBJECT-TYPE
    SYNTAX          Unsigned32 (0..255)
    MAX-ACCESS      read-write
    STATUS          current
    DESCRIPTION
        "The FIP priority value advertised by the FCF to ENodes by
        default.  ibFCoEStaticVfcFCFPriority configured for a VFC
        interface overrides this setting for the ENode associated
        with the VFC."
    DEFVAL { 128 }
    ::= { ibFCoECfgEntry 3 }

ibFCoECfgDATov OBJECT-TYPE
    SYNTAX          Unsigned32 (4..600)
    UNITS           "seconds"
    MAX-ACCESS      read-write
    STATUS          current
    DESCRIPTION
        "The Discovery_Advertisement_Timeout value configured for
        the FCF.  This is used as the timeout value in seconds by
        the FCF to send periodic Discovery Advertisements."
    DEFVAL { 8 }
    ::= { ibFCoECfgEntry 4 }

ibFCoECfgAddressingMode OBJECT-TYPE
    SYNTAX          INTEGER {
                        fpma(1),
                        spma(2),
                        fpmaAndSpma(3)
                    }
    MAX-ACCESS      read-write
    STATUS          current
    DESCRIPTION
        "Addressing mode(s) supported by the FCF.  Implementations
        should fail SetRequests for unsupported modes."
    ::= { ibFCoECfgEntry 5 }

ibFCoEVLANTable OBJECT-TYPE
    SYNTAX          SEQUENCE OF IbFCoEVLANEntry
    MAX-ACCESS      not-accessible
    STATUS          current
    DESCRIPTION
        "In fabrics in which VLANs are deployed, this table facilitates
        configuration of VLAN and Virtual Fabric associations in an
        FCoE network.  In such fabrics, FCoE forwarding for a fabric
        is over a VLAN in a (Layer-2) Ethernet network.  That is,
        reachability between the ENode/remote-FCF and an FCF for a
        given fabric is determined by the reachability provided by the
        Ethernet network on the corresponding VLAN.
        An active entry in this table indicates which VLAN is used
        to transport FCoE traffic for a particular Virtual Fabric.
        If VLANs are not deployed or not enabled, entries in this table
        are ignored by the bridge.
        Some implementations may allow traffic from only one Virtual
        Fabric to be transported over a given VLAN.  Such
        implementations should prevent multiple entries with the same
        VLAN-ID from being created in this table.
        Modifying existing VLAN-Virtual Fabric associations is not
        possible.  The specific row must first be deleted and then
        a new one created."
    ::= { ibFCoEConfig 2 }

ibFCoEVLANEntry OBJECT-TYPE
    SYNTAX          IbFCoEVLANEntry
    MAX-ACCESS      not-accessible
    STATUS          current
    DESCRIPTION
        "There is one entry in this table for each VLAN that is
        designated to transport FCoE traffic for a given Virtual
        Fabric."
    INDEX           {
                        fcmInstanceIndex,
                        ibFCoEVLANIndex,
                        ibFCoEFabricIndex
                    }
    ::= { ibFCoEVLANTable 1 }

IbFCoEVLANEntry ::= SEQUENCE {
        ibFCoEVLANIndex               VlanIndex,
        ibFCoEFabricIndex             T11FabricIndex,
        ibFCoEVLANOperState           INTEGER,
        ibFCoEVLANRowStatus           RowStatus
}

ibFCoEVLANIndex OBJECT-TYPE
    SYNTAX          VlanIndex
    MAX-ACCESS      not-accessible
    STATUS          current
    DESCRIPTION
        "This object identifies the VLAN-ID that the FCoE FCF function
        is being enabled for."
    ::= { ibFCoEVLANEntry 1 }

ibFCoEFabricIndex OBJECT-TYPE
    SYNTAX          T11FabricIndex
    MAX-ACCESS      not-accessible
    STATUS          current
    DESCRIPTION
        "This object identifies the Fabric Index of the Virtual Fabric
        traffic which is to be transported over the VLAN identified
        by ibFCoEVLANIndex."
    ::= { ibFCoEVLANEntry 2 }

ibFCoEVLANOperState OBJECT-TYPE
    SYNTAX          INTEGER {
                        up(1),
                        down(2)
                    }
    MAX-ACCESS      read-only
    STATUS          current
    DESCRIPTION
        "Operational state of this VLAN-Virtual Fabric association
        entry.  The 'up' state is achieved when both the Virtual
        Fabric and VLAN are valid."
    ::= { ibFCoEVLANEntry 3 }

ibFCoEVLANRowStatus OBJECT-TYPE
    SYNTAX          RowStatus
    MAX-ACCESS      read-create
    STATUS          current
    DESCRIPTION
        "The status of this conceptual row.  The RowStatus becomes active
        on successful creation of an entry."
    ::= { ibFCoEVLANEntry 4 }

ibFCoEStaticVfcTable OBJECT-TYPE
    SYNTAX          SEQUENCE OF IbFCoEStaticVfcEntry
    MAX-ACCESS      not-accessible
    STATUS          current
    DESCRIPTION
        "This table facilitates the creation and deletion of static
        VFC interfaces.  While VFCs can be dynamically created based on
        FIP FLOGI/ELP requests, operators may want to associate certain
        pre-configured policy for a particular ENode or a remote-FCF.
        In such cases static VFC creation becomes necessary.  In addition
        to being creating, a static VFC also needs to be associated to
        an ENode or remote-FCF.  The VFC binding provides such an
        association.  The binding does not need to be specified when
        the row for a VFC is created, but may be specified later."
    ::= { ibFCoEConfig 3 }

ibFCoEStaticVfcEntry OBJECT-TYPE
    SYNTAX          IbFCoEStaticVfcEntry
    MAX-ACCESS      not-accessible
    STATUS          current
    DESCRIPTION
        "There is one entry in this table for each statically created
        VFC Interface."
    INDEX           {
                        fcmInstanceIndex,
                        ibFCoEStaticVfcIndex
                    }
    ::= { ibFCoEStaticVfcTable 1 }

IbFCoEStaticVfcEntry ::= SEQUENCE {
        ibFCoEStaticVfcIndex              Unsigned32,
        ibFCoEStaticVfcFCFPriority        Unsigned32,
        ibFCoEStaticVfcBindType           IbFCoEVfcBindType,
        ibFCoEStaticVfcBindIfIndex        InterfaceIndexOrZero,
        ibFCoEStaticVfcBindMACAddress     MacAddress,
        ibFCoEStaticVfcIfIndex            InterfaceIndex,
        ibFCoEStaticVfcCreationTime       TimeStamp,
        ibFCoEStaticVfcFailureCause       SnmpAdminString,
        ibFCoEStaticVfcRowStatus          RowStatus
}

ibFCoEStaticVfcIndex OBJECT-TYPE
    SYNTAX          Unsigned32 (1..65535)
    MAX-ACCESS      not-accessible
    STATUS          current
    DESCRIPTION
        "This index uniquely identifies a static VFC entry in this
        table."
    ::= { ibFCoEStaticVfcEntry 1 }

ibFCoEStaticVfcFCFPriority OBJECT-TYPE
    SYNTAX          Unsigned32 (0..255)
    MAX-ACCESS      read-create
    STATUS          current
    DESCRIPTION
        "If this VFC is for a VF_Port this object is used to configure
        FCF priority to be advertised to the ENode associated with the
        VFC."
    DEFVAL { 128 }
    ::= { ibFCoEStaticVfcEntry 2 }

ibFCoEStaticVfcBindType OBJECT-TYPE
    SYNTAX          IbFCoEVfcBindType
    MAX-ACCESS      read-create
    STATUS          current
    DESCRIPTION
        "The mechanism to identify the ENode associated with this VFC
        if it is of type VF_Port or to identify the remote-FCF
        associated with this VFC if it is of type VE_Port."
    ::= { ibFCoEStaticVfcEntry 3 }

ibFCoEStaticVfcBindIfIndex OBJECT-TYPE
    SYNTAX          InterfaceIndexOrZero
    MAX-ACCESS      read-create
    STATUS          current
    DESCRIPTION
        "This object is applicable only when the local FCF is
        directly connected to an ENode or remote-FCF over a
        specific Ethernet interface, in which case this object
        contains the ifIndex of said Ethernet interface.
        If the ENode or remote-FCF is not directly connected
        to the FCF, this value of this object is zero."
    ::= { ibFCoEStaticVfcEntry 4 }

ibFCoEStaticVfcBindMACAddress OBJECT-TYPE
    SYNTAX          MacAddress
    MAX-ACCESS      read-create
    STATUS          current
    DESCRIPTION
        "This object is applicable when the ENode or remote-FCF to
        which the local FCF is connected is identified by a MAC
        address.  A FIP frame from an ENode or remote-FCF is
        associated with this VFC only if the source MAC address
        in the frame is the same as the value of this object."
    ::= { ibFCoEStaticVfcEntry 5 }

ibFCoEStaticVfcIfIndex OBJECT-TYPE
    SYNTAX          InterfaceIndex
    MAX-ACCESS      read-only
    STATUS          current
    DESCRIPTION
        "The ifIndex of this Virtual FC interface."
    ::= { ibFCoEStaticVfcEntry 6 }

ibFCoEStaticVfcCreationTime OBJECT-TYPE
    SYNTAX          TimeStamp
    MAX-ACCESS      read-only
    STATUS          current
    DESCRIPTION
        "The timestamp of this entry's creation time."
    ::= { ibFCoEStaticVfcEntry 7 }

ibFCoEStaticVfcFailureCause OBJECT-TYPE
    SYNTAX          SnmpAdminString
    MAX-ACCESS      read-only
    STATUS          current
    DESCRIPTION
        "The cause of failure for the last bind operation.  This
        object will be zero length if and only if the bind is
        successful."
    ::= { ibFCoEStaticVfcEntry 8 }

ibFCoEStaticVfcRowStatus OBJECT-TYPE
    SYNTAX          RowStatus
    MAX-ACCESS      read-create
    STATUS          current
    DESCRIPTION
        "The status of this conceptual row.  The RowStatus becomes
        active on successful creation of a VFC.  The VFC does not
        need to be bound for the row to be active, but the VFC must
        be bound before becoming operational."
    ::= { ibFCoEStaticVfcEntry 9 }

--
-- FIP Snooping related objects used to configure FIP Snooping
-- on a (FIP-aware) Ethernet Bridge
--

ibFCoEFIPSnoopingTable OBJECT-TYPE
    SYNTAX          SEQUENCE OF IbFCoEFIPSnoopingEntry
    MAX-ACCESS      not-accessible
    STATUS          current
    DESCRIPTION
        "FCoE provides increased flexibility, but with this flexibility
        new challenges arise in assuring highly robust Fabrics.  The FCF
        does not have the complete control that a Fibre Channel switch
        has.
        Ethernet bridges commonly provide a feature called Access Control
        Lists (ACLs).  Properly configured ACLs may emulate a point-to-point
        link by providing the traffic enforcement previously discussed.
        Furthermore, the FIP protocol has been designed to enable Ethernet
        bridges to efficiently monitor FIP frames passing through them.  This
        data facilitates the automatic configuration of these ACLs.  In
        addition, the automatic configuration is possible independent of
        any other ACLs that may be in use in the network for other
        applications.  And FIP Snooping is to maintain these ACLs."
    ::= { ibFCoEConfig 4 }

ibFCoEFIPSnoopingEntry OBJECT-TYPE
    SYNTAX          IbFCoEFIPSnoopingEntry
    MAX-ACCESS      not-accessible
    STATUS          current
    DESCRIPTION
        "There is one entry in this table for each VLAN that is
        designated to ensure that only valid FCoE traffic is allowed."
    INDEX           {
                        fcmInstanceIndex,
                        ibFCoEFIPSnoopingVLANIndex
                    }
    ::= { ibFCoEFIPSnoopingTable 1 }

IbFCoEFIPSnoopingEntry ::= SEQUENCE {
    ibFCoEFIPSnoopingVLANIndex    VlanIndex,
    ibFCoEFIPSnoopingEnable       TruthValue,
    ibFCoEFIPSnoopingFcmap        OCTET STRING
}

ibFCoEFIPSnoopingVLANIndex OBJECT-TYPE
    SYNTAX          VlanIndex
    MAX-ACCESS      not-accessible
    STATUS          current
    DESCRIPTION
        "This object identifies the VLAN-ID that the FIP Snooping function
        is being enabled for."
    ::= { ibFCoEFIPSnoopingEntry 1 }

ibFCoEFIPSnoopingEnable OBJECT-TYPE
    SYNTAX          TruthValue
    MAX-ACCESS      read-write
    STATUS          current
    DESCRIPTION
        "This object is used to enable or disable FIP Snooping on an
        Ethernet Bridge."
    DEFVAL { false }
    ::= { ibFCoEFIPSnoopingEntry 2 }

ibFCoEFIPSnoopingFcmap OBJECT-TYPE
    SYNTAX          OCTET STRING (SIZE (3))
    MAX-ACCESS      read-write
    STATUS          current
    DESCRIPTION
        "This object configures the FC-MAP value associated with the
        FIP snooping Ethernet Bridge."
    DEFVAL { '0EFC00'h }
    ::= { ibFCoEFIPSnoopingEntry 3 }

-- VLAN FCoE Configuration
ibFCoEVlanCfgTable     OBJECT-TYPE
    SYNTAX      SEQUENCE OF IbFCoEVlanCfgEntry
    MAX-ACCESS  not-accessible
    STATUS      current
    DESCRIPTION
        "A table contains FCoE related configurations and information of VLANs.
         An entry in this table is created when the corresponding VLAN
         is created and FCoE is enabled for the VLAN, as well as deleted when
         the VLAN is deleted or FCoE is disabled for the VLAN.
         If the switch mode is not FCF-NPV mode, all the operations
         on any object in this table result in errors."
    ::= { ibFCoEConfig 5 }

ibFCoEVlanCfgEntry  OBJECT-TYPE
    SYNTAX      IbFCoEVlanCfgEntry
    MAX-ACCESS  not-accessible
    STATUS      current
    DESCRIPTION
        "An entry used for managing the FCoE related configurations of a VLAN."
    INDEX { ibFCoEVLANIndex }
    ::= { ibFCoEVlanCfgTable 1}

IbFCoEVlanCfgEntry ::= SEQUENCE {
    ibFCoEVlanCfgFcmap                    OCTET STRING,
    ibFCoEVlanCfgFCFPriority              Unsigned32,
    ibFCoEVlanCfgDATov                    Unsigned32,
    ibFCoEVlanCfgRowStatus                RowStatus
}

ibFCoEVlanCfgFcmap OBJECT-TYPE
    SYNTAX          OCTET STRING (SIZE (3))
    MAX-ACCESS      read-create
    STATUS          current
    DESCRIPTION
        "This object configures the FC-MAP value used by the FCF in a VLAN
        when operating in FPMA mode.
        If this object is not configured, the default value is 0EFC00h."
    DEFVAL { '0EFC00'h }
    ::= { ibFCoEVlanCfgEntry 1 }

ibFCoEVlanCfgFCFPriority OBJECT-TYPE
    SYNTAX          Unsigned32 (0..255)
    MAX-ACCESS      read-create
    STATUS          current
    DESCRIPTION
        "The FIP priority value advertised by the FCF in a VLAN to ENodes by
        default.
        If this object is not configured, the default value is 128."
    DEFVAL { 128 }
    ::= { ibFCoEVlanCfgEntry 2 }

ibFCoEVlanCfgDATov OBJECT-TYPE
    SYNTAX          Unsigned32 (4..600)
    UNITS           "seconds"
    MAX-ACCESS      read-create
    STATUS          current
    DESCRIPTION
        "The Discovery_Advertisement_Timeout value configured for
        the FCF in a VLAN.
        This is used as the timeout value in seconds by
        the FCF in a VLAN to send periodic Discovery Advertisements.
        If this object is not configured, the default value is 8."
    DEFVAL { 8 }
    ::= { ibFCoEVlanCfgEntry 3 }

ibFCoEVlanCfgRowStatus OBJECT-TYPE
    SYNTAX      RowStatus
    MAX-ACCESS  read-create
    STATUS      current
    DESCRIPTION
        "Now only three states are supported:
         createAndGo, active, and destroy."
    ::= { ibFCoEVlanCfgEntry 4 }

-- FIP Snooping FCF information
ibFCoEFIPSnoopingFCFTable OBJECT-TYPE
    SYNTAX          SEQUENCE OF IbFCoEFIPSnoopingFCFEntry
    MAX-ACCESS      not-accessible
    STATUS          current
    DESCRIPTION
        "A table contains the remote FCF information on device."
    ::= { ibFCoEConfig 6 }

ibFCoEFIPSnoopingFCFEntry OBJECT-TYPE
    SYNTAX          IbFCoEFIPSnoopingFCFEntry
    MAX-ACCESS      not-accessible
    STATUS          current
    DESCRIPTION
        "Each entry contains information about a FCF for a VLAN."
    INDEX           {
                      fcmInstanceIndex,
                      ibFCoEFIPSnoopingFCFVLANIndex,
                      ibFCoEFIPSnoopingFCFIfIndex,
                      ibFCoEFIPSnoopingFCFMAC
                    }
    ::= { ibFCoEFIPSnoopingFCFTable 1 }

IbFCoEFIPSnoopingFCFEntry ::= SEQUENCE {
    ibFCoEFIPSnoopingFCFVLANIndex     VlanIndex,
    ibFCoEFIPSnoopingFCFIfIndex       InterfaceIndex,
    ibFCoEFIPSnoopingFCFMAC           MacAddress,
    ibFCoEFIPSnoopingFCFSwitchName    IbFcNameId,
    ibFCoEFIPSnoopingFCFFabricName    IbFcNameId,
    ibFCoEFIPSnoopingFCFENodeCount    Unsigned32
}

ibFCoEFIPSnoopingFCFVLANIndex OBJECT-TYPE
    SYNTAX          VlanIndex
    MAX-ACCESS      not-accessible
    STATUS          current
    DESCRIPTION
        "This object identifies the VLAN-ID whose FIP Snooping function
        gets ready on the FCF."
    ::= { ibFCoEFIPSnoopingFCFEntry 1 }

ibFCoEFIPSnoopingFCFIfIndex OBJECT-TYPE
    SYNTAX          InterfaceIndex
    MAX-ACCESS      not-accessible
    STATUS          current
    DESCRIPTION
        "This index uniquely identifies an Ethernet interface that connects
        to the FCF."
    ::= { ibFCoEFIPSnoopingFCFEntry 2 }

ibFCoEFIPSnoopingFCFMAC OBJECT-TYPE
    SYNTAX          MacAddress
    MAX-ACCESS      not-accessible
    STATUS          current
    DESCRIPTION
        "The MAC address of the Ethernet interface on the FCF directly
        connected to the local device."
    ::= { ibFCoEFIPSnoopingFCFEntry 3 }

ibFCoEFIPSnoopingFCFSwitchName OBJECT-TYPE
    SYNTAX          IbFcNameId
    MAX-ACCESS      read-only
    STATUS          current
    DESCRIPTION
        "The switch name of the FCF."
    ::= { ibFCoEFIPSnoopingFCFEntry 4 }

ibFCoEFIPSnoopingFCFFabricName OBJECT-TYPE
    SYNTAX          IbFcNameId
    MAX-ACCESS      read-only
    STATUS          current
    DESCRIPTION
        "The fabric name of the FCF."
    ::= { ibFCoEFIPSnoopingFCFEntry 5 }

ibFCoEFIPSnoopingFCFENodeCount OBJECT-TYPE
    SYNTAX          Unsigned32
    MAX-ACCESS      read-only
    STATUS          current
    DESCRIPTION
        "The total number of ENodes that log in through this Ethernet port."
    ::= { ibFCoEFIPSnoopingFCFEntry 6 }

-- FIP Snooping ENode information
ibFCoEFIPSnoopingENodeTable OBJECT-TYPE
    SYNTAX          SEQUENCE OF IbFCoEFIPSnoopingENodeEntry
    MAX-ACCESS      not-accessible
    STATUS          current
    DESCRIPTION
        "A table contains the ENode information on the local device."
    ::= { ibFCoEConfig 7 }

ibFCoEFIPSnoopingENodeEntry OBJECT-TYPE
    SYNTAX          IbFCoEFIPSnoopingENodeEntry
    MAX-ACCESS      not-accessible
    STATUS          current
    DESCRIPTION
        "Each entry contains information about an ENode for a VLAN."
    INDEX           {
                      fcmInstanceIndex,
                      ibFCoEFIPSnoopingENodeVLANIndex,
                      ibFCoEFIPSnoopingENodeIfIndex,
                      ibFCoEFIPSnoopingENodeMAC
                    }
    ::= { ibFCoEFIPSnoopingENodeTable 1 }

IbFCoEFIPSnoopingENodeEntry ::= SEQUENCE {
    ibFCoEFIPSnoopingENodeVLANIndex     VlanIndex,
    ibFCoEFIPSnoopingENodeIfIndex       InterfaceIndex,
    ibFCoEFIPSnoopingENodeMAC           MacAddress,
    ibFCoEFIPSnoopingENodeName          IbFcNameId
}

ibFCoEFIPSnoopingENodeVLANIndex OBJECT-TYPE
    SYNTAX          VlanIndex
    MAX-ACCESS      not-accessible
    STATUS          current
    DESCRIPTION
        "This object identifies the VLAN-ID whose FIP Snooping function
        gets ready on the ENode."
    ::= { ibFCoEFIPSnoopingENodeEntry 1 }

ibFCoEFIPSnoopingENodeIfIndex OBJECT-TYPE
    SYNTAX          InterfaceIndex
    MAX-ACCESS      not-accessible
    STATUS          current
    DESCRIPTION
        "This index uniquely identifies an Ethernet interface that connects
        to the ENode."
    ::= { ibFCoEFIPSnoopingENodeEntry 2 }

ibFCoEFIPSnoopingENodeMAC OBJECT-TYPE
    SYNTAX          MacAddress
    MAX-ACCESS      not-accessible
    STATUS          current
    DESCRIPTION
        "The MAC address of the ENode."
    ::= { ibFCoEFIPSnoopingENodeEntry 3 }

ibFCoEFIPSnoopingENodeName OBJECT-TYPE
    SYNTAX          IbFcNameId
    MAX-ACCESS      read-only
    STATUS          current
    DESCRIPTION
        "The node name of the ENode."
    ::= { ibFCoEFIPSnoopingENodeEntry 4 }

-- FIP Snooping VN information
ibFCoEFIPSnoopingVNTable OBJECT-TYPE
    SYNTAX          SEQUENCE OF IbFCoEFIPSnoopingVNEntry
    MAX-ACCESS      not-accessible
    STATUS          current
    DESCRIPTION
        "A table contains the virtual N_Port information on the local device."
    ::= { ibFCoEConfig 8 }

ibFCoEFIPSnoopingVNEntry OBJECT-TYPE
    SYNTAX          IbFCoEFIPSnoopingVNEntry
    MAX-ACCESS      not-accessible
    STATUS          current
    DESCRIPTION
        "Each entry contains information about a virtual N_Port."
    INDEX           {
                      fcmInstanceIndex,
                      ibFCoEFIPSnoopingVNVLANIndex,
                      ibFCoEFIPSnoopingVNENodeIfIndex,
                      ibFCoEFIPSnoopingVNENodeMAC,
                      ibFCoEFIPSnoopingVNFCFMAC,
                      ibFCoEFIPSnoopingVNMAC
                    }
    ::= { ibFCoEFIPSnoopingVNTable 1 }

IbFCoEFIPSnoopingVNEntry ::= SEQUENCE {
    ibFCoEFIPSnoopingVNVLANIndex     VlanIndex,
    ibFCoEFIPSnoopingVNENodeIfIndex  InterfaceIndex,
    ibFCoEFIPSnoopingVNENodeMAC      MacAddress,
    ibFCoEFIPSnoopingVNFCFMAC        MacAddress,
    ibFCoEFIPSnoopingVNMAC           MacAddress,
    ibFCoEFIPSnoopingVNName          IbFcNameId,
    ibFCoEFIPSnoopingVNFCFIfIndex    InterfaceIndex
}

ibFCoEFIPSnoopingVNVLANIndex OBJECT-TYPE
    SYNTAX          VlanIndex
    MAX-ACCESS      not-accessible
    STATUS          current
    DESCRIPTION
        "This object identifies the VLAN-ID through which a virtual N_Port
        logs in to the FCF."
    ::= { ibFCoEFIPSnoopingVNEntry 1 }

ibFCoEFIPSnoopingVNENodeIfIndex OBJECT-TYPE
    SYNTAX          InterfaceIndex
    MAX-ACCESS      not-accessible
    STATUS          current
    DESCRIPTION
        "This index uniquely identifies an Ethernet interface that connects
        to the ENode."
    ::= { ibFCoEFIPSnoopingVNEntry 2 }

ibFCoEFIPSnoopingVNENodeMAC OBJECT-TYPE
    SYNTAX          MacAddress
    MAX-ACCESS      not-accessible
    STATUS          current
    DESCRIPTION
        "The MAC address of the ENode."
    ::= { ibFCoEFIPSnoopingVNEntry 3 }

ibFCoEFIPSnoopingVNFCFMAC OBJECT-TYPE
    SYNTAX          MacAddress
    MAX-ACCESS      not-accessible
    STATUS          current
    DESCRIPTION
        "The MAC address of the FCF."
    ::= { ibFCoEFIPSnoopingVNEntry 4 }

ibFCoEFIPSnoopingVNMAC OBJECT-TYPE
    SYNTAX          MacAddress
    MAX-ACCESS      not-accessible
    STATUS          current
    DESCRIPTION
        "The MAC address of the virtual N_Port."
    ::= { ibFCoEFIPSnoopingVNEntry 5 }

ibFCoEFIPSnoopingVNName OBJECT-TYPE
    SYNTAX          IbFcNameId
    MAX-ACCESS      read-only
    STATUS          current
    DESCRIPTION
        "The port name of the virtual N_Port."
    ::= { ibFCoEFIPSnoopingVNEntry 6 }

ibFCoEFIPSnoopingVNFCFIfIndex OBJECT-TYPE
    SYNTAX          InterfaceIndex
    MAX-ACCESS      read-only
    STATUS          current
    DESCRIPTION
        "This index uniquely identifies an Ethernet interface that connects
        to the FCF."
    ::= { ibFCoEFIPSnoopingVNEntry 7 }

-- FIP Snooping Config type of Ethernet
ibFCoEFIPSnoopingIfCfgTable OBJECT-TYPE
    SYNTAX          SEQUENCE OF IbFCoEFIPSnoopingIfCfgEntry
    MAX-ACCESS      not-accessible
    STATUS          current
    DESCRIPTION
        "A table is used to configure FIP Snooping working mode of the Ethernet
        interface on the localdevice."
    ::= { ibFCoEConfig 9 }

ibFCoEFIPSnoopingIfCfgEntry OBJECT-TYPE
    SYNTAX          IbFCoEFIPSnoopingIfCfgEntry
    MAX-ACCESS      not-accessible
    STATUS          current
    DESCRIPTION
        "Each entry contains information about FIP Snooping working mode of the
        Ethernet interface."
    INDEX           {
                      fcmInstanceIndex,
                      ibFCoEFIPSnoopingIfCfgIfIndex
                    }
    ::= { ibFCoEFIPSnoopingIfCfgTable 1 }

IbFCoEFIPSnoopingIfCfgEntry ::= SEQUENCE {
    ibFCoEFIPSnoopingIfCfgIfIndex       InterfaceIndex,
    ibFCoEFIPSnoopingIfCfgPortType      INTEGER
}

ibFCoEFIPSnoopingIfCfgIfIndex OBJECT-TYPE
    SYNTAX          InterfaceIndex
    MAX-ACCESS      not-accessible
    STATUS          current
    DESCRIPTION
        "This index uniquely identifies an Ethernet interface."
    ::= { ibFCoEFIPSnoopingIfCfgEntry 1 }

ibFCoEFIPSnoopingIfCfgPortType OBJECT-TYPE
    SYNTAX          INTEGER {
                             fcf(1),
                             enode(2)
                            }
    MAX-ACCESS      read-write
    STATUS          current
    DESCRIPTION
        "The FIP Snooping working mode of an Ethernet interface on the local
        device.  The FCF mode means that the Ethernet interface must connect
        to an FCF.  The ENode mode means that the Ethernet interface must
        connect to an ENode."
    ::= { ibFCoEFIPSnoopingIfCfgEntry 2 }

END
