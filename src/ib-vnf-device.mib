-- =================================================================
-- Copyright (C) 2023 Intelbras S.A. All rights reserved.
--
-- Description: vnf-device mib
-- Reference:
-- Version: V1.2
-- History:
--  V1.0 Created by zhoufan
--      2020-11-18 updated by xuyuanqiang
--      Add ibVnfDeviceTraps
--          ibVmInfoTraps
--          ibVmChannelHealthTraps
--          ibVnfTrapObjects
--  V1.1 Updated by dongzhijian
--      Update ibVmInconsist
--          ibVmInconsistResume
--  V1.2 Updated by zhangfeng
--      Add mpuvm and lpuvm to ibVmType
--  Initial version 2020-11-18
-- =================================================================
IB-VNF-DEVICE-MIB DEFINITIONS ::= BEGIN

IMPORTS
    ibCommon
        FROM IB-OID-MIB
    Integer32, OBJECT-TYPE, MODULE-IDENTITY, NOTIFICATION-TYPE, Unsigned32
        FROM SNMPv2-SMI
    DisplayString, MacAddress
        FROM SNMPv2-TC
    InetAddressType,InetAddress
        FROM INET-ADDRESS-MIB;

ibVnfDevice MODULE-IDENTITY
    LAST-UPDATED "202107190000Z"
    ORGANIZATION
        "Intelbras S.A. Industria de Telecomunicacao Eletronica Brasileria."
    CONTACT-INFO
        ""
    DESCRIPTION
        "The MIB module is used for VM(virtual machine) management."
    REVISION "202107190000Z"
    DESCRIPTION
        "Add mpuvm and lpuvm to ibVmType"
    REVISION "202102040000Z"
    DESCRIPTION
        "Update ibVmInconsist ibVmInconsistResume"
    REVISION "202011180000Z"
    DESCRIPTION
        "Add ibVmAttr ibVmGroup ibVnfTrapObjects
             ibVnfDeviceTraps ibVmInfoTraps ibVmChannelHealthTraps"
    REVISION    "202010100000Z"
    DESCRIPTION    "The initial version."
    ::= { ibCommon 196 }

ibVnfDeviceTable OBJECT IDENTIFIER ::= { ibVnfDevice 1 }

ibVmInfoTable OBJECT-TYPE
    SYNTAX      SEQUENCE OF IbVmInfoEntry
    MAX-ACCESS  not-accessible
    STATUS      current
    DESCRIPTION
        "VM information table."
    ::= { ibVnfDeviceTable 1 }

ibVmInfoEntry OBJECT-TYPE
    SYNTAX      IbVmInfoEntry
    MAX-ACCESS  not-accessible
    STATUS      current
    DESCRIPTION
        "An entry of the ibVmInfoTable."
    INDEX    { ibVmSlot }
    ::= { ibVmInfoTable 1 }

IbVmInfoEntry ::= SEQUENCE
    {
        ibVmSlot                 Integer32,
        ibVmName                 DisplayString,
        ibVmType                 INTEGER,
        ibVmState                INTEGER,
        ibVmRole                 INTEGER,
        ibVmRegisterStatus       INTEGER,
        ibVmAttr                 INTEGER,
        ibVmGroup                Integer32
    }

ibVmSlot  OBJECT-TYPE
    SYNTAX      Integer32(1..2147483647)
    MAX-ACCESS  accessible-for-notify
    STATUS      current
    DESCRIPTION
        "VM slot."
    ::= { ibVmInfoEntry 1 }

ibVmName  OBJECT-TYPE
    SYNTAX      DisplayString (SIZE(1..255))
    MAX-ACCESS  read-only
    STATUS      current
    DESCRIPTION
        "VM name."
    ::= { ibVmInfoEntry 2 }

ibVmType   OBJECT-TYPE
    SYNTAX   INTEGER
    {
        other   (1),
        ctrlvm  (2),
        brasvm  (3),
        fwdvm   (4),
        mpuvm   (5),
        lpuvm   (6)
    }
    MAX-ACCESS   read-only
    STATUS       current
    DESCRIPTION
        "VM type."
    ::= { ibVmInfoEntry 3 }

ibVmState  OBJECT-TYPE
    SYNTAX   INTEGER
    {
        absent (1),
        normal (2),
        fault  (3),
        other  (4)
    }
    MAX-ACCESS   read-only
    STATUS       current
    DESCRIPTION
        "VM state."
    ::= { ibVmInfoEntry 4 }

ibVmRole  OBJECT-TYPE
    SYNTAX  INTEGER
    {
        master  (1),
        standby (2),
        other   (3)
    }
    MAX-ACCESS   read-only
    STATUS       current
    DESCRIPTION
        "VM role."
    ::= { ibVmInfoEntry 5 }

ibVmRegisterStatus    OBJECT-TYPE
    SYNTAX              INTEGER
    {
        registered               (1),
        unregistered             (2),
        unregisteredDestroying   (3),
        registering              (4),
        maddown                  (5),
        unregisteredMaddown      (6),
        other                    (7)
    }
    MAX-ACCESS   read-only
    STATUS       current
    DESCRIPTION
        "VM registration state."
    ::= { ibVmInfoEntry 6 }

ibVmAttr    OBJECT-TYPE
    SYNTAX              INTEGER
    {
        initDeploy               (1),
        manu                     (2),
        auto                     (3),
        autoAccept               (4)
    }
    MAX-ACCESS   read-only
    STATUS       current
    DESCRIPTION
        "VM attribute."
    ::= { ibVmInfoEntry 7 }

ibVmGroup   OBJECT-TYPE
    SYNTAX       Integer32(1..65535)
    MAX-ACCESS   read-only
    STATUS       current
    DESCRIPTION
        "VM belong to group.
        the Default is a invalid value 65535."
    ::= { ibVmInfoEntry 8 }
-- ==================================================================
--
-- VM trap object
--
-- ==================================================================
ibVnfDeviceTraps OBJECT IDENTIFIER ::= { ibVnfDevice 2 }
ibVnfmTrapPrefix OBJECT IDENTIFIER ::= { ibVnfDeviceTraps 0 }

ibVnfmConnectionFault NOTIFICATION-TYPE
    OBJECTS { ibVnfmIPType, ibVnfmIP, ibVnfmPort }
    STATUS  current
    DESCRIPTION
        "Cp and so communication failure."
    ::= { ibVnfmTrapPrefix 1 }

ibVnfmConnectionFaultResume NOTIFICATION-TYPE
    OBJECTS { ibVnfmIPType, ibVnfmIP, ibVnfmPort }
    STATUS  current
    DESCRIPTION
        "Cp and so communication recovery."
    ::= { ibVnfmTrapPrefix 2 }

ibVnvmAuthenFault NOTIFICATION-TYPE
    OBJECTS { ibVnfmIPType, ibVnfmIP, ibVnfmPort }
    STATUS  current
    DESCRIPTION
        "Cp and so authentication failed."
    ::= { ibVnfmTrapPrefix 3 }

ibVmInfoTraps OBJECT IDENTIFIER ::= { ibVnfDevice 3 }
ibVmInfoTrapPrefix OBJECT IDENTIFIER ::= { ibVmInfoTraps 0 }

ibVmCreate NOTIFICATION-TYPE
    OBJECTS { ibVmSlot, ibVmType, ibVmAttr, ibVmGroup }
    STATUS  current
    DESCRIPTION
        "The event of create VM."
    ::= { ibVmInfoTrapPrefix 1 }

ibVmDelete NOTIFICATION-TYPE
    OBJECTS { ibVmSlot, ibVmType, ibVmAttr, ibVmGroup }
    STATUS  current
    DESCRIPTION
        "The event of delete VM."
    ::= { ibVmInfoTrapPrefix 2 }

ibVmCreateSuccess NOTIFICATION-TYPE
    OBJECTS { ibVmSlot, ibVmType, ibVmAttr, ibVmGroup, ibVmRetryTimes }
    STATUS  current
    DESCRIPTION
        "Success to create VM."
    ::= { ibVmInfoTrapPrefix 3 }

ibVmCreateFail NOTIFICATION-TYPE
    OBJECTS { ibVmSlot, ibVmType, ibVmAttr, ibVmGroup, ibVmRetryTimes, ibVmCreateFailReason }
    STATUS  current
    DESCRIPTION
        "Failed to create VM."
    ::= { ibVmInfoTrapPrefix 4 }

ibVmDeleteSuccess NOTIFICATION-TYPE
    OBJECTS { ibVmSlot, ibVmType, ibVmAttr, ibVmGroup, ibVmRetryTimes }
    STATUS  current
    DESCRIPTION
        "Success to delete VM."
    ::= { ibVmInfoTrapPrefix 5 }

ibVmDeleteFail NOTIFICATION-TYPE
    OBJECTS { ibVmSlot, ibVmType, ibVmAttr, ibVmGroup, ibVmRetryTimes, ibVmDeleteFailReason }
    STATUS  current
    DESCRIPTION
        "Failed to delete VM."
    ::= { ibVmInfoTrapPrefix 6 }

ibVmInconsist NOTIFICATION-TYPE
    OBJECTS { ibVmSlot, ibVmName, ibVmStatusOnVnfm, ibVmInconsistFaultReason }
    STATUS  current
    DESCRIPTION
        "The local virtual machine resources are inconsistent with the resources on vnf."
    ::= { ibVmInfoTrapPrefix 7 }

ibVmInconsistResume NOTIFICATION-TYPE
    OBJECTS { ibVmSlot, ibVmName, ibVmStatusOnVnfm, ibVmInconsistFaultReason }
    STATUS  current
    DESCRIPTION
        "The local virtual machine resources are the same as those on vnf."
    ::= { ibVmInfoTrapPrefix 8 }

ibVmAcceptInconsistVm NOTIFICATION-TYPE
    OBJECTS { ibVmSlot, ibVmName, ibVmType, ibVmGroup }
    STATUS  current
    DESCRIPTION
        "Unconfigured VM claimed on vbras-cp."
    ::= { ibVmInfoTrapPrefix 9 }

ibVmReset NOTIFICATION-TYPE
    OBJECTS { ibVmSlot, ibVmType, ibVmGroup, ibVmResetResult }
    STATUS  current
    DESCRIPTION
        "VM restarts via VNFM."
    ::= { ibVmInfoTrapPrefix 10 }

ibVmUnregisterLongtime NOTIFICATION-TYPE
    OBJECTS { ibVmSlot, ibVmName, ibVmType, ibVmGroup }
    STATUS  current
    DESCRIPTION
        "VNFM has been allocated but will not be online for a long time."
    ::= { ibVmInfoTrapPrefix 11 }

ibVmIsolate NOTIFICATION-TYPE
    OBJECTS { ibVmSlot, ibVmType, ibVmGroup }
    STATUS  current
    DESCRIPTION
        "During the shrinking operation, it does not communicate with VNFM, VNFM isolates VM."
    ::= { ibVmInfoTrapPrefix 12 }

ibVmChannelHealthTraps OBJECT IDENTIFIER ::= { ibVnfDevice 4 }
ibVmChannelHealthTrapPrefix OBJECT IDENTIFIER ::= { ibVmChannelHealthTraps 0 }

ibVmChannelHealthNormal NOTIFICATION-TYPE
    OBJECTS { ibVmSelfSlot, ibVmPeerSlot, ibVmChannelType, ibVmChannelVlan }
    STATUS  current
    DESCRIPTION
        "The health check result of the control channel or data channel on the specified VM is normal."
    ::= { ibVmChannelHealthTrapPrefix 1 }

ibVmChannelHealthMinor NOTIFICATION-TYPE
    OBJECTS { ibVmSelfSlot, ibVmPeerSlot, ibVmChannelType, ibVmChannelVlan }
    STATUS  current
    DESCRIPTION
        "The control channel or data channel on the specified VM is in the minor sub-health state."
    ::= { ibVmChannelHealthTrapPrefix 2 }

ibVmChannelHealthSevere NOTIFICATION-TYPE
    OBJECTS { ibVmSelfSlot, ibVmPeerSlot, ibVmChannelType, ibVmChannelVlan }
    STATUS  current
    DESCRIPTION
        "The control channel or data channel on the specified VM is in the severe sub-health state."
    ::= { ibVmChannelHealthTrapPrefix 3 }

ibVmChannelLinkSwitch NOTIFICATION-TYPE
    OBJECTS { ibVmSelfSlot, ibVmChannelType, ibVmChannelVlan, ibVmChannelLinkMacAddress }
    STATUS  current
    DESCRIPTION
        "Link switching event."
    ::= { ibVmChannelHealthTrapPrefix 4 }
-- ==================================================================
--
-- VM trap Bind variable
--
-- ==================================================================
ibVnfTrapObjects OBJECT IDENTIFIER ::= { ibVnfDevice 5 }
ibVnfmTrapObjects OBJECT IDENTIFIER ::= { ibVnfTrapObjects 1 }

ibVnfmIPType   OBJECT-TYPE
    SYNTAX     InetAddressType
    MAX-ACCESS     accessible-for-notify
    STATUS     current
    DESCRIPTION
        "VNFM ip address."
    ::= { ibVnfmTrapObjects 1 }

ibVnfmIP   OBJECT-TYPE
    SYNTAX     InetAddress
    MAX-ACCESS     accessible-for-notify
    STATUS     current
    DESCRIPTION
        "VNFM ip address."
    ::= { ibVnfmTrapObjects 2 }

ibVnfmPort   OBJECT-TYPE
    SYNTAX     Unsigned32 (0..65535)
    MAX-ACCESS     accessible-for-notify
    STATUS     current
    DESCRIPTION
        "VNFM port number."
    ::= { ibVnfmTrapObjects 3 }

ibVmInfoTrapObjects OBJECT IDENTIFIER ::= { ibVnfTrapObjects 2 }

ibVmRetryTimes   OBJECT-TYPE
    SYNTAX     Unsigned32 (0..65535)
    MAX-ACCESS     accessible-for-notify
    STATUS     current
    DESCRIPTION
        "Number of retries."
    ::= { ibVmInfoTrapObjects 1 }

ibVmCreateAttr   OBJECT-TYPE
    SYNTAX              INTEGER
    {
        initDeploy               (1),
        manu                     (2),
        auto                     (3),
        autoAccept               (4)
    }
    MAX-ACCESS     accessible-for-notify
    STATUS     current
    DESCRIPTION
        "The VM creation properties."
    ::= { ibVmInfoTrapObjects 2 }

ibVmCreateFailReason   OBJECT-TYPE
    SYNTAX         OCTET STRING (SIZE(0..128))
    MAX-ACCESS     accessible-for-notify
    STATUS     current
    DESCRIPTION
        "The VM create failed reason."
    ::= { ibVmInfoTrapObjects 3 }

ibVmDeleteFailReason   OBJECT-TYPE
    SYNTAX         OCTET STRING (SIZE(0..128))
    MAX-ACCESS     accessible-for-notify
    STATUS     current
    DESCRIPTION
        "The VM delete failed reason."
    ::= { ibVmInfoTrapObjects 4 }

ibVmInconsistFaultReason   OBJECT-TYPE
    SYNTAX              INTEGER
    {
        exisitOnLocal               (1),
        existOnVnfm                 (2)
    }
    MAX-ACCESS     accessible-for-notify
    STATUS     current
    DESCRIPTION
        "Reasons for VM inconsistency."
    ::= { ibVmInfoTrapObjects 5 }

ibVmResetResult   OBJECT-TYPE
    SYNTAX         OCTET STRING (SIZE(0..128))
    MAX-ACCESS     accessible-for-notify
    STATUS     current
    DESCRIPTION
        "Reasons for the failure to restart the virtual machine."
    ::= { ibVmInfoTrapObjects 6 }

ibVmStatusOnVnfm   OBJECT-TYPE
    SYNTAX              INTEGER
    {
        building               (1),
        active                 (2),
        error                  (3),
        unknown                (4)
    }
    MAX-ACCESS     accessible-for-notify
    STATUS     current
    DESCRIPTION
        "The status of the virtual machine on VNFM(virtualized network function managers)."
    ::= { ibVmInfoTrapObjects 7 }

ibVmChannelHealthTrapObjects OBJECT IDENTIFIER ::= { ibVnfTrapObjects 3 }

ibVmSelfSlot   OBJECT-TYPE
    SYNTAX     Unsigned32 (0..65535)
    MAX-ACCESS     accessible-for-notify
    STATUS     current
    DESCRIPTION
        "VM local slot number."
    ::= { ibVmChannelHealthTrapObjects 1 }

ibVmPeerSlot    OBJECT-TYPE
    SYNTAX     Unsigned32 (0..65535)
    MAX-ACCESS     accessible-for-notify
    STATUS     current
    DESCRIPTION
        "VM opposite slot number."
    ::= { ibVmChannelHealthTrapObjects 2 }

ibVmChannelType   OBJECT-TYPE
    SYNTAX              INTEGER
    {
        controlchannel               (1),
        datachannel                  (2)
    }
    MAX-ACCESS     accessible-for-notify
    STATUS     current
    DESCRIPTION
        "VM channel type."
    ::= { ibVmChannelHealthTrapObjects 3 }

ibVmChannelVlan   OBJECT-TYPE
    SYNTAX     Unsigned32 (1..4094)
    MAX-ACCESS     accessible-for-notify
    STATUS     current
    DESCRIPTION
        "VM channel vlan."
    ::= { ibVmChannelHealthTrapObjects 4 }

ibVmChannelLinkMacAddress   OBJECT-TYPE
    SYNTAX     MacAddress
    MAX-ACCESS     accessible-for-notify
    STATUS     current
    DESCRIPTION
        "The mac address of the fault port."
    ::= { ibVmChannelHealthTrapObjects 5 }

END
