-- =============================================================================
-- Copyright (C) 2023 Intelbras S.A. All rights reserved.
--
-- Description: Multiprotocol Label Switching Static Crlsp MIB
-- Reference:
-- Version: V1.1
-- History:
--   V1.0 2022-06-08 Initial version Created by Zhouwan
--   V1.1 2023-03-14 Modified by Long lewen, Modified ibMplsExtNotifications
-- =============================================================================
IB-MPLSSCRLSP-MIB DEFINITIONS ::= BEGIN
IMPORTS
    MODULE-IDENTITY, OBJECT-TYPE, NOTIFICATION-TYPE
        FROM SNMPv2-SMI
    ibCommon
        FROM IB-OID-MIB
    ;

-- =============================================================================
-- module identity part
-- =============================================================================
ibMplsScrlsp    MODULE-IDENTITY
    LAST-UPDATED
        "202303141400Z"   -- Mar 14, 2023 at 14:00 GMT
    ORGANIZATION
        "Intelbras S.A. Industria de Telecomunicacao Eletronica Brasileria."
    CONTACT-INFO
        ""
    DESCRIPTION
        "Multiprotocol Label Switching Static Crlsp MIB"
    REVISION
        "202303141400Z"   -- Mar 14, 2023 at 14:00 GMT
    DESCRIPTION
        "Modified ibMplsExtNotifications"
    REVISION
        "202206070920Z"   -- June 07, 2022 at 09:20 GMT
    DESCRIPTION
        "Initial version of this MIB."
    ::= { ibCommon 231 }

-- =============================================================================
-- Top level components of this MIB module.
-- =============================================================================
ibMplsScrlspNotifications OBJECT IDENTIFIER ::= { ibMplsScrlsp 0 }

ibMplsScrlspObjects       OBJECT IDENTIFIER ::= { ibMplsScrlsp 1 }

ibMplsScrlspScalarGroup   OBJECT IDENTIFIER ::= { ibMplsScrlspObjects 1 }

ibMplsScrlspBaseInfo    OBJECT-TYPE
    SYNTAX      OCTET STRING (SIZE (1..127))
    MAX-ACCESS  accessible-for-notify
    STATUS      current
    DESCRIPTION
        "The base information of MPLS static CRLSP."
    ::= { ibMplsScrlspScalarGroup 1 }

ibMplsScrlspExtInfo    OBJECT-TYPE
    SYNTAX      OCTET STRING (SIZE (1..127))
    MAX-ACCESS  accessible-for-notify
    STATUS      current
    DESCRIPTION
        "The external information of MPLS static CRLSP"
    ::= { ibMplsScrlspScalarGroup 2 }

-- =============================================================================
-- Notifications
-- =============================================================================
ibMplsScrlspDown  NOTIFICATION-TYPE
    OBJECTS {
            ibMplsScrlspBaseInfo,
            ibMplsScrlspExtInfo
            }
    STATUS      current
    DESCRIPTION
      "This notification is generated when the Static CRLSP changed to Down."
    ::= { ibMplsScrlspNotifications 1 }

ibMplsScrlspUp  NOTIFICATION-TYPE
    OBJECTS {
            ibMplsScrlspBaseInfo,
            ibMplsScrlspExtInfo
            }
    STATUS      current
    DESCRIPTION
      "This notification is generated when the Static CRLSP changed to Up."
    ::= { ibMplsScrlspNotifications 2 }

ibMplsScrlspLabelConflict    NOTIFICATION-TYPE
    OBJECTS {
            ibMplsScrlspBaseInfo,
            ibMplsScrlspExtInfo
            }
    STATUS      current
    DESCRIPTION
      "This notification is generated when the Segment Routing label is
      configured for another prefix segment."
    ::= { ibMplsScrlspNotifications 3 }

ibMplsScrlspLabelDup     NOTIFICATION-TYPE
    OBJECTS {
            ibMplsScrlspBaseInfo,
            ibMplsScrlspExtInfo
            }
    STATUS      current
    DESCRIPTION
      "This notification is generated when the Incoming label is duplicate."
    ::= { ibMplsScrlspNotifications 4 }

-- =============================================================================
-- End of notifications.
-- =============================================================================

END
