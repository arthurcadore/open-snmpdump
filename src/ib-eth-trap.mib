-- =================================================================
-- Copyright (C) 2023 Intelbras S.A. All rights reserved.
--
-- Description: ETH TRAP MIB File
-- Reference:
-- Version: V1.0
-- History:
-- V1.0 2023-04-21 created by yuanyuchen
-- =================================================================
IB-ETH-TRAP-MIB DEFINITIONS ::= BEGIN

IMPORTS
        ibCommon
    FROM IB-OID-MIB
        OBJECT-TYPE, MODULE-IDENTITY, NOTIFICATION-TYPE, Unsigned32
    FROM SNMPv2-SMI
        DisplayString, MacAddress
    FROM SNMPv2-TC;

ibEthTrap MODULE-IDENTITY
    LAST-UPDATED
        "202304210920Z"
    ORGANIZATION
        "Intelbras S.A. Industria de Telecomunicacao Eletronica Brasileria."
    CONTACT-INFO
        ""
    DESCRIPTION
        "This MIB file defines the ETH trap warning feature only."
    REVISION
        "202304210920Z"
    DESCRIPTION
        "The initial version of this MIB file."
    ::= { ibCommon 262 }


ibEthTrapMlag OBJECT IDENTIFIER ::= { ibEthTrap 1 }

ibEthTrapsMlag OBJECT IDENTIFIER ::= { ibEthTrapMlag 0 }

-- ibEthTrapsMlag
ibEthTrapMlagSetDrvFailed NOTIFICATION-TYPE
    OBJECTS
        {
            ibEthTrapMlagSetDrvChassis,
            ibEthTrapMlagSetDrvSlot,
            ibEthTrapMlagSetDrvIfName,
            ibEthTrapMlagSetDrvMacAddress
        }
    STATUS      current
    DESCRIPTION
        "ETH m-lag failed to add the MAC address."
    ::= { ibEthTrapsMlag 1 }

ibEthTrapMlagObjects OBJECT IDENTIFIER ::= { ibEthTrapMlag 1 }

-- ibEthTrapMlagObjects
ibEthTrapMlagSetDrvChassis OBJECT-TYPE
    SYNTAX      Unsigned32
    MAX-ACCESS  accessible-for-notify
    STATUS      current
    DESCRIPTION
        "The information of chassis ID. If the value is 65535, the device is
         not a stacked device."
    ::= { ibEthTrapMlagObjects 1 }

ibEthTrapMlagSetDrvSlot OBJECT-TYPE
    SYNTAX      Unsigned32
    MAX-ACCESS  accessible-for-notify
    STATUS      current
    DESCRIPTION
    "The information of slot."
    ::= { ibEthTrapMlagObjects 2 }

ibEthTrapMlagSetDrvIfName OBJECT-TYPE
    SYNTAX      DisplayString (SIZE (1..255))
    MAX-ACCESS  accessible-for-notify
    STATUS      current
    DESCRIPTION
        "The information of interface name."
    ::= { ibEthTrapMlagObjects 3 }

ibEthTrapMlagSetDrvMacAddress OBJECT-TYPE
    SYNTAX      MacAddress
    MAX-ACCESS  accessible-for-notify
    STATUS      current
    DESCRIPTION
        "The information of mac address."
    ::= { ibEthTrapMlagObjects 4 }

END
