-- =============================================================================
-- Copyright (C) 2023 Intelbras S.A. All rights reserved.
--
-- Description:
--   The file defines a MIB to provide WLAN configuration extended.
-- Reference:
-- Version: V1.3
-- History:
--   V1.0 2007-04-25 Initial version, created by shiyang (Richard)
--   V1.1 2008-07-17 Changed by chenwei
--        Add ibDot11LoadBalanceTrafficGap and
--        ibDot11LoadBalanceSessionGap to ibDot11LBGlobalGroup.
--   V1.2 2010-02-22 Changed by Wang Chunsheng
--        Add new table of ibDot11LBRadioGroupTable for ibDot11LoadBalance.
--        2010-06-02 Changed by Yin Junjie
--        Add new node ibDot11LBTrafficThresKbps and
--        ibDot11LBTrafficGapKbps to ibDot11LBGlobalGroup.
--   V1.3 2016-03-11 add by yubo 04460
--        Add ibDot11LoadBalanceEnable to ibDot11LBGlobalGroup
-- =============================================================================
IB-DOT11-CFGEXT-MIB DEFINITIONS ::= BEGIN

IMPORTS
        TruthValue,
        RowStatus
    FROM SNMPv2-TC
        MODULE-IDENTITY,
        OBJECT-TYPE,
        Integer32,
        Unsigned32
    FROM SNMPv2-SMI
        ibDot11
    FROM IB-DOT11-REF-MIB;

ibDot11CFGEXT MODULE-IDENTITY
    LAST-UPDATED "201603111800Z"        -- Mar 11, 2016 at 18:00 GMT
    ORGANIZATION
        "Intelbras S.A. Industria de Telecomunicacao Eletronica Brasileria."
    CONTACT-INFO
        ""
    DESCRIPTION
        "This MIB provides information for WLAN configuration extended.
        The IB-DOT11-CFG-MIB define MIB objects for WLAN basic configuration,
        while this MIB will define MIB objects for load balance these kinds
        feature.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Fat AP
        Applied in the home, SOHO and so on, and it could
        work independently without help from AC.

        Fit AP
        Applied in the enterprise environment, it will work
        under the control and management from AC.

        Control And Provisioning of Wireless Access Points Protocol
        The short name of protocol is CAPWAP. AC will control
        and manage AP by CAPWAP tunnel protocol defined by IETF.
        Also, a data tunnel will be set up between AC and AP.

        BSS
        IEEE 802.11 Basic Service Set (Radio Cell).  The
        BSS of an AP comprises of the stations directly
        associating with the AP.

        Radio
        The chip set to receive and send wireless signal.

        Association
        The service used to establish access point
        or station mapping and enable station invocation
        of the distribution system services.
        (Wireless clients attempt to connect to
        access points.)

        Basic Rate
        A data rate that is mandatory for client
        devices to support in order for them to achieve
        successful association.

        MSDU
        MAC Service Data Unit, it is frame format defined by
        802.11.

        TU
        It is 1,024 microseconds (ms), which is about 1
        millisecond.

        AKM
        The authentication and key management method defined by
        802.11i, and which includes 802.1x and pre-shared key."
    REVISION "201603111800Z"        -- Mar 11, 2016 at 18:00 GMT
    DESCRIPTION
        "Modified to add new nodes."
    REVISION "201006021400Z"        -- Jun 02, 2010 at 14:00 GMT
    DESCRIPTION
        "Modified to add new nodes."
    REVISION "200704252000Z"        -- Apr. 25, 2007 at 20:00 GMT
    DESCRIPTION
        "The initial revision of this MIB module."
    ::= { ibDot11 6 }

-- *****************************************************************************
-- *  Major sections
-- *****************************************************************************
--  Load Balancing Group
--  DEFINED AS "The group to provide the configuration information
--  for load balancing feature.
ibDot11LoadBalance OBJECT IDENTIFIER   ::= { ibDot11CFGEXT 1 }
ibDot11LBGlobalGroup OBJECT IDENTIFIER ::= { ibDot11LoadBalance 1 }

-- *****************************************************************************
-- *  ibDot11LBGlobalGroup Definition
-- *****************************************************************************
ibDot11LoadBalanceTrafficEnable OBJECT-TYPE
    SYNTAX      TruthValue
    MAX-ACCESS  read-write
    STATUS      current
    DESCRIPTION
        "Represents whether enable load balancing according to station
        traffic."
    ::= { ibDot11LBGlobalGroup 1 }

ibDot11LoadBalanceTrafficThres OBJECT-TYPE
    SYNTAX      Integer32
    MAX-ACCESS  read-write
    STATUS      current
    DESCRIPTION
        "Represents the threshold value for Traffic based load balancing."
    ::= { ibDot11LBGlobalGroup 2 }

ibDot11LoadBalanceSessionEnable OBJECT-TYPE
    SYNTAX      TruthValue
    MAX-ACCESS  read-write
    STATUS      current
    DESCRIPTION
        "Represents whether enable load balancing according to station
        session number."
    ::= { ibDot11LBGlobalGroup 3 }

ibDot11LoadBalanceSessionThres OBJECT-TYPE
    SYNTAX      Integer32
    MAX-ACCESS  read-write
    STATUS      current
    DESCRIPTION
        "Represents the threshold value for session number based
        load balancing."
    ::= { ibDot11LBGlobalGroup 4 }

ibDot11LoadBalanceTrafficGap OBJECT-TYPE
    SYNTAX      Integer32 (10..40)
    MAX-ACCESS  read-write
    STATUS      current
    DESCRIPTION
        "Traffic gap threshold.  Load balancing is carried out for a radio
        when the traffic threshold and session gap are exceeded."
    DEFVAL { 20 }
    ::= { ibDot11LBGlobalGroup 5 }

ibDot11LoadBalanceSessionGap OBJECT-TYPE
    SYNTAX      Integer32 (1..8)
    MAX-ACCESS  read-write
    STATUS      current
    DESCRIPTION
        "Session gap threshold.  Load balancing is carried out for a radio
        when the session threshold and session gap are exceeded."
    DEFVAL { 4 }
    ::= { ibDot11LBGlobalGroup 6 }

ibDot11LBTrafficThresKbps OBJECT-TYPE
    SYNTAX      Integer32
    UNITS       "kbps"
    MAX-ACCESS  read-write
    STATUS      current
    DESCRIPTION
        "Represents the threshold value for Traffic based load balancing."
    ::= { ibDot11LBGlobalGroup 7 }

ibDot11LBTrafficGapKbps OBJECT-TYPE
    SYNTAX      Integer32
    UNITS       "kbps"
    MAX-ACCESS  read-write
    STATUS      current
    DESCRIPTION
        "Traffic gap threshold.  Load balancing is carried out for a radio
        when the traffic threshold gap are exceeded."
    ::= { ibDot11LBGlobalGroup 8 }

ibDot11LoadBalanceEnable OBJECT-TYPE
    SYNTAX      INTEGER
    {
        none(0),
        trafficBased(1),
        userBased(2)
    }
    MAX-ACCESS  read-write
    STATUS      current
    DESCRIPTION
        "Represents whether to enable load balancing.
         0    - none
         1    - enable load balancing according to station traffic
         2    - enable load balancing according to station session number."
    DEFVAL      { none }
    ::= { ibDot11LBGlobalGroup 9 }

-- *****************************************************************************
-- *  End of ibDot11LBGlobalGroup Definition
-- *****************************************************************************

-- *****************************************************************************
-- *  ibDot11LBRadioGroup Definition
-- *****************************************************************************
ibDot11LBRadioGroupTable OBJECT-TYPE
    SYNTAX SEQUENCE OF IbDot11LBRadioGroupEntry
    MAX-ACCESS not-accessible
    STATUS current
    DESCRIPTION
        "This table defines load balance radio group."
    ::= { ibDot11LoadBalance 2 }

ibDot11LBRadioGroupEntry OBJECT-TYPE
    SYNTAX      IbDot11LBRadioGroupEntry
    MAX-ACCESS  not-accessible
    STATUS      current
    DESCRIPTION
        "Each entry contains information of one load balance radio group."
    INDEX
        {
            ibDot11LBRadioGroupId
        }
    ::= { ibDot11LBRadioGroupTable 1 }

IbDot11LBRadioGroupEntry ::= SEQUENCE
    {
        ibDot11LBRadioGroupId        Unsigned32,
        ibDot11LBRadioGroupDesc      OCTET STRING,
        ibDot11LBRadioGroupRowStatus RowStatus
    }

ibDot11LBRadioGroupId OBJECT-TYPE
    SYNTAX      Unsigned32
    MAX-ACCESS  not-accessible
    STATUS      current
    DESCRIPTION
        "Represents load balance radio group ID."
    ::= { ibDot11LBRadioGroupEntry 1 }

ibDot11LBRadioGroupDesc OBJECT-TYPE
    SYNTAX      OCTET STRING
    MAX-ACCESS  read-create
    STATUS      current
    DESCRIPTION
        "Represents the description of load balance radio group."
    ::= { ibDot11LBRadioGroupEntry 2 }

ibDot11LBRadioGroupRowStatus OBJECT-TYPE
    SYNTAX      RowStatus
    MAX-ACCESS  read-create
    STATUS      current
    DESCRIPTION
        "The row status of this table entry."
    ::= { ibDot11LBRadioGroupEntry 3 }

-- *****************************************************************************
-- *  End of ibDot11LBRadioGroup Definition
-- *****************************************************************************

END
