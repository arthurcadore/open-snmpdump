-- =================================================================
-- Copyright (C) 2023 Intelbras S.A. All rights reserved.
--
-- Description: ENTITY RELATION MIB
-- Version: V1.2
-- History:
--   V1.0(Initial version) 19th Aug 2004
--   V1.1 2004-09-10 Exchange MIB objects' sequence, including ibEntRelationType
--                   and ibEntityIndex.
--                   Change subidentifier of ibEntRelationConformance from 3 to 2.
--   V1.2 2004-10-12 updated by gaolong
--        Remove ibEntityIndex, ibEntRelationType from ibEntRelationGroup
--        because they are not-accessible objects.
-- =================================================================
--

    IB-ENTRELATION-MIB DEFINITIONS ::= BEGIN

        IMPORTS
            PhysicalIndex
                FROM ENTITY-MIB
            ibCommon
                FROM IB-OID-MIB
            OBJECT-GROUP, MODULE-COMPLIANCE
                FROM SNMPv2-CONF
            OBJECT-TYPE, MODULE-IDENTITY
                FROM SNMPv2-SMI
            TEXTUAL-CONVENTION
                FROM SNMPv2-TC;



        ibEntityRelation MODULE-IDENTITY
            LAST-UPDATED "200408190000Z"
            ORGANIZATION
                "Intelbras S.A. Industria de Telecomunicacao Eletronica Brasileria."
            CONTACT-INFO
                ""
            DESCRIPTION
                "The private MIB file includes the general relation information
                information of entities.
                Entity MIB is used to express the physical location of the physical
                entities. Other relations, such as stack port pair and combo port
                pair, are not suitable to be implemented in Entity MIB. So this MIB is
                used to  express these relations. "
            ::= { ibCommon 15 }



--  Textual conventions
--
        IbEntRelationType ::= TEXTUAL-CONVENTION
            STATUS current
            DESCRIPTION
                "entRelationType describe the relation type of the two entities
                (indicated by entityIndex and relatedEntityIndex) .
                stackport: this port is a stack port.
                entityIndex is the default uplinkport index,
                and relatedEntityIndex is the default downlinkport index.
                comboport: this port is a combo port.
                entityIndex is the default active port index,
                and relatedEntityIndex is the default inactive port index."
            SYNTAX INTEGER
                {
                stackport(1),
                comboport(2)
                }




--  Node definitions
--
        ibEntRelationObjects OBJECT IDENTIFIER ::= { ibEntityRelation 1 }

--    MIB contains four groups
        ibEntRelation OBJECT IDENTIFIER ::= { ibEntRelationObjects 1 }

        ibEntRelationTable OBJECT-TYPE
            SYNTAX SEQUENCE OF IbEntRelationEntry
            MAX-ACCESS not-accessible
            STATUS current
            DESCRIPTION
                "Entity MIB is used to express the physical location of
                the physical entities. Other relations, such as stack
                port pair and combo port pair, are not suitable to be
                implemented in Entity MIB. This MIB is used to express
                these relations. "
            ::= { ibEntRelation 1 }

        ibEntRelationEntry OBJECT-TYPE
            SYNTAX IbEntRelationEntry
            MAX-ACCESS not-accessible
            STATUS current
            DESCRIPTION
                "The information about a particular physical entity."
            INDEX { ibEntRelationType, ibEntityIndex, ibRelatedEntityIndex }
            ::= { ibEntRelationTable 1 }

        IbEntRelationEntry ::=
            SEQUENCE {
                ibEntRelationType
                    IbEntRelationType,
                ibEntityIndex
                    PhysicalIndex,
                ibRelatedEntityIndex
                    PhysicalIndex
             }

        ibEntRelationType OBJECT-TYPE
            SYNTAX IbEntRelationType
            MAX-ACCESS not-accessible
            STATUS current
            DESCRIPTION
                "The index of ibEntRelationTable.
                entRelationType describe the relation type of the two
                entities(indicated by entityIndex and relatedEntityIndex) "
            ::= { ibEntRelationEntry 1 }

        ibEntityIndex OBJECT-TYPE
            SYNTAX PhysicalIndex
            MAX-ACCESS not-accessible
            STATUS current
            DESCRIPTION
                "The index of ibEntRelationTable.
                entityIndex is the index of the entity.
                This index is identical to entPhysicalIndex in ENTITY-MIB"
            ::= { ibEntRelationEntry 2 }

        ibRelatedEntityIndex OBJECT-TYPE
            SYNTAX PhysicalIndex
            MAX-ACCESS read-only
            STATUS current
            DESCRIPTION
                "The index of ibEntRelationTable.
                relatedEntityIndex is the entity index that entityIndex related to,
                This index is identical to entPhysicalIndex in ENTITY-MIB"
            ::= { ibEntRelationEntry 3 }

--    Conformance and Compliance
        ibEntRelationConformance OBJECT IDENTIFIER ::= { ibEntityRelation 2 }

        ibEntRelationCompliances OBJECT IDENTIFIER ::= { ibEntRelationConformance 1 }


-- this module
        ibEntRelationCompliance MODULE-COMPLIANCE
            STATUS current
            DESCRIPTION
                "The compliance statement for systems supporting this MIB."
            MODULE -- this module
                MANDATORY-GROUPS { ibEntRelationGroup }
            ::= { ibEntRelationCompliances 1 }

        ibEntRelationGroups OBJECT IDENTIFIER ::= { ibEntRelationConformance 2 }

        ibEntRelationGroup OBJECT-GROUP
            OBJECTS { ibRelatedEntityIndex }
            STATUS current
            DESCRIPTION
                "Standard Entity Relation group."
            ::= { ibEntRelationGroups 1 }


    END
