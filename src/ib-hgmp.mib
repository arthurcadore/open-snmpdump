-- ==================================================================
-- Copyright (C) 2023 Intelbras S.A. All rights reserved.
--
-- Description:  HGMP Information MIB
-- Reference:
-- Version: V1.8
-- History:
--   V1.0 2001.5.15 Created Ye dalu
--   V1.1 2004/7/20 Modify Object Name from IbNDPNbEntry
--        to IbNDPPortNbEntry
--   V1.2 2004/8/09 add notification ibhgmpNetTopChange
--   V1.3 2004-09-24 modify value of STATUS clause from 'mandatory' to 'current' by gaolong
--   V1.4 2004-10-12 updated by gaolong
--        Import NOTIFICATION-TYPE.
--   V1.5 2004-11-02 updated by gaolong
--        Import Counter32.
--   V1.6 2005-12-9  added by zhanglin KF0176
--        add ibhgmpClusterProtocolMac
--        add ibhgmpWhitelistNbTable
--        add ibhgmpWhitelistTable
--        add ibhgmpBlacklistTable
--        2005-12-20 added by zushuzhi 03030
--        add ibhgmpMemberPriPortTable
--        add ibhgmpNTDPTopLinkStatus
--   V1.7 2006-04-30 modified by gaolong
--        relocate ibhgmpProtocolMac, ibhgmpTopologyManagement, ibhgmpMemberPriPortTable
--        and the objects below them.
--        relocate ibhgmpNTDPTopLinkStatus in ibhgmpNTDPTopLinkStatus.
--   V1.8 2006-05-08 modify the description of ibhgmpNTDPCollectTopTime by shanfeng
-- ==================================================================
-- ==================================================================
--
-- Varibles and types be imported
--
-- ==================================================================
IB-HGMP-MIB  DEFINITIONS ::= BEGIN
    IMPORTS
        ibRhw
            FROM IB-OID-MIB
        IpAddress, Integer32, OBJECT-TYPE, MODULE-IDENTITY, OBJECT-IDENTITY,
        NOTIFICATION-TYPE, Counter32, Unsigned32
            FROM SNMPv2-SMI
        RowStatus, MacAddress, TEXTUAL-CONVENTION, DisplayString
            FROM SNMPv2-TC;

    ibHgmp MODULE-IDENTITY
        LAST-UPDATED "200512061452Z"
        ORGANIZATION
            "Intelbras S.A. Industria de Telecomunicacao Eletronica Brasileria."
        CONTACT-INFO
            ""
        DESCRIPTION
            "This MIB contains objects to manage the ibhgmp operations,
            which are used on lanswitch products."
        ::= { ibRhw 7 }

-- ==================================================================
--
-- ======================= definition begin =========================
--
-- ==================================================================

--
-- cluster definitions
--

    ibClusterObject OBJECT-IDENTITY
        STATUS      current
        DESCRIPTION
            "This MIB contains objects to manage the cluster operations, which
            are used on lanswitch products."
        ::= { ibHgmp 1 }

    ibhgmpSetVLANSecurity OBJECT-TYPE
        SYNTAX      INTEGER
            {
                noSecurity(0),
                security(1)
            }
        MAX-ACCESS  read-write
        STATUS      current
        DESCRIPTION
            "Configure whether to perform the VLAN check inside the cluster."
        DEFVAL { security }
        ::= { ibClusterObject 1 }

    ibhgmpHandShakeInterval OBJECT-TYPE
        SYNTAX      Integer32(1..255)
        MAX-ACCESS  read-write
        STATUS      current
        DESCRIPTION
            "Handshaking interval of the cluster member switches."
        DEFVAL { 10 }
        ::= { ibClusterObject 2 }

    ibhgmpHandShakeHoldtime OBJECT-TYPE
        SYNTAX      Integer32(1..255)
        MAX-ACCESS  read-write
        STATUS      current
        DESCRIPTION
            "Holdtime of administrator switch and member switch in the cluster."
        DEFVAL { 60 }
        ::= { ibClusterObject 3 }

    ibhgmpGrpMemberTableChange OBJECT-TYPE
        SYNTAX      Integer32(0..65535)
        MAX-ACCESS  read-only
        STATUS      current
        DESCRIPTION
            "Add 1 to the member list after it changes. The administrator checks if
            the value has changed. If not, he will not read the list once more."
        DEFVAL { 0 }
        ::= { ibClusterObject 4 }

    ibhgmpMemberDisconRate OBJECT-TYPE
        SYNTAX      Integer32
        MAX-ACCESS  read-only
        STATUS      current
        DESCRIPTION
            "Disconnection times of the member and administrator switches divided by
            member number times 1000."
        DEFVAL { 0 }
        ::= { ibClusterObject 5 }

    ibhgmpCmdLanswitchFlag OBJECT-TYPE
        SYNTAX      INTEGER
            {
                false(0),
                true(1)
            }
        MAX-ACCESS  read-write
        STATUS      current
        DESCRIPTION
            "Administrator switch flag"
        DEFVAL { false }
        ::= { ibClusterObject 6 }

    ibhgmpCmdClusterName OBJECT-TYPE
        SYNTAX      OCTET STRING(SIZE (0..8))
        MAX-ACCESS  read-write
        STATUS      current
        DESCRIPTION
            "Cluster name of the administrator switch"
        ::= { ibClusterObject 7 }

    ibhgmpMngPriIpSegCMIP OBJECT-TYPE
        SYNTAX      IpAddress
        MAX-ACCESS  read-write
        STATUS      current
        DESCRIPTION
            "The private management IP address of the administrator switch,
            which can not be modified after the cluster has been created."
        ::= { ibClusterObject 8 }

    ibhgmpMngPriIpMask OBJECT-TYPE
        SYNTAX      IpAddress
        MAX-ACCESS  read-write
        STATUS      current
        DESCRIPTION
            "The private management IP address mask assigned by the administrator
            switch, which cannot be modified after the cluster has been created."
        ::= { ibClusterObject 9 }

    ibhgmpFtpServer OBJECT-TYPE
        SYNTAX      IpAddress
        MAX-ACCESS  read-write
        STATUS      current
        DESCRIPTION
            "The cluster members can access the Ftp Server through the administrator
            switch, which can only be configured and accessed on the administrator
            switch."
        ::= { ibClusterObject 10 }

    ibhgmpTftpServer OBJECT-TYPE
        SYNTAX      IpAddress
        MAX-ACCESS  read-write
        STATUS      current
        DESCRIPTION
            "The cluster members can access the Tftp Server through the administrator
             switch, which can only be configured and accessed on the administrator
             switch."
        ::= { ibClusterObject 11 }

    ibhgmpSnmpHost OBJECT-TYPE
        SYNTAX      IpAddress
        MAX-ACCESS  read-write
        STATUS      current
        DESCRIPTION
            "The Snmp Host to send the cluster trap packets, which can only be
            configured and accessed on the administrator switch."
        ::= { ibClusterObject 12 }

    ibhgmpLogHost OBJECT-TYPE
        SYNTAX      IpAddress
        MAX-ACCESS  read-write
        STATUS      current
        DESCRIPTION
            "Log host of the cluster, which can only be configured and accessed on
            the administrator switch."
        ::= { ibClusterObject 13 }

--
-- TABLE: Group member table
--

    ibhgmpGrpMemberTable OBJECT-TYPE
        SYNTAX      SEQUENCE OF IbHgmpGrpMemberEntry
        MAX-ACCESS  not-accessible
        STATUS      current
        DESCRIPTION
            "Table of cluster member switches"
        ::= { ibClusterObject 14 }

    ibhgmpGrpMemberEntry OBJECT-TYPE
        SYNTAX      IbHgmpGrpMemberEntry
        MAX-ACCESS  not-accessible
        STATUS      current
        DESCRIPTION
            ""
        INDEX
            {
                ibhgmpGrpMemberDeviceId
            }
        ::= { ibhgmpGrpMemberTable 1 }

    IbHgmpGrpMemberEntry ::=
        SEQUENCE
            {
                ibhgmpGrpMemberDeviceId       OCTET STRING,
                ibhgmpGrpMemberSerial         Integer32,
                ibhgmpGrpMemberIpAddr         IpAddress,
                ibhgmpGrpMemberName           OCTET STRING,
                ibhgmpGrpMemberPassword       OCTET STRING,
                ibhgmpGrpMemberPlatform       OCTET STRING,
                ibhgmpGrpMemberStatus         INTEGER,
                ibhgmpGrpMemberDisconCount    Integer32,
                ibhgmpGrpMemberEnrollTime     Integer32,
                ibhgmpGrpMemberOperate        RowStatus
            }

    ibhgmpGrpMemberDeviceId OBJECT-TYPE
        SYNTAX      OCTET STRING(SIZE(0..10))
        MAX-ACCESS  read-only
        STATUS      current
        DESCRIPTION
            "4 bytes reserved as 0x0 + 6 bytes of MAC address, expressed as
            a character string of the hexadecimal number."
        ::= { ibhgmpGrpMemberEntry 1 }

    ibhgmpGrpMemberSerial OBJECT-TYPE
        SYNTAX      Integer32(0..2047)
        MAX-ACCESS  read-only
        STATUS      current
        DESCRIPTION
            "When adding member switch to the cluster, the administrator switch
            will assign an unique integer to identify it."
        ::= { ibhgmpGrpMemberEntry 2 }

    ibhgmpGrpMemberIpAddr OBJECT-TYPE
        SYNTAX      IpAddress
        MAX-ACCESS  read-only
        STATUS      current
        DESCRIPTION
            "The private IP addresses of the member switches for the communication
            inside the cluster."
        ::= { ibhgmpGrpMemberEntry 3 }

    ibhgmpGrpMemberName OBJECT-TYPE
        SYNTAX      OCTET STRING(SIZE(0..32))
        MAX-ACCESS  read-only
        STATUS      current
        DESCRIPTION
            "Hostname of the member switch"
        ::= { ibhgmpGrpMemberEntry 4 }

    ibhgmpGrpMemberPassword OBJECT-TYPE
        SYNTAX      OCTET STRING
        MAX-ACCESS  read-write
        STATUS      current
        DESCRIPTION
            "Member password for joining a cluster"
        ::= { ibhgmpGrpMemberEntry 5 }

    ibhgmpGrpMemberPlatform OBJECT-TYPE
        SYNTAX      OCTET STRING
        MAX-ACCESS  read-only
        STATUS      current
        DESCRIPTION
            "Set the hardware platform. A null string indicates the information
            does not exist in the device adjacency table."
        ::= { ibhgmpGrpMemberEntry 6 }

    ibhgmpGrpMemberStatus OBJECT-TYPE
        SYNTAX      INTEGER
            {
                normal(0),
                fault(1)
            }
        MAX-ACCESS  read-only
        STATUS      current
        DESCRIPTION
            "Member status on the administrator switch, use for displaying the
            network management status."
        DEFVAL { fault }
        ::= { ibhgmpGrpMemberEntry 7 }

    ibhgmpGrpMemberDisconCount OBJECT-TYPE
        SYNTAX      Integer32
        MAX-ACCESS  read-only
        STATUS      current
        DESCRIPTION
            "Count of inside communication disconnection between the member switch
            and the administrator switch."
        ::= { ibhgmpGrpMemberEntry 8 }

    ibhgmpGrpMemberEnrollTime OBJECT-TYPE
        SYNTAX      Integer32
        MAX-ACCESS  read-only
        STATUS      current
        DESCRIPTION
            "Enrollment time of the member, measured in seconds."
        ::= { ibhgmpGrpMemberEntry 9 }

    ibhgmpGrpMemberOperate OBJECT-TYPE
        SYNTAX      RowStatus
        MAX-ACCESS  read-write
        STATUS      current
        DESCRIPTION
            "Operation indication field, indicates the operation of adding/removing
            a member by the network management agent."
        ::= { ibhgmpGrpMemberEntry 10 }

--
-- TABLE: Member reset table
--

    ibhgmpMemberResetTable OBJECT-TYPE
        SYNTAX      SEQUENCE OF IbHgmpMemberResetEntry
        MAX-ACCESS  not-accessible
        STATUS      current
        DESCRIPTION
            "Reset a member switch in the cluster."
        ::= { ibClusterObject 15 }

    ibhgmpMemberResetEntry OBJECT-TYPE
        SYNTAX      IbHgmpMemberResetEntry
        MAX-ACCESS  not-accessible
        STATUS      current
        DESCRIPTION
            ""
        INDEX
            {
                ibhgmpMemberResetMAC
            }
        ::= { ibhgmpMemberResetTable 1 }

    IbHgmpMemberResetEntry ::=
        SEQUENCE
            {
                ibhgmpMemberResetMAC      OCTET STRING,
                ibhgmpMemberEraseflash    INTEGER
            }

    ibhgmpMemberResetMAC OBJECT-TYPE
        SYNTAX      OCTET STRING(SIZE(0..6))
        MAX-ACCESS  read-only
        STATUS      current
        DESCRIPTION
            "The management MAC address of the switch to be reset, which is the
            unique identifier of the switch."
        ::= { ibhgmpMemberResetEntry  1 }

    ibhgmpMemberEraseflash OBJECT-TYPE
        SYNTAX      INTEGER
            {
                noErase(0),
                erase(1),
                cannotget(65535)
            }
        MAX-ACCESS  read-write
        STATUS      current
        DESCRIPTION
            "Whether to erase the configuration file from the flash after
            resetting the switch. Read this node, cannotget(65535) will be
            returned."
        ::= { ibhgmpMemberResetEntry  2 }

    ibhgmpEventsV2 OBJECT-IDENTITY
        STATUS      current
        DESCRIPTION
            "Definition point for cluster notifications."
        ::= { ibClusterObject 0 }

    ibhgmpMemberfailure NOTIFICATION-TYPE
        OBJECTS
            {
                ibhgmpGrpMemberDeviceId
            }
        STATUS      current
        DESCRIPTION
            "When a cluster member failure, send a snmp trap to the network
            management."
        ::= { ibhgmpEventsV2 1 }

    ibhgmpMemberRecover NOTIFICATION-TYPE
        OBJECTS
            {
                ibhgmpGrpMemberDeviceId
            }
        STATUS      current
        DESCRIPTION
            "When a cluster member recover, send a snmp trap to the network
            management."
        ::= { ibhgmpEventsV2 2 }

    ibhgmpMemberStatusChange NOTIFICATION-TYPE
        OBJECTS
            {
                ibhgmpGrpMemberDeviceId,
                ibhgmpNTDPCacheClusterRole
            }
        STATUS      current
        DESCRIPTION
            "When a cluster member status change, send a snmp trap to the
            network management."
        ::= { ibhgmpEventsV2 3 }

    ibhgmpNetTopChange NOTIFICATION-TYPE
        STATUS      current
        DESCRIPTION
            "When net topology of this cluster change, send a snmp trap
            to the network management."
        ::= { ibhgmpEventsV2 4 }

    ibhgmpClusterRole OBJECT-TYPE
        SYNTAX      INTEGER
            {
                roleCMDSW(1),
                roleMEMBERSW(2),
                roleBAKSW(3),
                roleCASW(16),
                roleUNISW(17)
            }
        MAX-ACCESS  read-only
        STATUS      current
        DESCRIPTION
            "This switch's role in cluster."
        DEFVAL { roleUNISW }
        ::= { ibClusterObject 16 }

    ibhgmpClusterMaxPoolNum OBJECT-TYPE
        SYNTAX      INTEGER
        MAX-ACCESS  read-only
        STATUS      current
        DESCRIPTION
            "Max switch members that the cluster can support(include
            administrator switch)."
        ::= { ibClusterObject 17 }

    ibhgmpClusterCmdSwMac OBJECT-TYPE
        SYNTAX      OCTET STRING(SIZE(0..6))
        MAX-ACCESS  read-only
        STATUS      current
        DESCRIPTION
            "The MAC address of administrator switch. It will be filled with
            zero when not be a member of cluster."
        ::= { ibClusterObject 18 }

    ibhgmpRun OBJECT-TYPE
        SYNTAX      INTEGER
            {
                false(0),
                true(1)
            }
        MAX-ACCESS  read-write
        STATUS      current
        DESCRIPTION
            "Enable cluster on this switch."
        DEFVAL { true }
        ::= { ibClusterObject 19 }

--
-- cluster protocol MAC
--

    ibhgmpProtocolMac OBJECT IDENTIFIER ::= { ibClusterObject 22 }

    ibhgmpClusterProtocolMac OBJECT-TYPE
        SYNTAX      MacAddress
        MAX-ACCESS  read-write
        STATUS      current
        DESCRIPTION
            "Protocol MAC of HGMP protocol family. All multicast packets of this
            protocol family use this MAC as destination MAC."
        DEFVAL { '0180C200000A'H }
        ::= { ibhgmpProtocolMac 1 }

--
-- ibhgmp topology management
--

    ibhgmpTopologyManagement OBJECT IDENTIFIER ::= { ibClusterObject 23 }

--
-- TABLE: Whitelist Table
--

    ibhgmpWhitelistTable OBJECT-TYPE
        SYNTAX      SEQUENCE OF IbHgmpWhitelistEntry
        MAX-ACCESS  not-accessible
        STATUS      current
        DESCRIPTION
            "Cluster switches white list table. White list topology is the
            topology which has been affirmed by network administrator in a
            cluster, and all devices in white list topology are recorded in this
            table. Against to white list table, black list table records the
            devices which are denied to join in cluster. Adding a black list
            device to white list table will cause a failure."
        ::= { ibhgmpTopologyManagement 1 }

    ibhgmpWhitelistEntry OBJECT-TYPE
        SYNTAX      IbHgmpWhitelistEntry
        MAX-ACCESS  not-accessible
        STATUS      current
        DESCRIPTION
            "Entry items"
        INDEX
            {
                ibhgmpWhitelistDeviceId
            }
        ::= { ibhgmpWhitelistTable 1 }

    IbHgmpWhitelistEntry ::=
        SEQUENCE
            {
                ibhgmpWhitelistDeviceId     OCTET STRING,
                ibhgmpWhitelistSerial       Integer32,
                ibhgmpWhitelistRowStatus    RowStatus
            }

    ibhgmpWhitelistDeviceId OBJECT-TYPE
        SYNTAX      OCTET STRING(SIZE(10))
        MAX-ACCESS  not-accessible
        STATUS      current
        DESCRIPTION
            "Unique identifier indicating a white list switch. Value format of the
            this object is 'XXXXYYYYYY', in which 'XXXX' is reserved as 4 bytes of
            0x0, 'YYYYYY' is a MAC address.
            For example, if the MAC is 000f-e459-000a, the value of this object is
            an octet string: '00' '00' '00' '00' '00' '0f' 'e4' '59' '00' '0a'."
        ::= { ibhgmpWhitelistEntry  1 }

    ibhgmpWhitelistSerial OBJECT-TYPE
        SYNTAX      Integer32(0..2047 | 65535)
        MAX-ACCESS  read-only
        STATUS      current
        DESCRIPTION
            "When adding member switch to the cluster, the administrator switch
            will assign an unique integer to identify it. 0xffff means invalid
            value for this object."
        ::= { ibhgmpWhitelistEntry  2 }

    ibhgmpWhitelistRowStatus OBJECT-TYPE
        SYNTAX      RowStatus
        MAX-ACCESS  read-create
        STATUS      current
        DESCRIPTION
            "The row status of this table."
        ::= { ibhgmpWhitelistEntry 3 }

--
-- TABLE: Whitelist neighbor table
--

    ibhgmpWhitelistNbTable OBJECT-TYPE
        SYNTAX      SEQUENCE OF IbHgmpWhitelistNbEntry
        MAX-ACCESS  not-accessible
        STATUS      current
        DESCRIPTION
            "Cluster switches white list neighboring information table. White
            list neighbor table records all neighbor devices for every white
            list device. In fact, white list neighbor table displays the whole
            white list topology."
        ::= { ibhgmpTopologyManagement 2 }

    ibhgmpWhitelistNbEntry OBJECT-TYPE
        SYNTAX      IbHgmpWhitelistNbEntry
        MAX-ACCESS  not-accessible
        STATUS      current
        DESCRIPTION
            "Entry items"
        INDEX
            {
                ibhgmpWhitelistDeviceId,
                ibhgmpWhitelistNbIndex
            }
        ::= { ibhgmpWhitelistNbTable 1 }

    IbHgmpWhitelistNbEntry ::=
        SEQUENCE
            {
                ibhgmpWhitelistNbIndex       Integer32,
                ibhgmpWhitelistNbDeviceId    OCTET STRING,
                ibhgmpWhitelistPortName      OCTET STRING,
                ibhgmpWhitelistNbPortName    OCTET STRING
            }

    ibhgmpWhitelistNbIndex OBJECT-TYPE
        SYNTAX      Integer32(1..65535)
        MAX-ACCESS  not-accessible
        STATUS      current
        DESCRIPTION
            "Index of a switch which is the neighbor of a white list switch
            identified by 'hgmpWhitelistDeviceId'."
        ::= { ibhgmpWhitelistNbEntry  1 }

    ibhgmpWhitelistNbDeviceId OBJECT-TYPE
        SYNTAX      OCTET STRING(SIZE(10))
        MAX-ACCESS  read-only
        STATUS      current
        DESCRIPTION
            "Unique identifier indicating a neighbor switch of a white list
            switch. Value format of the this object is 'XXXXYYYYYY', in which
            'XXXX' is reserved as 4 bytes of 0x0, 'YYYYYY' is a MAC address.
            For example, if the MAC is 000f-e459-000a, the value of this object
            is an octet string: '00' '00' '00' '00' '00' '0f' 'e4' '59' '00' '0a'."
        ::= { ibhgmpWhitelistNbEntry  2 }

    ibhgmpWhitelistPortName OBJECT-TYPE
        SYNTAX      OCTET STRING(SIZE(0..47))
        MAX-ACCESS  read-only
        STATUS      current
        DESCRIPTION
            "The name of the port which a white list switch connects to the
            neighbor specified by 'hgmpWhitelistNbIndex'."
        ::= { ibhgmpWhitelistNbEntry  3 }

    ibhgmpWhitelistNbPortName OBJECT-TYPE
        SYNTAX      OCTET STRING(SIZE(0..47))
        MAX-ACCESS  read-only
        STATUS      current
        DESCRIPTION
            "The name of the port which a neighbor device connects to the white
            list switch specified by 'hgmpWhitelistDeviceId'."
        ::= { ibhgmpWhitelistNbEntry  4 }

--
-- TABLE: Blacklist table
--

    ibhgmpBlacklistTable OBJECT-TYPE
        SYNTAX      SEQUENCE OF IbHgmpBlacklistEntry
        MAX-ACCESS  not-accessible
        STATUS      current
        DESCRIPTION
            "Cluster switches black list table. The black list table records all
            black list devices, and a device in black list is not permitted to
            join in any cluster."
        ::= { ibhgmpTopologyManagement 3 }

    ibhgmpBlacklistEntry OBJECT-TYPE
        SYNTAX      IbHgmpBlacklistEntry
        MAX-ACCESS  not-accessible
        STATUS      current
        DESCRIPTION
            "Entry items"
        INDEX
            {
                ibhgmpBlacklistDeviceId
            }
        ::= { ibhgmpBlacklistTable 1 }

    IbHgmpBlacklistEntry ::=
        SEQUENCE
            {
                ibhgmpBlacklistDeviceId         OCTET STRING,
                ibhgmpBlacklistAccessDeviceId   OCTET STRING,
                ibhgmpBlacklistAccessPortName   OCTET STRING,
                ibhgmpBlacklistRowStatus        RowStatus
            }

    ibhgmpBlacklistDeviceId OBJECT-TYPE
        SYNTAX      OCTET STRING(SIZE(10))
        MAX-ACCESS  not-accessible
        STATUS      current
        DESCRIPTION
            "Unique identifier indicating a black list switch. Value format of the
            this object is 'XXXXYYYYYY', in which 'XXXX' is reserved as 4 bytes
            of 0x0, 'YYYYYY' is a MAC address.
            For example, if the MAC is 000f-e459-000a, the value of this object is
            an octet string: '00' '00' '00' '00' '00' '0f' 'e4' '59' '00' '0a'."
        ::= { ibhgmpBlacklistEntry  1 }

    ibhgmpBlacklistAccessDeviceId OBJECT-TYPE
        SYNTAX      OCTET STRING(SIZE(10))
        MAX-ACCESS  read-only
        STATUS      current
        DESCRIPTION
            "Unique identifier indicating the access device of a black list switch.
            Tracing from a black list device to the cluster commander switch, the
            device which the black list switch directly connects to is the access
            device.
            Value format of the this object is 'XXXXYYYYYY', in which 'XXXX' is
            reserved as 4 bytes of 0x0, 'YYYYYY' is a MAC address. 10 bytes of 0xff
            means invalid value for this object.
            For example, if the MAC is 000f-e459-000a, the value of this object is
            an octet string: '00' '00' '00' '00' '00' '0f' 'e4' '59' '00' '0a'."
        ::= { ibhgmpBlacklistEntry  2 }

    ibhgmpBlacklistAccessPortName OBJECT-TYPE
        SYNTAX      OCTET STRING(SIZE(0..47))
        MAX-ACCESS  read-only
        STATUS      current
        DESCRIPTION
            "The port which the access device connecting to the black list switch
            is named access port, the object returns the access port name.
            An empty string means invalid value for this object."
        ::= { ibhgmpBlacklistEntry  3 }

    ibhgmpBlacklistRowStatus OBJECT-TYPE
        SYNTAX      RowStatus
        MAX-ACCESS  read-create
        STATUS      current
        DESCRIPTION
            "The row status of this table."
        ::= { ibhgmpBlacklistEntry 4 }

--
-- TABLE: Member private port number table
--

    ibhgmpMemberPriPortTable OBJECT-TYPE
        SYNTAX      SEQUENCE OF IbHgmpMemberPriPortEntry
        MAX-ACCESS  not-accessible
        STATUS      current
        DESCRIPTION
            "This table contains port number for different network protocols
            on each member switch. The port number can be used to access
            a specified member switch with specified protocol and private
            IP address."
        ::= { ibClusterObject 24 }

    ibhgmpMemberPriPortEntry OBJECT-TYPE
        SYNTAX      IbHgmpMemberPriPortEntry
        MAX-ACCESS  not-accessible
        STATUS      current
        DESCRIPTION
            "Information about a specified member private port entry. The
            indexes of the entry are ibhgmpGrpMemberDevId and
            ibhgmpMemberPriPortProto, which indicate entries in the table."
        INDEX
            {
                ibhgmpMemberDevId,
                ibhgmpMemberPriPortProto
            }
        ::= { ibhgmpMemberPriPortTable 1 }

    IbHgmpMemberPriPortEntry ::=
        SEQUENCE
            {
                ibhgmpMemberDevId                OCTET STRING,
                ibhgmpMemberPriPortProto         Unsigned32,
                ibhgmpMemberPriPortProtoDescr    DisplayString,
                ibhgmpMemberPriPortNum           Unsigned32
            }

    ibhgmpMemberDevId OBJECT-TYPE
        SYNTAX      OCTET STRING(SIZE(0..10))
        MAX-ACCESS  read-only
        STATUS      current
        DESCRIPTION
            "Unique identifier indicating the switch in cluster.
            Value format of the this object is 'XXXXYYYYYY', in which 'XXXX' is
            is reserved as 4 bytes of 0x0, 'YYYYYY' is a MAC address."
        ::= { ibhgmpMemberPriPortEntry 1 }

    ibhgmpMemberPriPortProto OBJECT-TYPE
        SYNTAX      Unsigned32
        MAX-ACCESS  not-accessible
        STATUS      current
        DESCRIPTION
            "The index of this table. Each instance value of this object
            corresponds to a different protocol."
        ::= { ibhgmpMemberPriPortEntry 2 }

    ibhgmpMemberPriPortProtoDescr OBJECT-TYPE
        SYNTAX      DisplayString
        MAX-ACCESS  read-only
        STATUS      current
        DESCRIPTION
            "It describes the ibhgmpMemberPriPortProtocol object value.
            For example, it is 'SNMP' when ibhgmpMemberPriPortProtocol value
            is 1."
        ::= { ibhgmpMemberPriPortEntry 3 }

    ibhgmpMemberPriPortNum OBJECT-TYPE
        SYNTAX      Unsigned32
        MAX-ACCESS  read-only
        STATUS      current
        DESCRIPTION
            "The private port number of member switch, used by specified
            ibhgmpMemberPriPortProto. By using the private IP address,
            specified protocol and port number, other devices outside
            cluster can access member switch. The private IP address
            can be acquired by reading ibhgmpGrpMemberIpAddr."
        ::= { ibhgmpMemberPriPortEntry 4 }

--
-- stack definitions
--

    ibStackObject OBJECT-IDENTITY
        STATUS      current
        DESCRIPTION
            "This MIB contains objects to manage the stack operations, which is
            used on lanswitch products."
        ::= { ibHgmp 2 }

    ibhgmpStackMemberTableChange OBJECT-TYPE
        SYNTAX      Integer32(0..65535)
        MAX-ACCESS  read-only
        STATUS      current
        DESCRIPTION
            "Change identifier of the stack member table."
        DEFVAL { 0 }
        ::= { ibStackObject 1 }

    ibhgmpStackMemberDisconRate OBJECT-TYPE
        SYNTAX      Integer32
        MAX-ACCESS  read-only
        STATUS      current
        DESCRIPTION
            "Disconnection rate of the stack member switches."
        DEFVAL { 0 }
        ::= { ibStackObject 2 }

    ibhgmpMainLanswitchFlag OBJECT-TYPE
        SYNTAX      INTEGER
            {
                false(0),
                true(1)
            }
        MAX-ACCESS  read-write
        STATUS      current
        DESCRIPTION
            "The status of the local switch in the stack."
        DEFVAL { false }
        ::= { ibStackObject 3 }

    ibhgmpStackIpPoolStartIP OBJECT-TYPE
        SYNTAX      IpAddress
        MAX-ACCESS  read-write
        STATUS      current
        DESCRIPTION
            "The first address of the management IP network segment assigned by
            the master switch, which cannot be modified in the case that there
            is IP address assignment."
        ::= { ibStackObject 4 }

    ibhgmpStackIpPoolLength OBJECT-TYPE
        SYNTAX      INTEGER(1..200)
        MAX-ACCESS  read-write
        STATUS      current
        DESCRIPTION
            "The length of the management IP segment assigned by the master
            switch, which cannot be modified in the case that there is IP
            address assignment."
        ::= { ibStackObject 5 }

    ibhgmpStackIpPoolMask OBJECT-TYPE
        SYNTAX      IpAddress
        MAX-ACCESS  read-write
        STATUS      current
        DESCRIPTION
            "The mask of the management IP segment assigned by the master switch,
            which cannot be modified in the case that there is IP address assignment."
        DEFVAL { 'FFFF0000'H }
        ::= { ibStackObject 10 }

--
-- TABLE: Stack member table
--

    ibhgmpStackMemberTable OBJECT-TYPE
        SYNTAX      SEQUENCE OF IbHgmpStackMemberEntry
        MAX-ACCESS  not-accessible
        STATUS      current
        DESCRIPTION
            "Stack member table."
        ::= { ibStackObject 6 }

    ibhgmpStackMemberEntry OBJECT-TYPE
        SYNTAX      IbHgmpStackMemberEntry
        MAX-ACCESS  not-accessible
        STATUS      current
        DESCRIPTION
            ""
        INDEX
            {
                ibhgmpStackMemberDeviceId
            }
        ::= { ibhgmpStackMemberTable 1 }

    IbHgmpStackMemberEntry ::=
        SEQUENCE
        {
            ibhgmpStackMemberDeviceId       OCTET STRING,
            ibhgmpStackMemberSerial         Integer32,
            ibhgmpStackMemberIpAddr         IpAddress,
            ibhgmpStackMemberName           OCTET STRING,
            ibhgmpStackMemberPassword       OCTET STRING,
            ibhgmpStackMemberPlatform       OCTET STRING,
            ibhgmpStackMemberStatus         INTEGER,
            ibhgmpStackMemberDisconCount    Integer32,
            ibhgmpStackMemberEnrollTime     Integer32
        }

    ibhgmpStackMemberDeviceId OBJECT-TYPE
        SYNTAX      OCTET STRING(SIZE(0..10))
        MAX-ACCESS  read-only
        STATUS      current
        DESCRIPTION
            "2 bytes address type of the switch + 2 bytes zero + MAC address,
            expressed as a hexadecimal number string."
        ::= { ibhgmpStackMemberEntry 1 }

    ibhgmpStackMemberSerial OBJECT-TYPE
        SYNTAX      Integer32(0..2047)
        MAX-ACCESS  read-only
        STATUS      current
        DESCRIPTION
            "When adding a member switch to the stack, the master switch will
            assign an unique integer to identify it."
        ::= { ibhgmpStackMemberEntry 2 }

    ibhgmpStackMemberIpAddr OBJECT-TYPE
        SYNTAX      IpAddress
        MAX-ACCESS  read-only
        STATUS      current
        DESCRIPTION
            "The private member IP address for the communication inside the stack."
        ::= { ibhgmpStackMemberEntry 3 }

    ibhgmpStackMemberName OBJECT-TYPE
        SYNTAX      OCTET STRING
        MAX-ACCESS  read-only
        STATUS      current
        DESCRIPTION
            "Hostname of the member switch."
        ::= { ibhgmpStackMemberEntry 4 }

    ibhgmpStackMemberPassword OBJECT-TYPE
        SYNTAX      OCTET STRING
        MAX-ACCESS  read-only
        STATUS      current
        DESCRIPTION
            "Member password for joining a stack."
        ::= { ibhgmpStackMemberEntry 5 }

    ibhgmpStackMemberPlatform OBJECT-TYPE
        SYNTAX      OCTET STRING
        MAX-ACCESS  read-only
        STATUS      current
        DESCRIPTION
            "Set the hardware platform. A null string indicates the information
            does not exist in the device adjacency table."
        ::= { ibhgmpStackMemberEntry 6 }

    ibhgmpStackMemberStatus OBJECT-TYPE
        SYNTAX      INTEGER
            {
                normal(0),
                fault(1)
            }
        MAX-ACCESS  read-only
        STATUS      current
        DESCRIPTION
            "Member status on the master switch, use for displaying the network
            management status."
        DEFVAL { fault }
        ::= { ibhgmpStackMemberEntry 7 }

    ibhgmpStackMemberDisconCount OBJECT-TYPE
        SYNTAX      Integer32
        MAX-ACCESS  read-only
        STATUS      current
        DESCRIPTION
            "Count of inside communication disconnection between the member switch
            and the master switch."
        ::= { ibhgmpStackMemberEntry 8 }

    ibhgmpStackMemberEnrollTime OBJECT-TYPE
        SYNTAX      Integer32
        MAX-ACCESS  read-only
        STATUS      current
        DESCRIPTION
            "Enrollment time of the member, measured in seconds."
        ::= { ibhgmpStackMemberEntry 9 }

    ibhgmpStackRole OBJECT-TYPE
        SYNTAX      INTEGER
            {
                roleCMDSW(1),
                roleMEMBERSW(2),
                roleBAKSW(3),
                roleCASW(16),
                roleUNISW(17)
            }
        MAX-ACCESS  read-only
        STATUS      current
        DESCRIPTION
            "This switch's role status in stack."
        DEFVAL { roleUNISW }
        ::= { ibStackObject 7 }

    ibhgmpStackMaxPoolNum OBJECT-TYPE
        SYNTAX      INTEGER
        MAX-ACCESS  read-only
        STATUS      current
        DESCRIPTION
            "Max switch members in one stack that the switch support (include
            main switch)."
        ::= { ibStackObject 8 }

    ibhgmpStackMainSwMac OBJECT-TYPE
        SYNTAX      OCTET STRING(SIZE(0..6))
        MAX-ACCESS  read-only
        STATUS      current
        DESCRIPTION
            "The MAC address of main switch. It will be 00.00.00 when not be a
            member of stack."
        ::= { ibStackObject 9 }

--
-- Neighbor protocol objects
--

    ibNDPObject OBJECT-IDENTITY
        STATUS      current
        DESCRIPTION
            "This MIB contains objects to manage the ndp operations, which are
            used on lanswitch products."
        ::= { ibHgmp 5 }

    ibNDPStatus OBJECT-TYPE
        SYNTAX      INTEGER
            {
                disable(0),
                enable(1)
            }
        MAX-ACCESS  read-write
        STATUS      current
        DESCRIPTION
            "NDP protocol module enable flag"
        DEFVAL { enable }
        ::= { ibNDPObject 1 }

    ibNDPHelloTimer OBJECT-TYPE
        SYNTAX      Integer32 (5..254)
        MAX-ACCESS  read-write
        STATUS      current
        DESCRIPTION
            "NDP packet transmission interval, measured in seconds."
        DEFVAL { 60 }
        ::= { ibNDPObject 2 }

    ibNDPAgingTime OBJECT-TYPE
        SYNTAX      Integer32(5..255)
        MAX-ACCESS  read-write
        STATUS      current
        DESCRIPTION
            "How long the NDP information of the local switch can be hold in
            the adjacent switch, measured in seconds."
        DEFVAL { 180 }
        ::= { ibNDPObject 3 }

    ibNDPChange OBJECT-TYPE
        SYNTAX      Counter32
        MAX-ACCESS  read-only
        STATUS      current
        DESCRIPTION
            "Change identifier of the Neighbor table"
        DEFVAL { 0 }
        ::= { ibNDPObject 4 }

    ibNDPPortTable OBJECT-TYPE
        SYNTAX      SEQUENCE OF IbNDPPortEntry
        MAX-ACCESS  not-accessible
        STATUS      current
        DESCRIPTION
            "Configure to enable/disable the interface NDP of the switch."
        ::= { ibNDPObject 5 }

    ibNDPPortEntry OBJECT-TYPE
        SYNTAX      IbNDPPortEntry
        MAX-ACCESS  not-accessible
        STATUS      current
        DESCRIPTION
            ""
        INDEX
            {
                ibNDPIfIndex
            }
        ::= { ibNDPPortTable 1 }

    IbNDPPortEntry ::=
        SEQUENCE
            {
                ibNDPIfIndex       Integer32,
                ibNDPPortStatus    INTEGER
            }

    ibNDPIfIndex OBJECT-TYPE
        SYNTAX      Integer32
        MAX-ACCESS  read-only
        STATUS      current
        DESCRIPTION
            "Unique identifier of an interface of the device."
        ::= { ibNDPPortEntry 1 }

    ibNDPPortStatus OBJECT-TYPE
        SYNTAX      INTEGER
            {
                disable(0),
                enable(1)
            }
        MAX-ACCESS  read-write
        STATUS      current
        DESCRIPTION
            "If it is enable, the device will send and receive the NDP
            packets via the interface. To disable the NDP function on the
            interface, set the entry as false."
        DEFVAL { enable }
        ::= { ibNDPPortEntry 2 }

    ibNDPPortNbTable OBJECT-TYPE
        SYNTAX      SEQUENCE OF IbNDPPortNbEntry
        MAX-ACCESS  not-accessible
        STATUS      current
        DESCRIPTION
            "NDP neighbor information on the switch."
        ::= { ibNDPObject 6 }

    ibNDPPortNbEntry OBJECT-TYPE
        SYNTAX      IbNDPPortNbEntry
        MAX-ACCESS  not-accessible
        STATUS      current
        DESCRIPTION
            ""
        INDEX
            {
                ibNDPIfIndex,
                ibNDPPortNbDeviceId,
                ibNDPPortNbPortName
            }
        ::= { ibNDPPortNbTable 1 }

    IbNDPPortNbEntry ::=
        SEQUENCE
            {
                ibNDPPortNbDeviceId      OCTET STRING,
                ibNDPPortNbPortName      OCTET STRING,
                ibNDPPortNbDeviceName    OCTET STRING,
                ibNDPPortNbPortMode      INTEGER,
                ibNDPPortNbProductVer    OCTET STRING,
                ibNDPPortNbHardVer       OCTET STRING,
                ibNDPPortNbBootromVer    OCTET STRING,
                ibNDPPortNbSoftVer       OCTET STRING,
                ibNDPPortNbAgingtime     Integer32
            }

    ibNDPPortNbDeviceId OBJECT-TYPE
        SYNTAX      OCTET STRING(SIZE(0..10))
        MAX-ACCESS  read-only
        STATUS      current
        DESCRIPTION
            "2 bytes address type of the member switch + 2 bytes zero + MAC
            address, expressed as a character string of the hexadecimal
            number."
        ::= { ibNDPPortNbEntry 1 }

    ibNDPPortNbPortName OBJECT-TYPE
        SYNTAX      OCTET STRING(SIZE(0..47))
        MAX-ACCESS  read-only
        STATUS      current
        DESCRIPTION
            "Unique identifier of a port. A null string indicates that the
            field was not included in in the latest NDP packet. Interface
            type + card number / slot number / sequence number."
        ::= { ibNDPPortNbEntry 2 }

    ibNDPPortNbDeviceName OBJECT-TYPE
        SYNTAX      OCTET STRING
        MAX-ACCESS  read-only
        STATUS      current
        DESCRIPTION
            "Device name. A null string indicates that the field was not
            included in the latest NDP packet."
        ::= { ibNDPPortNbEntry 3 }

    ibNDPPortNbPortMode OBJECT-TYPE
        SYNTAX      INTEGER
            {
                full(1),
                half(2),
                auto(3)
            }
        MAX-ACCESS  read-only
        STATUS      current
        DESCRIPTION
            "The neighbor port duplex mode."
        ::= { ibNDPPortNbEntry 4 }

    ibNDPPortNbProductVer OBJECT-TYPE
        SYNTAX      OCTET STRING
        MAX-ACCESS  read-only
        STATUS      current
        DESCRIPTION
            "Product version. A null string indicates that the field was
            not included in the latest NDP packet."
        ::= { ibNDPPortNbEntry 5 }

    ibNDPPortNbHardVer OBJECT-TYPE
        SYNTAX      OCTET STRING
        MAX-ACCESS  read-only
        STATUS      current
        DESCRIPTION
            "Hardware version. A null string indicates that the field was
            not included in the latest NDP packet."
        ::= { ibNDPPortNbEntry 6 }

    ibNDPPortNbBootromVer OBJECT-TYPE
        SYNTAX      OCTET STRING
        MAX-ACCESS  read-only
        STATUS      current
        DESCRIPTION
            "Bootrom version. A null string indicates that the field was
            not included in the latest NDP packet."
        ::= { ibNDPPortNbEntry 7 }

    ibNDPPortNbSoftVer OBJECT-TYPE
        SYNTAX      OCTET STRING
        MAX-ACCESS  read-only
        STATUS      current
        DESCRIPTION
            "Software version. A null string indicates that the field was
            not included in the latest NDP packet."
        ::= { ibNDPPortNbEntry 8 }

    ibNDPPortNbAgingtime OBJECT-TYPE
        SYNTAX      Integer32 (5..255)
        MAX-ACCESS  read-only
        STATUS      current
        DESCRIPTION
            "How long the NDP information of the local switch can be hold
            in the adjacent switch, measured in seconds."
        ::= { ibNDPPortNbEntry 9 }

--
-- NTDP management objects
--

    ibNTDPObject OBJECT-IDENTITY
        STATUS      current
        DESCRIPTION
            "This MIB contains objects to manage the ntdp operations, which
            are used on lanswitch products."
        ::= { ibHgmp 4 }

    ibhgmpNTDPCollectTopTime OBJECT-TYPE
        SYNTAX      Integer32 (0..65535)
        MAX-ACCESS  read-write
        STATUS      current
        DESCRIPTION
            "Topology collection interval of the administrator switch of
            the cluster, measured in minutes."
        DEFVAL { 0 }
        ::= { ibNTDPObject 1 }

    ibhgmpNTDPHopRange OBJECT-TYPE
        SYNTAX      Integer32 (1..16)
        MAX-ACCESS  read-write
        STATUS      current
        DESCRIPTION
            "Range of the topology collection of the administrator switch"
        DEFVAL { 3 }
        ::= { ibNTDPObject 2 }

    ibhgmpNTDPRun OBJECT-TYPE
        SYNTAX      INTEGER
            {
                false(0),
                true(1)
            }
        MAX-ACCESS  read-write
        STATUS      current
        DESCRIPTION
            "Enable/Disable the NTDP function on the switch."
        DEFVAL { true }
        ::= { ibNTDPObject 3 }

    ibhgmpNTDPPortDelay OBJECT-TYPE
        SYNTAX      Integer32 (1..100)
        MAX-ACCESS  read-write
        STATUS      current
        DESCRIPTION
            "Set the delay to forward the topology request via the ports,
            measured in milliseconds."
        DEFVAL { 20 }
        ::= { ibNTDPObject 4 }

    ibhgmpNTDPHopDelay OBJECT-TYPE
        SYNTAX      Integer32 (1..1000)
        MAX-ACCESS  read-write
        STATUS      current
        DESCRIPTION
            "Set the delay to forward the topology request from every hop,
            measured in milliseconds."
        DEFVAL { 200 }
        ::= { ibNTDPObject 5 }

    ibhgmpNTDPLastTopCollectDuration OBJECT-TYPE
        SYNTAX      Integer32
        MAX-ACCESS  read-only
        STATUS      current
        DESCRIPTION
            "Duration of the latest overall topology collection, a
            performance count measured in seconds."
        DEFVAL { 0 }
        ::= { ibNTDPObject 6 }

    ibhgmpNTDPCacheChange OBJECT-TYPE
        SYNTAX      Integer32 (0..65535)
        MAX-ACCESS  read-only
        STATUS      current
        DESCRIPTION
            "Add 1 when the device table changes. The network administrator
            will check if it has changed before accessing the table. If it
            has not changed, he will not access again."
        DEFVAL { 0 }
        ::= { ibNTDPObject 7 }

    ibhgmpNTDPTOPTableChange OBJECT-TYPE
        SYNTAX      Integer32 (0..65535)
        MAX-ACCESS  read-only
        STATUS      current
        DESCRIPTION
            "Add 1 when the topology table changes. The network
            administrator will check if it has changed before accessing
            the table. If it has not changed, he will not access again."
        DEFVAL { 0 }
        ::= { ibNTDPObject 8 }

    ibhgmpNTDPInterfaceTable OBJECT-TYPE
        SYNTAX      SEQUENCE OF IbHgmpNTDPInterfaceEntry
        MAX-ACCESS  not-accessible
        STATUS      current
        DESCRIPTION
            "Enable/Disable the NTDP on the switch port."
        ::= { ibNTDPObject 9 }

    ibhgmpNTDPInterfaceEntry OBJECT-TYPE
        SYNTAX      IbHgmpNTDPInterfaceEntry
        MAX-ACCESS  not-accessible
        STATUS      current
        DESCRIPTION
            ""
        INDEX
            {
                ibhgmpNTDPInterfaceIfIndex
            }
        ::= { ibhgmpNTDPInterfaceTable 1 }

    IbHgmpNTDPInterfaceEntry ::=
        SEQUENCE
            {
                ibhgmpNTDPInterfaceIfIndex    Integer32,
                ibhgmpNTDPInterfaceEnable     INTEGER
            }

    ibhgmpNTDPInterfaceIfIndex OBJECT-TYPE
        SYNTAX      Integer32
        MAX-ACCESS  read-only
        STATUS      current
        DESCRIPTION
            "Unique identifier an interface of the device."
        ::= { ibhgmpNTDPInterfaceEntry 1 }

    ibhgmpNTDPInterfaceEnable OBJECT-TYPE
        SYNTAX      INTEGER
            {
                false(0),
                true(1)
            }
        MAX-ACCESS  read-write
        STATUS      current
        DESCRIPTION
            "If it is true, the device will send and receive the NTDP
            packets via the interface. To disable the NTDP function on the
            interface, set the entry as false."
        DEFVAL { true }
        ::= { ibhgmpNTDPInterfaceEntry 2 }

    ibhgmpNTDPCacheTable OBJECT-TYPE
        SYNTAX      SEQUENCE OF IbHgmpNTDPCacheEntry
        MAX-ACCESS  not-accessible
        STATUS      current
        DESCRIPTION
            "Access the information about the switch from the topology table."
        ::= { ibNTDPObject 10 }

    ibhgmpNTDPCacheEntry OBJECT-TYPE
        SYNTAX      IbHgmpNTDPCacheEntry
        MAX-ACCESS  not-accessible
        STATUS      current
        DESCRIPTION
            ""
        INDEX
            {
                ibhgmpNTDPCacheHashIndex,
                ibhgmpNTDPCacheDeviceID
            }
        ::= { ibhgmpNTDPCacheTable 1 }

    IbHgmpNTDPCacheEntry ::=
        SEQUENCE
            {
                ibhgmpNTDPCacheHashIndex       Integer32,
                ibhgmpNTDPCacheDeviceID        OCTET STRING,
                ibhgmpNTDPCacheClusterName     OCTET STRING,
                ibhgmpNTDPCacheClusterRole     INTEGER,
                ibhgmpNTDPCacheCapabilities    INTEGER,
                ibhgmpNTDPCacheVersion         OCTET STRING,
                ibhgmpNTDPCachePlatform        OCTET STRING,
                ibhgmpNTDPCacheMngVLAN         INTEGER,
                ibhgmpNTDPCacheHop             INTEGER
            }

    ibhgmpNTDPCacheHashIndex OBJECT-TYPE
        SYNTAX      Integer32 (0..255)
        MAX-ACCESS  read-only
        STATUS      current
        DESCRIPTION
            "Our NTDP information is saved in the HASH table on the
            administrator switch. Using DeviceID as index will lead to the
            comparison of a large amount of character strings, which puts
            too many burdens on the administrator switch. A HAHSIndex is
            added to reduce the character string comparison to the
            least range."
        ::= { ibhgmpNTDPCacheEntry 1 }

    ibhgmpNTDPCacheDeviceID OBJECT-TYPE
        SYNTAX      OCTET STRING(SIZE(0..10))
        MAX-ACCESS  read-only
        STATUS      current
        DESCRIPTION
            "2 bytes address type of the member switch + 2 bytes zero + MAC
            address, expressed as a character string of the
            hexadecimal number."
        ::= { ibhgmpNTDPCacheEntry 2 }

    ibhgmpNTDPCacheClusterName OBJECT-TYPE
        SYNTAX      OCTET STRING
        MAX-ACCESS  read-only
        STATUS      current
        DESCRIPTION
            "Name of the cluster including the device."
        ::= { ibhgmpNTDPCacheEntry 3 }

    ibhgmpNTDPCacheClusterRole OBJECT-TYPE
        SYNTAX      INTEGER
            {
                roleCOSW(1),
                roleMSW(2),
                roleBKSW(3),
                roleCASW(16),
                roleUNISW(17)
            }
        MAX-ACCESS  read-only
        STATUS      current
        DESCRIPTION
            "Cluster role of the current device, which can be a
            administrator switch (0x01), member switch(0x02), backup
            switch(0x03), candidate switch(0x10) or an independent
            switch (incapable of cluster member) (0x11)."
        DEFVAL { 17 }
        ::= { ibhgmpNTDPCacheEntry 4 }

    ibhgmpNTDPCacheCapabilities OBJECT-TYPE
        SYNTAX      INTEGER
        MAX-ACCESS  read-only
        STATUS      current
        DESCRIPTION
            "The capabilities of the device. FF indicates that the field
            was not included in in the latest NTDP packet."
        DEFVAL { 255 }
        ::= { ibhgmpNTDPCacheEntry 5 }

    ibhgmpNTDPCacheVersion OBJECT-TYPE
        SYNTAX      OCTET STRING
        MAX-ACCESS  read-only
        STATUS      current
        DESCRIPTION
            "The version information of the corresponding device. A null
            string indicates that the field was not included in in the
            latest NTDP packet."
        ::= { ibhgmpNTDPCacheEntry 6 }

    ibhgmpNTDPCachePlatform OBJECT-TYPE
        SYNTAX      OCTET STRING
        MAX-ACCESS  read-only
        STATUS      current
        DESCRIPTION
            "Hardware platform. A null string indicates that the field
            was not included in the latest NTDP packet."
        ::= { ibhgmpNTDPCacheEntry 7 }

    ibhgmpNTDPCacheMngVLAN OBJECT-TYPE
        SYNTAX      INTEGER
        MAX-ACCESS  read-only
        STATUS      current
        DESCRIPTION
            "The management VLAN ID of the device."
        DEFVAL { 1 }
        ::= { ibhgmpNTDPCacheEntry 8 }

    ibhgmpNTDPCacheHop OBJECT-TYPE
        SYNTAX      INTEGER
        MAX-ACCESS  read-only
        STATUS      current
        DESCRIPTION
            "Hops to this switch."
        ::= { ibhgmpNTDPCacheEntry 9 }

    ibhgmpNTDPTopTable OBJECT-TYPE
        SYNTAX      SEQUENCE OF IbHgmpNTDPTopEntry
        MAX-ACCESS  not-accessible
        STATUS      current
        DESCRIPTION
            "Access the topology structure collected by the NTDP."
        ::= { ibNTDPObject 11 }

    ibhgmpNTDPTopEntry OBJECT-TYPE
        SYNTAX      IbHgmpNTDPTopEntry
        MAX-ACCESS  not-accessible
        STATUS      current
        DESCRIPTION
            ""
        INDEX
            {
                ibhgmpNTDPTopHashIndex,
                ibhgmpNTDPTopEdgeStartDevID,
                ibhgmpNTDPTopEdgeIndex
            }
        ::= { ibhgmpNTDPTopTable 1 }

    IbHgmpNTDPTopEntry ::=
        SEQUENCE
            {
                ibhgmpNTDPTopHashIndex                  Integer32,
                ibhgmpNTDPTopEdgeStartDevID             OCTET STRING,
                ibhgmpNTDPTopEdgeIndex                  Integer32,
                ibhgmpNTDPTopEdgeEndDevID               OCTET STRING,
                ibhgmpNTDPTopEdgeStartPort              OCTET STRING,
                ibhgmpNTDPTopEdgeStartPortFullDuplex    INTEGER,
                ibhgmpNTDPTopEdgeStartPortSpeed         Integer32,
                ibhgmpNTDPTopEdgeEndPort                OCTET STRING,
                ibhgmpNTDPTopLinkStatus                 INTEGER
            }

    ibhgmpNTDPTopHashIndex OBJECT-TYPE
        SYNTAX      Integer32 (0..255)
        MAX-ACCESS  read-only
        STATUS      current
        DESCRIPTION
            "Our NTDP information is saved in the HASH table on the
            administrator switch. Using DeviceID as index will lead to the
            comparison of a large amount of character strings, which puts
            too many burdens on the administrator switch. A HAHSIndex is
            added to reduce the character string comparison to the
            least range."
        ::= { ibhgmpNTDPTopEntry 1 }

    ibhgmpNTDPTopEdgeStartDevID OBJECT-TYPE
        SYNTAX      OCTET STRING(SIZE(0..10))
        MAX-ACCESS  read-only
        STATUS      current
        DESCRIPTION
            "2 bytes address type of the member switch + 2 bytes zero + MAC
            address, expressed as a character string of the hexadecimal number."
        ::= { ibhgmpNTDPTopEntry 2 }

    ibhgmpNTDPTopEdgeIndex OBJECT-TYPE
        SYNTAX      Integer32 (0..65535)
        MAX-ACCESS  read-only
        STATUS      current
        DESCRIPTION
            "Edge index of this entry in the data structure."
        ::= { ibhgmpNTDPTopEntry 3 }

    ibhgmpNTDPTopEdgeEndDevID OBJECT-TYPE
        SYNTAX      OCTET STRING(SIZE(0..10))
        MAX-ACCESS  read-only
        STATUS      current
        DESCRIPTION
            "2 bytes address type of the member switch + 2 bytes zero + MAC
            address, expressed as a character string of the hexadecimal number."
        ::= { ibhgmpNTDPTopEntry 4 }

    ibhgmpNTDPTopEdgeStartPort OBJECT-TYPE
        SYNTAX      OCTET STRING(SIZE(0..47))
        MAX-ACCESS  read-only
        STATUS      current
        DESCRIPTION
            "The number of the first port of a topology edge. Interface
            type + card number / slot number / sequence number."
        ::= { ibhgmpNTDPTopEntry 5 }

    ibhgmpNTDPTopEdgeStartPortFullDuplex OBJECT-TYPE
        SYNTAX      INTEGER
            {
                half(0),
                full(1)
            }
        MAX-ACCESS  read-only
        STATUS      current
        DESCRIPTION
            "The full-duplex status of the first port on a topology edge."
        DEFVAL { half }
        ::= { ibhgmpNTDPTopEntry 6 }

    ibhgmpNTDPTopEdgeStartPortSpeed OBJECT-TYPE
        SYNTAX      Integer32
        MAX-ACCESS  read-only
        STATUS      current
        DESCRIPTION
            "The speed of the first port on a topology edge."
        DEFVAL { 0 }
        ::= { ibhgmpNTDPTopEntry 7 }

    ibhgmpNTDPTopEdgeEndPort OBJECT-TYPE
        SYNTAX      OCTET STRING(SIZE(0..47))
        MAX-ACCESS  read-only
        STATUS      current
        DESCRIPTION
            "The number of the last port of a topology edge. Interface
            type + card number / slot number / sequence number."
        ::= { ibhgmpNTDPTopEntry 8 }

    ibhgmpNTDPTopLinkStatus OBJECT-TYPE
        SYNTAX      INTEGER
            {
                forwarding(1),
                blocking(2)
            }
        MAX-ACCESS  read-only
        STATUS      current
        DESCRIPTION
            "In STP or RSTP, it describes link status according to port STP
            steady status. In MSTP it describes STP steady status of the
            instance which management VLAN belongs to. Either
            'hgmpNTDPTopEdgeStartPort' or 'hgmpNTDPTopEdgeEndPort' STP
            steady status is 'blocking', this object is 'blocking',
            otherwise is 'forwarding'.
            If STP or MSTP is disabled, this object is 'forwarding'."
        ::= { ibhgmpNTDPTopEntry 11 }

    ibhgmpStackEventsV2 OBJECT-IDENTITY
        STATUS      current
        DESCRIPTION
            "Definition point for Stack notifications."
        ::= { ibStackObject 0 }

    ibhgmpStackMemberfailure NOTIFICATION-TYPE
        OBJECTS
            {
                ibhgmpStackMemberDeviceId
            }
        STATUS      current
        DESCRIPTION
            "When a stack member failure, send a snmp trap to the network
            management."
        ::= { ibhgmpStackEventsV2 1 }

    ibhgmpStackMemberRecover NOTIFICATION-TYPE
        OBJECTS
            {
                ibhgmpStackMemberDeviceId
            }
        STATUS      current
        DESCRIPTION
            "When a stack member Recover, send a snmp trap to the network
            management."
        ::= { ibhgmpStackEventsV2 2 }

    ibhgmpStackMemberStatusChange NOTIFICATION-TYPE
        OBJECTS
            {
                ibhgmpStackMemberDeviceId,
                ibhgmpNTDPCacheClusterRole
            }
        STATUS      current
        DESCRIPTION
            "When a stack member status change, send a snmp trap to the network
            management."
        ::= { ibhgmpStackEventsV2 3 }
END
