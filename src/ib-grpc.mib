-- =================================================================
-- Copyright (C) 2023 Intelbras S.A. All rights reserved.
--
-- Description: GRPC mib
-- Reference:
-- Version: V1.1
-- History:
--  V1.0 Created by xiexiang
--      Initial version 2022-12-22
--  V1.1 2023-06-25 Updated by meishenhe
--      Added notification node ibGrpcConnectionFailure
--      Added notification node ibGrpcConnectionRecover
-- =================================================================
IB-GRPC-MIB DEFINITIONS ::= BEGIN

IMPORTS
    MODULE-IDENTITY, OBJECT-TYPE, NOTIFICATION-TYPE,
    Integer32
        FROM SNMPv2-SMI
    DisplayString
        FROM SNMPv2-TC
    InetAddressType, InetAddress
        FROM INET-ADDRESS-MIB
    ibCommon
        FROM IB-OID-MIB;

ibGrpc MODULE-IDENTITY
    LAST-UPDATED "202306252101Z"
    ORGANIZATION
        "Intelbras S.A. Industria de Telecomunicacao Eletronica Brasileria."
    CONTACT-INFO
        ""
    DESCRIPTION
        "The MIB module is used for GRPC connection notification."
    REVISION "202306252101Z"
    DESCRIPTION
        "Added notification node ibGrpcConnectionFailure
         Added notification node ibGrpcConnectionRecover"
    REVISION    "202212220000Z"
    DESCRIPTION    "The initial version."
    ::= { ibCommon 259 }

-- ==================================================================
--
-- GRPC trap object
--
-- ==================================================================
ibGrpcObjects OBJECT IDENTIFIER ::= { ibGrpc 1 }

ibGrpcConnObjects OBJECT IDENTIFIER ::= { ibGrpcObjects 1 }

ibGrpcUserName OBJECT-TYPE
    SYNTAX       DisplayString (SIZE(1..80))
    MAX-ACCESS   accessible-for-notify
    STATUS   current
    DESCRIPTION
    "The name of an GRPC user."
    ::= { ibGrpcConnObjects 1 }

ibGrpcUserIPAddressType OBJECT-TYPE
    SYNTAX       InetAddressType
    MAX-ACCESS   accessible-for-notify
    STATUS   current
    DESCRIPTION
    "The IP address type of the GRPC user."
    ::= { ibGrpcConnObjects 2 }

ibGrpcUserIPAddress OBJECT-TYPE
    SYNTAX       InetAddress
    MAX-ACCESS   accessible-for-notify
    STATUS   current
    DESCRIPTION
    "The IP address of the GRPC user."
    ::= { ibGrpcConnObjects 3 }

ibGrpcSessionId OBJECT-TYPE
    SYNTAX       Integer32(1..2147483647)
    MAX-ACCESS   accessible-for-notify
    STATUS   current
    DESCRIPTION
    "ID of a GRPC session."
    ::= { ibGrpcConnObjects 4 }

ibGrpcTrapDescription OBJECT-TYPE
    SYNTAX       DisplayString (SIZE(1..80))
    MAX-ACCESS   accessible-for-notify
    STATUS   current
    DESCRIPTION
    "The description of the GRPC trap."
    ::= { ibGrpcConnObjects 5 }

ibGrpcEventName OBJECT-TYPE
    SYNTAX       DisplayString (SIZE(1..80))
    MAX-ACCESS   accessible-for-notify
    STATUS   current
    DESCRIPTION
    "The name of an GRPC event."
    ::= { ibGrpcConnObjects 6 }

ibGrpcModuleName OBJECT-TYPE
    SYNTAX       DisplayString (SIZE(1..80))
    MAX-ACCESS   accessible-for-notify
    STATUS   current
    DESCRIPTION
    "The name of a GRPC module."
    ::= { ibGrpcConnObjects 7 }

ibGrpcServerIPAddress OBJECT-TYPE
    SYNTAX         InetAddress
    MAX-ACCESS     accessible-for-notify
    STATUS         current
    DESCRIPTION
        "The IP address of the GRPC Server."
    ::= { ibGrpcConnObjects 8 }

ibGrpcServerPort OBJECT-TYPE
    SYNTAX         Integer32(1..2147483647)
    MAX-ACCESS     accessible-for-notify
    STATUS         current
    DESCRIPTION
        "The port of the GRPC Server."
    ::= { ibGrpcConnObjects 9 }

ibGrpcVpnInstance OBJECT-TYPE
    SYNTAX         OCTET STRING (SIZE(1..255))
    MAX-ACCESS     accessible-for-notify
    STATUS         current
    DESCRIPTION
        "The IP address of the GRPC Server."
    ::= { ibGrpcConnObjects 10 }

ibGrpcDestDg OBJECT-TYPE
    SYNTAX         OCTET STRING (SIZE(1..255))
    MAX-ACCESS     accessible-for-notify
    STATUS         current
    DESCRIPTION
        "The destination group of the GRPC."
    ::= { ibGrpcConnObjects 11 }

ibGrpcSubscription OBJECT-TYPE
    SYNTAX         OCTET STRING (SIZE(1..255))
    MAX-ACCESS     accessible-for-notify
    STATUS         current
    DESCRIPTION
        "The subscription of the GRPC."
    ::= { ibGrpcConnObjects 12 }

ibGrpcTrap OBJECT IDENTIFIER ::= { ibGrpc 2 }

ibGrpcConnTrapPrefix OBJECT IDENTIFIER ::= { ibGrpcTrap 0 }

ibGrpcLogin NOTIFICATION-TYPE
    OBJECTS {
            ibGrpcUserName,
            ibGrpcUserIPAddressType,
            ibGrpcUserIPAddress,
            ibGrpcSessionId
        }
    STATUS  current
    DESCRIPTION
        "This notification is generated when a user logs in successfully through GRPC."
::= { ibGrpcConnTrapPrefix 1 }

ibGrpcLoginFailure NOTIFICATION-TYPE
    OBJECTS {
            ibGrpcUserName,
            ibGrpcUserIPAddressType,
            ibGrpcUserIPAddress
        }
    STATUS  current
    DESCRIPTION
        "This notification is generated when a user fails to log in through GRPC."
::= { ibGrpcConnTrapPrefix 2 }

ibGrpcLogout NOTIFICATION-TYPE
    OBJECTS {
            ibGrpcUserName,
            ibGrpcSessionId
        }
    STATUS  current
    DESCRIPTION
        "This notification is generated when a user logs out successfully through GRPC."
::= { ibGrpcConnTrapPrefix 3 }

ibGrpcServerFailure NOTIFICATION-TYPE
    OBJECTS {
            ibGrpcTrapDescription
        }
    STATUS  current
    DESCRIPTION
        "This notification is generated when the GRPC server fails to enable ."
::= { ibGrpcConnTrapPrefix 4 }

ibGrpcServiceStop NOTIFICATION-TYPE
    OBJECTS {
            ibGrpcTrapDescription
        }
    STATUS  current
    DESCRIPTION
        "This notification is generated when the CPU usage threshold has been exceeded."
::= { ibGrpcConnTrapPrefix 5 }

ibGrpcServiceRecover NOTIFICATION-TYPE
    OBJECTS {
            ibGrpcTrapDescription
        }
    STATUS  current
    DESCRIPTION
        "This notification is generated when the GRPC service recovered."
::= { ibGrpcConnTrapPrefix 6 }

ibGrpcSubscribeEventFailure NOTIFICATION-TYPE
    OBJECTS {
            ibGrpcEventName
        }
    STATUS  current
    DESCRIPTION
        "This notification is generated when the GRPC subscribes event unsuccessfully."
::= { ibGrpcConnTrapPrefix 7 }

ibGrpcReceiveSubscription NOTIFICATION-TYPE
    OBJECTS {
            ibGrpcModuleName
        }
    STATUS  current
    DESCRIPTION
        "This notification is generated when the GRPC subscription is received."
::= { ibGrpcConnTrapPrefix 8 }

ibGrpcConnectionFailure NOTIFICATION-TYPE
    OBJECTS {
            ibGrpcServerIPAddress,
            ibGrpcServerPort,
            ibGrpcVpnInstance,
            ibGrpcDestDg,
            ibGrpcSubscription
        }
    STATUS  current
    DESCRIPTION
        "This notification is generated when the GRPC device disconnected from a collector."
::= { ibGrpcConnTrapPrefix 9 }

ibGrpcConnectionRecover NOTIFICATION-TYPE
    OBJECTS {
            ibGrpcServerIPAddress,
            ibGrpcServerPort,
            ibGrpcVpnInstance,
            ibGrpcDestDg,
            ibGrpcSubscription
        }
    STATUS  current
    DESCRIPTION
        "This notification is generated when the GRPC connection established to a collector."
::= { ibGrpcConnTrapPrefix 10 }
END
