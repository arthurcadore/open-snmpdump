-- =========================================================================
-- Copyright (C) 2023 Intelbras S.A. All rights reserved.
--
-- Description:This file describes the MIB implementation of mpls lsr.
-- Reference:
-- Version: V1.0
-- History:
-- 	    V1.0 6th Mar 2004
--		Initial version
-- =========================================================================
IB-MPLS-LSR-MIB DEFINITIONS ::= BEGIN

IMPORTS
   MODULE-IDENTITY, OBJECT-TYPE, NOTIFICATION-TYPE,
   Integer32, Counter32, Unsigned32,
   Counter64, Gauge32
      FROM SNMPv2-SMI
      
   MODULE-COMPLIANCE, OBJECT-GROUP, NOTIFICATION-GROUP
      FROM SNMPv2-CONF
      
   TEXTUAL-CONVENTION, TruthValue, RowStatus, StorageType,
   RowPointer, TimeStamp
      FROM SNMPv2-TC
      
   InterfaceIndex, InterfaceIndexOrZero
      FROM IF-MIB

   ibMpls
      FROM IB-OID-MIB

   AddressFamilyNumbers
      FROM IANA-ADDRESS-FAMILY-NUMBERS-MIB
      
   InetAddressIPv4, InetAddressIPv6, InetAddressType
      FROM INET-ADDRESS-MIB;

ibMplsLsr MODULE-IDENTITY
   LAST-UPDATED "200007121200Z"  -- 12 July 2000 12:00:00 EST
   ORGANIZATION
       "Intelbras S.A. Industria de Telecomunicacao Eletronica Brasileria."
   CONTACT-INFO
       ""
   DESCRIPTION
       "This MIB contains managed object definitions for the
        Multiprotocol Label Switching (MPLS) Router as
        defined in: Rosen, E., Viswanathan, A., and R.
        Callon, Multiprotocol Label Switching Architecture,
        Internet Draft <draft-ietf-mpls-arch-06.txt>,
        August 1999."
   
   -- Revision history.
   REVISION
       "200007121200Z"  -- 12 July 2000 12:00:00 EST
   DESCRIPTION
       "Seventh draft version. Fix minor compilation errors."
   REVISION
       "200007071200Z"  -- 07 July 2000 12:00:00 EST
   DESCRIPTION
       "Sixth draft version. Made minor typographical corrections 
        noted from WG mailing list during second working group last
        call."
   REVISION
       "200004261200Z"  -- 26 April 2000 12:00:00 EST
   DESCRIPTION
       "Fifth draft version. Made minor typographical corrections 
        noted from WG mailing list."
   REVISION
       "200004211200Z"  -- 21 April 2000 12:00:00 EST
   DESCRIPTION
       "Fourth draft version.  Made corrections from WG Last 
        Call comments."
   REVISION
       "200003061200Z"  -- 6 March 2000 12:00:00 EST
   DESCRIPTION
       "Third draft version."
   REVISION
       "200002161200Z"  -- 16 February 2000 12:00:00 EST
   DESCRIPTION
       "Second draft version."
   REVISION
       "199906161200Z"  -- 16 June 1999 12:00:00 EST
   DESCRIPTION
      "Initial draft version."
   ::= { ibMpls 1 }


-- Textual Conventions.

IbMplsLSPID ::= TEXTUAL-CONVENTION
   STATUS        current
   DESCRIPTION
       "An identifier that is assigned to each LSP and is
        used to uniquely identify it.  This is assigned at
        the head end of the LSP and can be used by all LSRs
        to identify this LSP.  This value is piggybacked by
        the signaling protocol when this LSP is signaled
        within the network.  This identifier can then be
        used at each LSR to identify which labels are being
        swapped to other labels for this LSP.  For IPv4
        addresses this results in a 6-octet long cookie."
   SYNTAX        OCTET STRING (SIZE (0..31))

-- An MPLS label.
IbMplsLabel ::= TEXTUAL-CONVENTION
   STATUS        current
   DESCRIPTION
       "This value represents an MPLS label.  Note that the
        contents of a label field are interpreted in an
        interface-type specific fashion.  For example, the
        20-bit wide label carried in the MPLS shim header is
        contained in bits 0-19 and bits 20-31 must be zero.
        The frame relay label can be either 10 or 23 bits
        wide depending on the size of the DLCI field and
        bits 10-31, or 23-31 must be zero, respectively.
        For an ATM interface, bits 0-15 must be interpreted
        as the VCI, bits 16-23 as the VPI and bits 24-31
        must be zero.  Note that the permissible label
        values are also a function of the interface type.
        For example, the value 3 has special semantics in
        the control plane for an MPLS shim header label and
        is not a valid label value in the data path."
   REFERENCE
       "1. MPLS Label Stack Encoding, Rosen et al, draft-
          ietf-mpls-label-encaps-07.txt, March 2000.
        2. Use of Label Switching on Frame Relay Networks,
          Conta et al, draft-ietf-mpls-fr-03.txt, Nov.
          1998.
        3. MPLS using LDP and ATM VC switching, Davie et al,
          draft-ietf-mpls-atm-02.txt, April 1999."
   SYNTAX  Unsigned32 (0..4294967295)

IbMplsBitRate ::= TEXTUAL-CONVENTION
   DISPLAY-HINT "d"
   STATUS      current
   DESCRIPTION
       "An estimate of bandwidth in units of 1,000 bits per
        second.  If this object reports a value of 'n' then
        the rate of the object is somewhere in the range of
        'n-500' to 'n+499'. For objects which do not vary in
        bitrate, or for those where no accurate estimation
        can be made, this object should contain the nominal
        bitrate."
   SYNTAX  Integer32 (1..2147483647)

IbMplsBurstSize ::= TEXTUAL-CONVENTION
   DISPLAY-HINT "d"
   STATUS      current
   DESCRIPTION
       "The number of octets of MPLS data that the stream
        may send back-to-back without concern for policing."
   SYNTAX  Integer32 (1..2147483647)

IbMplsObjectOwner ::= TEXTUAL-CONVENTION
   STATUS      current
   DESCRIPTION
           "The entity which owns the object in question."
   SYNTAX   INTEGER {
                other(1),
                snmp(2),
                ldp(3),
                rsvp(4),
                crldp(5),
                policyAgent(6),
                unknown (7)
             }

-- Top level components of this MIB.

-- Tables, Scalars
ibmplsLsrObjects       OBJECT IDENTIFIER ::= { ibMplsLsr 1 }
-- traps
ibmplsLsrNotifications OBJECT IDENTIFIER ::= { ibMplsLsr 2 }
ibmplsLsrNotifyPrefix OBJECT IDENTIFIER ::= { ibmplsLsrNotifications 0 }
-- conformance
ibmplsLsrConformance   OBJECT IDENTIFIER ::= { ibMplsLsr 3 }


-- MPLS Interface Configuration Table.

ibmplsInterfaceConfTable  OBJECT-TYPE
   SYNTAX        SEQUENCE OF IbMplsInterfaceConfEntry
   MAX-ACCESS    not-accessible
   STATUS        current
   DESCRIPTION
       "This table specifies per-interface MPLS capability
        and associated information."
   ::= { ibmplsLsrObjects 1 }

ibmplsInterfaceConfEntry OBJECT-TYPE
   SYNTAX        IbMplsInterfaceConfEntry
   MAX-ACCESS    not-accessible
   STATUS        current
   DESCRIPTION
       "An entry in this table is created by an LSR for
        every interface capable of supporting MPLS. The
        entry with index 0 represents the per-platform label
        space and contains parameters that apply to all
        interfaces that participate in the per-platform
        label space. Other entries defined in this table
        represent additional MPLS interfaces that may
        participate in either the per-platform or per-
        interface label spaces, or both. Additional
        information about label space participation of an
        interface is provided in the description clause of
        ibmplsInterfaceLabelParticipationType."
   INDEX       { ibmplsInterfaceConfIndex }
      ::= { ibmplsInterfaceConfTable 1 }

IbMplsInterfaceConfEntry ::= SEQUENCE {
  ibmplsInterfaceConfIndex              InterfaceIndexOrZero,
  ibmplsInterfaceLabelMinIn             IbMplsLabel,
  ibmplsInterfaceLabelMaxIn             IbMplsLabel,
  ibmplsInterfaceLabelMinOut            IbMplsLabel,
  ibmplsInterfaceLabelMaxOut            IbMplsLabel,
  ibmplsInterfaceTotalBandwidth         IbMplsBitRate,
  ibmplsInterfaceAvailableBandwidth     IbMplsBitRate,
  ibmplsInterfaceLabelParticipationType BITS,
  ibmplsInterfaceConfStorageType        StorageType
}

ibmplsInterfaceConfIndex OBJECT-TYPE
   SYNTAX        InterfaceIndexOrZero
   MAX-ACCESS    not-accessible
   STATUS        current
   DESCRIPTION
       "This is a unique index for an entry in the
        ibmplsInterfaceConfTable.  A non-zero index for an
        entry indicates the ifIndex for the corresponding
        interface entry in of the MPLS-layer in the ifTable.
        Note that the per-platform label space may apply to
        several interfaces, and therefore the configuration
        of the per-platform label space interface parameters
        will apply to all of the interfaces that are
        participating in the per-platform label space."
   REFERENCE
       "RFC 2233 - The Interfaces Group MIB using SMIv2,
        McCloghrie, K., and F. Kastenholtz, Nov. 1997"
   ::= { ibmplsInterfaceConfEntry 1 }

ibmplsInterfaceLabelMinIn OBJECT-TYPE
   SYNTAX        IbMplsLabel
   MAX-ACCESS    read-only
   STATUS        current
   DESCRIPTION
       "This is the minimum value of an MPLS label that this
        LSR is willing to receive on this interface."
   ::= { ibmplsInterfaceConfEntry 2 }

ibmplsInterfaceLabelMaxIn OBJECT-TYPE
   SYNTAX        IbMplsLabel
   MAX-ACCESS    read-only
   STATUS        current
   DESCRIPTION
       "This is the maximum value of an MPLS label that this
        LSR is willing to receive on this interface."
   ::= { ibmplsInterfaceConfEntry 3 }

ibmplsInterfaceLabelMinOut OBJECT-TYPE
   SYNTAX        IbMplsLabel
   MAX-ACCESS    read-only
   STATUS        current
   DESCRIPTION
       "This is the minimum value of an MPLS label that this
        LSR is willing to send on this interface."
   ::= { ibmplsInterfaceConfEntry 4 }

ibmplsInterfaceLabelMaxOut OBJECT-TYPE
   SYNTAX        IbMplsLabel
   MAX-ACCESS    read-only
   STATUS        current
   DESCRIPTION
       "This is the maximum value of an MPLS label that this
        LSR is willing to send on this interface."
   ::= { ibmplsInterfaceConfEntry 5 }

ibmplsInterfaceTotalBandwidth        OBJECT-TYPE
   SYNTAX        IbMplsBitRate
   MAX-ACCESS    read-only
   STATUS        current
   DESCRIPTION
       "This value indicates the total amount of usable
        bandwidth on this interface and is specified in
        kilobits per second (Kbps).  This variable is
        not applicable when applied to the interface with
        index 0."
::= { ibmplsInterfaceConfEntry 6 }

ibmplsInterfaceAvailableBandwidth       OBJECT-TYPE
   SYNTAX        IbMplsBitRate
   MAX-ACCESS    read-only
   STATUS        current
   DESCRIPTION
       "This value indicates the total amount of available
        bandwidth available on this interface and is
        specified in kilobits per second (Kbps).  This
        value is calculated as the difference between the
        amount of bandwidth currently in use and that
        specified in ibmplsInterfaceTotalBandwidth.  This
        variable is not applicable when applied to the
        interface with index 0."
::= { ibmplsInterfaceConfEntry 7 }

ibmplsInterfaceLabelParticipationType OBJECT-TYPE
   SYNTAX  BITS {
                perPlatform (0),
                perInterface (1)
              }
   MAX-ACCESS    read-only
   STATUS        current
   DESCRIPTION
       "Either the perPlatform(0) or perInterface(1) bit
        MUST be set. If the value of the
        ibmplsInterfaceConfIndex for this entry is zero, then
        only the perPlatform(0) bit MUST be set and the
        perInterface(1) bit is meaningless. If the
        perInterface(1) bit is set then the value of
        ibmplsInterfaceLabelMinIn, ibmplsInterfaceLabelMaxIn,
        ibmplsInterfaceLabelMinOut, and
        ibmplsInterfaceLabelMaxOut for this entry reflect the
        label ranges for this interface.  If only the
        perPlatform(0) bit is set, then the value of
        ibmplsInterfaceLabelMinIn, ibmplsInterfaceLabelMaxIn,
        ibmplsInterfaceLabelMinOut, and
        ibmplsInterfaceLabelMaxOut for this entry must be
        identical to the instance of these objects with
        index 0."
   REFERENCE
      "Multiprotocol Label Switching, Rosen et al, draft-ietf-mpls-
       arch-06.txt, August 1999."
::= { ibmplsInterfaceConfEntry 8 }

ibmplsInterfaceConfStorageType  OBJECT-TYPE
   SYNTAX      StorageType
   MAX-ACCESS  read-create
   STATUS      current
   DESCRIPTION
       "The storage type for this entry."
   ::= { ibmplsInterfaceConfEntry 9 }

-- End of ibmplsInterfaceConfTable


-- MPLS Interface Performance Table.
ibmplsInterfacePerfTable  OBJECT-TYPE
   SYNTAX        SEQUENCE OF IbMplsInterfacePerfEntry
   MAX-ACCESS    not-accessible
   STATUS        current
   DESCRIPTION
       "This table provides MPLS performance information on
        a per-interface basis."
   ::= { ibmplsLsrObjects 2 }

ibmplsInterfacePerfEntry OBJECT-TYPE
   SYNTAX        IbMplsInterfacePerfEntry
   MAX-ACCESS    not-accessible
   STATUS        current
   DESCRIPTION
       "An entry in this table is created by the LSR for
        every interface capable of supporting MPLS.  Its is
        an extension to the ibmplsInterfaceConfEntry table."
   AUGMENTS      { ibmplsInterfaceConfEntry }
      ::= { ibmplsInterfacePerfTable 1 }

IbMplsInterfacePerfEntry ::= SEQUENCE {
      -- incoming direction
      ibmplsInterfaceInLabelsUsed          Gauge32,
      ibmplsInterfaceFailedLabelLookup     Counter32,
      
      -- outgoing direction
      ibmplsInterfaceOutLabelsUsed         Gauge32,
      ibmplsInterfaceOutFragments          Counter32
   }

ibmplsInterfaceInLabelsUsed OBJECT-TYPE
   SYNTAX        Gauge32
   MAX-ACCESS    read-only
   STATUS        current
   DESCRIPTION
       "This object counts the number of labels
        that are in use at this point in time on this
        interface in the incoming direction. If the interface
        participates in the per-platform label space only,
        then this instance of this object MUST be identical
        with the instance with index 0. If the interface
        participates in the per-interface label space, then this
        this instance of this object MUST represent the number of
        of per-interface labels that are in use at this point in
        time on this interface."
   ::= { ibmplsInterfacePerfEntry 1 }

ibmplsInterfaceFailedLabelLookup OBJECT-TYPE
   SYNTAX        Counter32
   MAX-ACCESS    read-only
   STATUS        current
   DESCRIPTION
       "This object counts the number of labeled packets
        that have been received on this interface and were
        discarded because there was no matching cross-connect
        entry. This object MUST count on a per-interface basis
        regardless of which label space the interface participates
        in."
   ::= { ibmplsInterfacePerfEntry 2 }

ibmplsInterfaceOutLabelsUsed OBJECT-TYPE
   SYNTAX        Gauge32
   MAX-ACCESS    read-only
   STATUS        current
   DESCRIPTION
       "This object counts the number of top-most labels in the
        outgoing label stacks that are in use at this point
        in time on this interface. This object
        MUST count on a per-interface basis regardless of
        which label space the interface participates in."
   ::= { ibmplsInterfacePerfEntry 3 }

ibmplsInterfaceOutFragments OBJECT-TYPE
   SYNTAX        Counter32
   MAX-ACCESS    read-only
   STATUS        current
   DESCRIPTION
       "This object counts the number of outgoing MPLS
        packets that required fragmentation before
        transmission on this interface. This object
        transmission on this interface. This object
        MUST count on a per-interface basis regardless of 
        which label space the interface participates in."
::= { ibmplsInterfacePerfEntry 4 }

-- In-segment table.

ibmplsInSegmentTable  OBJECT-TYPE
   SYNTAX        SEQUENCE OF IbMplsInSegmentEntry
   MAX-ACCESS    not-accessible
   STATUS        current
   DESCRIPTION
       "This table contains a collection of incoming
        segments to an LSR."
   ::= { ibmplsLsrObjects 3 }

ibmplsInSegmentEntry  OBJECT-TYPE
   SYNTAX        IbMplsInSegmentEntry
   MAX-ACCESS    not-accessible
   STATUS        current
   DESCRIPTION
       "An entry in this table represents one incoming
        segment.  An entry can be created by a network
        administrator or an SNMP agent, or an MPLS signaling
        protocol.  The creator of the entry is denoted by
        ibmplsInSegmentOwner.  An entry in this table is
        indexed by the ifIndex of the incoming interface and
        the (top) label."
   INDEX         { ibmplsInSegmentIfIndex, ibmplsInSegmentLabel }
   ::= { ibmplsInSegmentTable 1 }

IbMplsInSegmentEntry ::= SEQUENCE {
  ibmplsInSegmentIfIndex              InterfaceIndexOrZero,
  ibmplsInSegmentLabel                IbMplsLabel,
  ibmplsInSegmentNPop                 Integer32,
  ibmplsInSegmentAddrFamily           AddressFamilyNumbers,
  ibmplsInSegmentXCIndex              Integer32,
  ibmplsInSegmentOwner                IbMplsObjectOwner,
  ibmplsInSegmentTrafficParamPtr      RowPointer,
  ibmplsInSegmentRowStatus            RowStatus,
  ibmplsInSegmentStorageType          StorageType
}

ibmplsInSegmentIfIndex OBJECT-TYPE
   SYNTAX        InterfaceIndexOrZero
   MAX-ACCESS    accessible-for-notify
   STATUS        current
   DESCRIPTION
       "This is a unique index for an entry in the
        ibmplsInSegmentTable.  This value represents the
        interface index for the incoming MPLS interface.  A
        value of zero represents an incoming label from the
        per-platform label space.  In this case, the
        ibmplsInSegmentLabel is interpreted to be an MPLS-type
        label."
   ::= { ibmplsInSegmentEntry 1 }

ibmplsInSegmentLabel OBJECT-TYPE
   SYNTAX        IbMplsLabel
   MAX-ACCESS    accessible-for-notify
   STATUS        current
   DESCRIPTION
       "The incoming label for this segment."
   ::= { ibmplsInSegmentEntry 2 }

ibmplsInSegmentNPop OBJECT-TYPE
   SYNTAX        Integer32 (1..2147483647)
   MAX-ACCESS    read-create
   STATUS        current
   DESCRIPTION
       "The number of labels to pop from the incoming
        packet.  Normally only the top label is popped from
        the packet and used for all switching decisions for
        that packet.  Note that technologies which do not
        support label popping should set this value to its
        default value of 1."
   DEFVAL        { 1 }
   ::= { ibmplsInSegmentEntry 3 }

ibmplsInSegmentAddrFamily OBJECT-TYPE
   SYNTAX        AddressFamilyNumbers
   MAX-ACCESS    read-create
   STATUS        current
   DESCRIPTION
       "The IANA address family [IANAFamily] of the incoming
        packet.  A value of other(0) indicates that the
        family type is either unknown or undefined."
   DEFVAL        { other }
   ::= { ibmplsInSegmentEntry 4 }

ibmplsInSegmentXCIndex OBJECT-TYPE
SYNTAX        Integer32 (0..2147483647)
   MAX-ACCESS    read-only
   STATUS        current
   DESCRIPTION
       "Index into ibmplsXCTable which identifies which cross-
        connect entry this segment is part of.  A value of
        zero indicates that this entry is not referred to by
        any cross-connect entry.  When a cross-connect entry
        is created which this in-segment is a part of, this
        object is automatically updated to reflect the value
        of ibmplsXCIndex of that cross-connect entry."
   DEFVAL        { 0 }
   ::= { ibmplsInSegmentEntry 5 }
   
ibmplsInSegmentOwner OBJECT-TYPE
   SYNTAX        IbMplsObjectOwner
   MAX-ACCESS    read-create
   STATUS        current
   DESCRIPTION
       "Denotes the entity that created and is responsible
        for managing this segment."
   DEFVAL { unknown }
   ::= { ibmplsInSegmentEntry 6 }

ibmplsInSegmentTrafficParamPtr OBJECT-TYPE
   SYNTAX            RowPointer
   MAX-ACCESS        read-create
   STATUS            current
   DESCRIPTION
     "This variable represents a pointer to the traffic
     parameter specification for this in-segment.  This
     value may point at an entry in the
     ibmplsTrafficParamTable to indicate which
     ibmplsTrafficParamEntry is to be assigned to this
     segment.  This value may optionally point at an
     externally defined traffic parameter specification
     table.  A value of zero-dot-zero indicates best-effort
     treatment.  By having the same value of this object,
     two or more segments can indicate resource sharing."
   ::= { ibmplsInSegmentEntry 7 }

ibmplsInSegmentRowStatus OBJECT-TYPE
   SYNTAX        RowStatus
   MAX-ACCESS    read-create
   STATUS        current
   DESCRIPTION
       "This variable is used to create, modify, and/or
        delete a row in this table."
   ::= { ibmplsInSegmentEntry 8 }
   
ibmplsInSegmentStorageType OBJECT-TYPE
   SYNTAX        StorageType
   MAX-ACCESS    read-create
   STATUS        current
   DESCRIPTION
       "This variable indicates the storage type for this
        object."
   ::= { ibmplsInSegmentEntry 9 }

-- End of ibmplsInSegmentTable

-- In-segment performance table.

ibmplsInSegmentPerfTable  OBJECT-TYPE
   SYNTAX        SEQUENCE OF IbMplsInSegmentPerfEntry
   MAX-ACCESS    not-accessible
   STATUS        current
   DESCRIPTION
       "This table contains statistical information for
        incoming MPLS segments to an LSR."
   ::= { ibmplsLsrObjects 4 }

ibmplsInSegmentPerfEntry  OBJECT-TYPE
   SYNTAX        IbMplsInSegmentPerfEntry
   MAX-ACCESS    not-accessible
   STATUS        current
   DESCRIPTION
       "An entry in this table contains statistical
        information about one incoming segment which was
        configured in the ibmplsInSegmentTable. The counters
        in this entry should behave in a manner similar to
        that of the interface."
   AUGMENTS      { ibmplsInSegmentEntry }
   ::= { ibmplsInSegmentPerfTable 1 }

IbMplsInSegmentPerfEntry ::= SEQUENCE {
    ibmplsInSegmentOctets                 Counter32,
    ibmplsInSegmentPackets                Counter32,
    ibmplsInSegmentErrors                 Counter32,
    ibmplsInSegmentDiscards               Counter32,
    
    -- high capacity counter
    ibmplsInSegmentHCOctets               Counter64,
    
    ibmplsInSegmentPerfDiscontinuityTime  TimeStamp
   }
ibmplsInSegmentOctets OBJECT-TYPE
   SYNTAX        Counter32
   MAX-ACCESS    read-only
   STATUS        current
   DESCRIPTION
       "This value represents the total number of octets
        received by this segment."
   ::= { ibmplsInSegmentPerfEntry 1 }

ibmplsInSegmentPackets OBJECT-TYPE
   SYNTAX        Counter32
   MAX-ACCESS    read-only
   STATUS        current
   DESCRIPTION
       "Total number of packets received by this segment."
   ::= { ibmplsInSegmentPerfEntry 2 }

ibmplsInSegmentErrors OBJECT-TYPE
   SYNTAX        Counter32
   MAX-ACCESS    read-only
   STATUS        current
   DESCRIPTION
       "The number of errored packets received on this
        segment."
   ::= { ibmplsInSegmentPerfEntry 3 }

ibmplsInSegmentDiscards OBJECT-TYPE
   SYNTAX        Counter32
   MAX-ACCESS    read-only
   STATUS        current
   DESCRIPTION
       "The number of labeled packets received on this in-
        segment, which were chosen to be discarded even
        though no errors had been detected to prevent their
        being transmitted.  One possible reason for
        discarding such a labeled packet could be to free up
        buffer space."
   ::= { ibmplsInSegmentPerfEntry 4 }

ibmplsInSegmentHCOctets OBJECT-TYPE
   SYNTAX        Counter64
   MAX-ACCESS    read-only
   STATUS        current
   DESCRIPTION
       "The total number of octets received.  This is the 64
        bit version of ibmplsInSegmentOctets."
   ::= { ibmplsInSegmentPerfEntry 5 }
   
ibmplsInSegmentPerfDiscontinuityTime OBJECT-TYPE

       SYNTAX      TimeStamp
       MAX-ACCESS  read-only
       STATUS      current
       DESCRIPTION
         "The value of sysUpTime on the most recent occasion at
          which any one or more of this segment's Counter32 or
          Counter64 suffered a discontinuity. If no such
          discontinuities have occurred since the last re-
          initialization of the local management subsystem, then
          this object contains a zero value."
       ::= { ibmplsInSegmentPerfEntry 6 }
   

-- End of ibmplsInSegmentPerfTable.

-- Out-segment table.

ibmplsOutSegmentIndexNext OBJECT-TYPE
   SYNTAX        Integer32 (0..2147483647)
   MAX-ACCESS    read-only
   STATUS        current
   DESCRIPTION
       "This object contains the next appropriate value to
        be used for ibmplsOutSegmentIndex when creating
        entries in the ibmplsOutSegmentTable.  If the number
        of unassigned entries is exhausted, this object will
        take on the value of 0.  To obtain the
        ibmplsOutSegmentIndex value for a new entry, the
        manager must first issue a management protocol
        retrieval operation to obtain the current value of
        this object.  The agent should modify the value to
        reflect the next unassigned index after each
        retrieval operation.  After a manager retrieves a
        value the agent will determine through its local
        policy when this index value will be made available
        for reuse."
   ::= { ibmplsLsrObjects 5 }


ibmplsOutSegmentTable  OBJECT-TYPE
   SYNTAX        SEQUENCE OF IbMplsOutSegmentEntry
   MAX-ACCESS    not-accessible
   STATUS        current
   DESCRIPTION
       "This table contains a representation of the outgoing
        segments from an LSR."
   ::= { ibmplsLsrObjects 6 }

ibmplsOutSegmentEntry  OBJECT-TYPE
   SYNTAX        IbMplsOutSegmentEntry
   MAX-ACCESS    not-accessible
   STATUS        current
   DESCRIPTION
       "An entry in this table represents one outgoing
        segment.  An entry can be created by a network
        administrator or an SNMP agent, or an MPLS signaling
        protocol.  The object ibmplsOutSegmentOwner indicates
        the creator of this entry."
   INDEX         { ibmplsOutSegmentIndex }
   ::= { ibmplsOutSegmentTable 1 }

IbMplsOutSegmentEntry ::= SEQUENCE {
  ibmplsOutSegmentIndex                Integer32,
  ibmplsOutSegmentIfIndex              InterfaceIndex,
  ibmplsOutSegmentPushTopLabel         TruthValue,
  ibmplsOutSegmentTopLabel             IbMplsLabel,
  ibmplsOutSegmentNextHopIpAddrType    InetAddressType,
  ibmplsOutSegmentNextHopIpv4Addr      InetAddressIPv4,
  ibmplsOutSegmentNextHopIpv6Addr      InetAddressIPv6,
  ibmplsOutSegmentXCIndex              Integer32,
  ibmplsOutSegmentOwner                IbMplsObjectOwner,
  ibmplsOutSegmentTrafficParamPtr      RowPointer,
  ibmplsOutSegmentRowStatus            RowStatus,
  ibmplsOutSegmentStorageType          StorageType
}

ibmplsOutSegmentIndex OBJECT-TYPE
   SYNTAX        Integer32(0..2147483647)
   MAX-ACCESS    accessible-for-notify
   STATUS        current
   DESCRIPTION
       "This value contains a unique index for this row.
        While a value of 0 is not valid as an index for this
        row it can be supplied as a valid value to index
        ibmplsXCTable to access entries for which no out-
        segment has been configured."
   ::= { ibmplsOutSegmentEntry 1 }

ibmplsOutSegmentIfIndex OBJECT-TYPE
   SYNTAX        InterfaceIndex
   MAX-ACCESS    read-create
   STATUS        current
   DESCRIPTION
       "This value contains the interface index of the
        outgoing interface."
   ::= { ibmplsOutSegmentEntry 2 }

ibmplsOutSegmentPushTopLabel OBJECT-TYPE
   SYNTAX        TruthValue
   MAX-ACCESS    read-create
   STATUS        current
   DESCRIPTION
       "This value indicates whether or not a top label
        should be pushed onto the outgoing packet's label
        stack.  The value of this variable must be set to
        true if the outgoing interface does not support pop-
        and-go (for example an ATM interface) or if it is a
        tunnel origination.  Note that it is considered an
        error in the case that ibmplsOutSegmentPushTopLabel is
        set to false, but the cross-connect entry which
        refers to this out-segment has a non-zero
        ibmplsLabelStackIndex.  The LSR MUST ensure that this
        situation does not happen "
   ::= { ibmplsOutSegmentEntry 3 }

ibmplsOutSegmentTopLabel OBJECT-TYPE
   SYNTAX        IbMplsLabel
   MAX-ACCESS    read-create
   STATUS        current
   DESCRIPTION
       "If ibmplsOutSegmentPushTopLabel is true then this
        represents the label that should be pushed onto the
        top of the outgoing packet's label stack."
   ::= { ibmplsOutSegmentEntry 4 }

ibmplsOutSegmentNextHopIpAddrType OBJECT-TYPE
   SYNTAX        InetAddressType
   MAX-ACCESS    read-create
   STATUS        current
   DESCRIPTION
       "Indicates whether the next hop address is IPv4 or
        IPv6.  Note that a value of unknown (0) is valid
        only when the outgoing interface is of type point-to-
        point."
   DEFVAL        { unknown }
   ::= { ibmplsOutSegmentEntry 5 }

ibmplsOutSegmentNextHopIpv4Addr OBJECT-TYPE
   SYNTAX        InetAddressIPv4
   MAX-ACCESS    read-create
   STATUS        current
   DESCRIPTION
       "IPv4 Address of the next hop.  Its value is
        significant only when
        ibmplsOutSegmentNextHopIpAddrType is ipV4 (1),
        otherwise it should return a value of 0."
   ::= { ibmplsOutSegmentEntry 6 }

ibmplsOutSegmentNextHopIpv6Addr OBJECT-TYPE
   SYNTAX        InetAddressIPv6
   MAX-ACCESS    read-create
   STATUS        current
   DESCRIPTION
       "IPv6 address of the next hop.  Its value is
        significant only when
        ibmplsOutSegmentNextHopIpAddrType is ipV6 (2),
        otherwise it should return a value of 0."
   ::= { ibmplsOutSegmentEntry 7 }

ibmplsOutSegmentXCIndex OBJECT-TYPE
   SYNTAX        Integer32 (0..2147483647)
   MAX-ACCESS    read-only
   STATUS        current
   DESCRIPTION
       "Index into ibmplsXCTable which identifies which cross-
        connect entry this segment is part of.  A value of
        zero indicates that this entry is not referred to by
        any cross-connect entry.  When a cross-connect entry
        is created which this out-segment is a part of, this
        object is automatically updated to reflect the value
        of ibmplsXCIndex of that cross-connect entry."
   DEFVAL        { 0 }
   ::= { ibmplsOutSegmentEntry 8 }

ibmplsOutSegmentOwner OBJECT-TYPE
   SYNTAX        IbMplsObjectOwner
   MAX-ACCESS    read-create
   STATUS        current
   DESCRIPTION
       "Denotes the entity which created and is responsible
        for managing this segment."
   DEFVAL { unknown }
   ::= { ibmplsOutSegmentEntry 9 }

ibmplsOutSegmentTrafficParamPtr OBJECT-TYPE
   SYNTAX        RowPointer
   MAX-ACCESS    read-create
   STATUS        current
   DESCRIPTION
     "This variable represents a pointer to the traffic
      parameter specification for this out-segment.  This
      value may point at an entry in the
      ibmplsTrafficParamTable to indicate which
      ibmplsTrafficParamEntry is to be assigned to this
      segment.  This value may optionally point at an
      externally defined traffic parameter specification
      table.  A value of zero-dot-zero indicates best-
      effort treatment.  By having the same value of this
      object, two or more segments can indicate resource
      sharing."
   ::= { ibmplsOutSegmentEntry 10 }

ibmplsOutSegmentRowStatus OBJECT-TYPE
   SYNTAX        RowStatus
   MAX-ACCESS    read-create
   STATUS        current
   DESCRIPTION
       "For creating, modifying, and deleting this row."
   ::= { ibmplsOutSegmentEntry 11 }

ibmplsOutSegmentStorageType OBJECT-TYPE
   SYNTAX        StorageType
   MAX-ACCESS    read-create
   STATUS        current
   DESCRIPTION
       "This variable indicates the storage type for this
        object."
   ::= { ibmplsOutSegmentEntry 12 }

-- End of ibmplsOutSegmentTable


-- Out-segment performance table.

ibmplsOutSegmentPerfTable  OBJECT-TYPE
   SYNTAX        SEQUENCE OF IbMplsOutSegmentPerfEntry
   MAX-ACCESS    not-accessible
   STATUS        current
   DESCRIPTION
       "This table contains statistical information about
        outgoing segments from an LSR. The counters in this
        entry should behave in a manner similar to that of
        the interface."
   ::= { ibmplsLsrObjects 7 }

ibmplsOutSegmentPerfEntry  OBJECT-TYPE
   SYNTAX        IbMplsOutSegmentPerfEntry
   MAX-ACCESS    not-accessible
   STATUS        current
   DESCRIPTION
       "An entry in this table contains statistical
        information about one outgoing segment configured in
        ibmplsOutSegmentTable."
   AUGMENTS      { ibmplsOutSegmentEntry }
      ::= { ibmplsOutSegmentPerfTable 1 }

IbMplsOutSegmentPerfEntry ::= SEQUENCE {
      ibmplsOutSegmentOctets                Counter32,
      ibmplsOutSegmentPackets               Counter32,
      ibmplsOutSegmentErrors                Counter32,
      ibmplsOutSegmentDiscards              Counter32,
      
      -- HC counter
      ibmplsOutSegmentHCOctets              Counter64,
      
      ibmplsOutSegmentPerfDiscontinuityTime  TimeStamp
   }

ibmplsOutSegmentOctets OBJECT-TYPE
   SYNTAX        Counter32
   MAX-ACCESS    read-only
   STATUS        current
   DESCRIPTION
       "This value contains the total number of octets sent
        on this segment."
   ::= { ibmplsOutSegmentPerfEntry 1 }

ibmplsOutSegmentPackets OBJECT-TYPE
   SYNTAX        Counter32
   MAX-ACCESS    read-only
   STATUS        current
   DESCRIPTION
       "This value contains the total number of packets sent
        on this segment."
   ::= { ibmplsOutSegmentPerfEntry 2 }

ibmplsOutSegmentErrors OBJECT-TYPE
   SYNTAX        Counter32
   MAX-ACCESS    read-only
   STATUS        current
   DESCRIPTION
       "Number of packets that could not be sent due to
        errors on this segment."
   ::= { ibmplsOutSegmentPerfEntry 3 }

ibmplsOutSegmentDiscards OBJECT-TYPE
   SYNTAX        Counter32
   MAX-ACCESS    read-only
   STATUS        current
   DESCRIPTION
       "The number of labeled packets received on this out-
        segment, which were chosen to be discarded even
        though no errors had been detected to prevent their
        being transmitted.  One possible reason for
        discarding such a labeled packet could be to free up
        buffer space."
   ::= { ibmplsOutSegmentPerfEntry 4 }

ibmplsOutSegmentHCOctets OBJECT-TYPE
   SYNTAX        Counter64
   MAX-ACCESS    read-only
   STATUS        current
   DESCRIPTION
       "Total number of octets sent.  This is the 64 bit
        version of ibmplsOutSegmentOctets."
   ::= { ibmplsOutSegmentPerfEntry 5 }
   
ibmplsOutSegmentPerfDiscontinuityTime OBJECT-TYPE
       SYNTAX      TimeStamp
       MAX-ACCESS  read-only
       STATUS      current
       DESCRIPTION
         "The value of sysUpTime on the most recent occasion at
          which any one or more of this segment's Counter32 or
          Counter64 suffered a discontinuity. If no such
          discontinuities have occurred since the last re-
          initialization of the local management subsystem, then
          this object contains a zero value."
       ::= { ibmplsOutSegmentPerfEntry 6 }
   

-- End of ibmplsOutSegmentPerfTable.

-- Cross-connect table.

ibmplsXCIndexNext OBJECT-TYPE
   SYNTAX        Integer32 (0..2147483647)
   MAX-ACCESS    read-only
   STATUS        current
   DESCRIPTION
       "This object contains an appropriate value to be used
        for ibmplsXCIndex when creating entries in the
        ibmplsXCTable.  The value 0 indicates that no
        unassigned entries are available.  To obtain the
        value of ibmplsXCIndex for a new entry in the
        ibmplsXCTable, the manager issues a management
        protocol retrieval operation to obtain the current
        value of ibmplsXCIndex.  After each retrieval
        operation, the agent should modify the value to
        reflect the next unassigned index.  After a manager
        retrieves a value the agent will determine through
        its local policy when this index value will be made
        available for reuse."
   ::= { ibmplsLsrObjects 8 }

ibmplsXCTable  OBJECT-TYPE
   SYNTAX        SEQUENCE OF IbMplsXCEntry
   MAX-ACCESS    not-accessible
   STATUS        current
   DESCRIPTION

       "This table specifies information for switching
        between LSP segments.  It supports point-to-point,
        point-to-multipoint and multipoint-to-point
        connections.  ibmplsLabelStackTable specifies the
        label stack information for a cross-connect LSR and
        is referred to from ibmplsXCTable."
   ::= { ibmplsLsrObjects 9 }

ibmplsXCEntry  OBJECT-TYPE
   SYNTAX        IbMplsXCEntry
   MAX-ACCESS    not-accessible
   STATUS        current
   DESCRIPTION
       "A row in this table represents one cross-connect
        entry.  The following objects index it:
       
        - cross-connect index ibmplsXCIndex that uniquely
          identifies a group of cross-connect entries
        - interface index of the in-segment,
          ibmplsInSegmentIfIndex
        - incoming label(s), ibmplsInSegmentLabel
        - out-segment index, ibmplsOutSegmentIndex
       
       Originating LSPs:
        These are represented by using the special
        combination of values ibmplsInSegmentIfIndex=0 and
        ibmplsInSegmentLabel=0 as indexes.  In this case the
        ibmplsOutSegmentIndex MUST be non-zero.
       
       Terminating LSPs:
       These are represented by using the special value
        ibmplsOutSegmentIndex=0 as index.

       Special labels:
        Entries indexed by reserved MPLS label values 0
        through 15 imply terminating LSPs and MUST have
        ibmplsOutSegmentIfIndex = 0.  Note that situations
        where LSPs are terminated with incoming label equal
        to 0, should have ibmplsInSegmentIfIndex = 0 as well,
        but can be distinguished from originating LSPs
        because the ibmplsOutSegmentIfIndex = 0.  The
        ibmplsOutSegmentIfIndex MUST only be set to 0 in
        cases of terminating LSPs.
       
        An entry can be created by a network administrator
        or by an SNMP agent as instructed by an MPLS
        signaling protocol."
   INDEX  { ibmplsXCIndex, ibmplsInSegmentIfIndex,
            ibmplsInSegmentLabel,
            ibmplsOutSegmentIndex }

      ::= { ibmplsXCTable 1 }

IbMplsXCEntry ::= SEQUENCE {
      ibmplsXCIndex                 Integer32,
      ibmplsXCLspId                 IbMplsLSPID,
      ibmplsXCLabelStackIndex       Integer32,
      ibmplsXCIsPersistent          TruthValue,
      ibmplsXCOwner                 IbMplsObjectOwner,
      ibmplsXCRowStatus             RowStatus,
      ibmplsXCStorageType           StorageType,
      ibmplsXCAdminStatus           INTEGER,
      ibmplsXCOperStatus            INTEGER
   }

ibmplsXCIndex OBJECT-TYPE
   SYNTAX        Integer32 (1..2147483647)
   MAX-ACCESS    accessible-for-notify
   STATUS        current
   DESCRIPTION
       "Primary index for the conceptual row identifying 
        a group of cross-connect segments."
   ::= { ibmplsXCEntry 1 }

ibmplsXCLspId OBJECT-TYPE
   SYNTAX        IbMplsLSPID
   MAX-ACCESS    read-create
   STATUS        current
   DESCRIPTION
       "This value identifies the label switched path that
        this cross-connect entry belongs to."
   ::= { ibmplsXCEntry 2 }

ibmplsXCLabelStackIndex OBJECT-TYPE
   SYNTAX        Integer32 (0..2147483647)
   MAX-ACCESS    read-create
   STATUS        current
   DESCRIPTION
       "Primary index into ibmplsLabelStackTable identifying a
        stack of labels to be pushed beneath the top label.
        Note that the top label identified by the out-
        segment ensures that all the components of a
        multipoint-to-point connection have the same
        outgoing label.  A value of 0 indicates that no
        labels are to be stacked beneath the top label."
   ::= { ibmplsXCEntry 3 }

ibmplsXCIsPersistent OBJECT-TYPE
   SYNTAX        TruthValue
   MAX-ACCESS    read-create
   STATUS        current
   DESCRIPTION
       "Denotes whether or not this cross-connect entry and
        associated in- and out-segments should be restored
        automatically after failures.  This value MUST be
        set to false in cases where this cross-connect entry
        was created by a signaling protocol."
   DEFVAL        { false }
   ::= { ibmplsXCEntry 4 }
   
ibmplsXCOwner OBJECT-TYPE
   SYNTAX    IbMplsObjectOwner
   MAX-ACCESS    read-create
   STATUS        current
   DESCRIPTION
       "Denotes the entity that created and is responsible
        for managing this cross-connect."
   ::= { ibmplsXCEntry 5 }

ibmplsXCRowStatus OBJECT-TYPE
   SYNTAX        RowStatus
   MAX-ACCESS    read-create
   STATUS        current
   DESCRIPTION
       "For creating, modifying, and deleting this row."
   ::= { ibmplsXCEntry 6 }
   
ibmplsXCStorageType OBJECT-TYPE
   SYNTAX        StorageType
   MAX-ACCESS    read-create
   STATUS        current
   DESCRIPTION
       "Defines the storage type for this object."
   ::= { ibmplsXCEntry 7 }

ibmplsXCAdminStatus OBJECT-TYPE
   SYNTAX   INTEGER {
                up(1),     -- ready to pass packets
                down(2),
                testing(3) -- in some test mode
                }
   MAX-ACCESS    read-create
   STATUS        current
   DESCRIPTION
       "The desired operational status of this segment."
   ::= { ibmplsXCEntry 8 }

ibmplsXCOperStatus OBJECT-TYPE
   SYNTAX   INTEGER {
         up(1),            -- ready to pass packets
         down(2),
         testing(3),       -- in some test mode
         unknown(4),       -- status cannot be determined
                           -- for some reason.
         dormant(5),
         notPresent(6),    -- some component is missing
         lowerLayerDown(7) -- down due to the state of
                           -- lower layer interfaces
      }
   MAX-ACCESS    read-only
   STATUS        current
   DESCRIPTION
       "The actual operational status of this cross-
        connect."
   ::= { ibmplsXCEntry 9 }

-- End of ibmplsXCTable


-- Label stack table.
ibmplsMaxLabelStackDepth  OBJECT-TYPE
   SYNTAX        Integer32 (1..2147483647)
   MAX-ACCESS    read-only
   STATUS        current
   DESCRIPTION
       "The maximum stack depth supported by this LSR."
::= { ibmplsLsrObjects 10 }

ibmplsLabelStackIndexNext  OBJECT-TYPE
   SYNTAX        Integer32 (0..2147483647)
   MAX-ACCESS    read-only
   STATUS        current
   DESCRIPTION
       "This object contains an appropriate value to be used
        for ibmplsLabelStackIndex when creating entries in the
        ibmplsLabelStackTable.  The value 0 indicates that no
        unassigned entries are available.  To obtain an
        ibmplsLabelStackIndex value for a new entry, the
        manager issues a management protocol retrieval
        operation to obtain the current value of this
        object.  After each retrieval operation, the agent
        should modify the value to reflect the next
        unassigned index.  After a manager retrieves a value
        the agent will determine through its local policy
        when this index value will be made available for
        reuse."
::= { ibmplsLsrObjects 11 }

ibmplsLabelStackTable OBJECT-TYPE
   SYNTAX        SEQUENCE OF IbMplsLabelStackEntry
   MAX-ACCESS    not-accessible
   STATUS        current
   DESCRIPTION
       "This table specifies the label stack to be pushed
        onto a packet, beneath the top label.  Entries into
        this table are referred to from ibmplsXCTable."
   ::= { ibmplsLsrObjects 12 }

ibmplsLabelStackEntry OBJECT-TYPE
   SYNTAX        IbMplsLabelStackEntry
   MAX-ACCESS    not-accessible
   STATUS        current
   DESCRIPTION
       "An entry in this table represents one label which is
        to be pushed onto an outgoing packet, beneath the
        top label.  An entry can be created by a network
        administrator or by an SNMP agent as instructed by
        an MPLS signaling protocol."
   INDEX         { ibmplsLabelStackIndex, ibmplsLabelStackLabelIndex }
      ::= { ibmplsLabelStackTable 1 }

IbMplsLabelStackEntry ::= SEQUENCE {
      ibmplsLabelStackIndex             Integer32,
      ibmplsLabelStackLabelIndex        Integer32,
      ibmplsLabelStackLabel             IbMplsLabel,
      ibmplsLabelStackRowStatus         RowStatus,
      ibmplsLabelStackStorageType       StorageType
   }

ibmplsLabelStackIndex OBJECT-TYPE
   SYNTAX        Integer32 (1..2147483647)
   MAX-ACCESS    not-accessible
   STATUS        current
   DESCRIPTION
       "Primary index for this row identifying a stack of
        labels to be pushed on an outgoing packet, beneath
        the top label."
   ::= { ibmplsLabelStackEntry 1 }

ibmplsLabelStackLabelIndex OBJECT-TYPE
   SYNTAX        Integer32 (1..2147483647)
   MAX-ACCESS    not-accessible
   STATUS        current
   DESCRIPTION
       "Secondary index for this row identifying one label
        of the stack.  Note that an entry with a smaller
        ibmplsLabelStackLabelIndex would refer to a label
        higher up the label stack and would be popped at a
        downstream LSR before a label represented by a
        higher ibmplsLabelStackLabelIndex at a downstream
        LSR."

   ::= { ibmplsLabelStackEntry 2 }

ibmplsLabelStackLabel OBJECT-TYPE
   SYNTAX        IbMplsLabel
   MAX-ACCESS    read-create
   STATUS        current
   DESCRIPTION
       "The label to pushed."
   ::= { ibmplsLabelStackEntry 3 }

ibmplsLabelStackRowStatus OBJECT-TYPE
   SYNTAX        RowStatus
   MAX-ACCESS    read-create
   STATUS        current
   DESCRIPTION
       "For creating, modifying, and deleting this row."
   ::= { ibmplsLabelStackEntry 4 }
   
ibmplsLabelStackStorageType OBJECT-TYPE
   SYNTAX        StorageType
   MAX-ACCESS    read-create
   STATUS        current
   DESCRIPTION
       "Defines the storage type for this object."
   ::= { ibmplsLabelStackEntry 5 }

-- End of ibmplsLabelStackTable

-- Traffic Parameter table.

ibmplsTrafficParamIndexNext OBJECT-TYPE
   SYNTAX        Integer32 (0..2147483647)
   MAX-ACCESS    read-only
   STATUS        current
   DESCRIPTION
       "This object contains an appropriate value which will
        be used for ibmplsTrafficParamIndex when creating
        entries in the ibmplsTrafficParamTable.  The value 0
        indicates that no unassigned entries are available.
        To obtain the ibmplsTrafficParamIndex value for a new
        entry, the manager issues a management protocol
        retrieval operation to obtain the current value of
        this object.  After each retrieval operation, the
        agent should modify the value to reflect the next
        unassigned index.  After a manager retrieves a value
        the agent will determine through its local policy
        when this index value will be made available for
        reuse."
   ::= { ibmplsLsrObjects 13 }


ibmplsTrafficParamTable OBJECT-TYPE
   SYNTAX        SEQUENCE OF IbMplsTrafficParamEntry
   MAX-ACCESS    not-accessible
   STATUS        current
   DESCRIPTION
       "This table specifies the Traffic Parameter objects
        for in and out-segments."
   ::= { ibmplsLsrObjects 14 }

ibmplsTrafficParamEntry OBJECT-TYPE
   SYNTAX        IbMplsTrafficParamEntry
   MAX-ACCESS    not-accessible
   STATUS        current
   DESCRIPTION
       "An entry in this table represents the TrafficParam
        objects for one or more in or out segments.  A
        single entry can be pointed to by multiple segments
        indicating resource sharing."
   INDEX         { ibmplsTrafficParamIndex }
      ::= { ibmplsTrafficParamTable 1 }

IbMplsTrafficParamEntry ::= SEQUENCE {
      ibmplsTrafficParamIndex           Integer32,
      ibmplsTrafficParamMaxRate         IbMplsBitRate,
      ibmplsTrafficParamMeanRate        IbMplsBitRate,
      ibmplsTrafficParamMaxBurstSize    IbMplsBurstSize,
      ibmplsTrafficParamRowStatus       RowStatus,
      ibmplsTrafficParamStorageType     StorageType
   }

ibmplsTrafficParamIndex OBJECT-TYPE
   SYNTAX        Integer32 (1..2147483647)
   MAX-ACCESS    not-accessible
   STATUS        current
   DESCRIPTION
       "Uniquely identifies this row of the table.  Note
        that zero represents an invalid index."
   ::= { ibmplsTrafficParamEntry 1 }

ibmplsTrafficParamMaxRate OBJECT-TYPE
   SYNTAX        IbMplsBitRate
   UNITS         "kilobits per second"
   MAX-ACCESS    read-create
   STATUS        current
   DESCRIPTION
       "Maximum rate in kilobits/second."
   ::= { ibmplsTrafficParamEntry 2 }

ibmplsTrafficParamMeanRate OBJECT-TYPE
   SYNTAX        IbMplsBitRate
   UNITS         "kilobits per second"
   MAX-ACCESS    read-create
   STATUS        current
   DESCRIPTION
       "Mean rate in kilobits/second."
   ::= { ibmplsTrafficParamEntry 3 }

ibmplsTrafficParamMaxBurstSize OBJECT-TYPE
   SYNTAX        IbMplsBurstSize
   UNITS         "bytes"
   MAX-ACCESS    read-create
   STATUS        current
   DESCRIPTION
       "Maximum burst size in bytes."
   ::= { ibmplsTrafficParamEntry 4 }

ibmplsTrafficParamRowStatus OBJECT-TYPE
   SYNTAX        RowStatus
   MAX-ACCESS    read-create
   STATUS        current
   DESCRIPTION
       "For creating, modifying, and deleting this row."
   ::= { ibmplsTrafficParamEntry 5 }
   
ibmplsTrafficParamStorageType OBJECT-TYPE
   SYNTAX        StorageType
   MAX-ACCESS    read-create
   STATUS        current
   DESCRIPTION
       "The storage type for this object."
   ::= { ibmplsTrafficParamEntry 6 }

-- End of ibmplsTrafficParamTable

-- Notification Configuration

ibmplsXCTrapEnable OBJECT-TYPE
   SYNTAX        TruthValue
   MAX-ACCESS    read-write
   STATUS        current
   DESCRIPTION
       "If this object is true, then it enables the
        generation of ibmplsXCUp and ibmplsXCDown traps,
        otherwise these traps are not emitted."
   DEFVAL { false }
   ::= { ibmplsLsrObjects 15 }

-- Cross-connect.

ibmplsXCUp NOTIFICATION-TYPE
   OBJECTS     { ibmplsXCIndex,
                  ibmplsInSegmentIfIndex,
                  ibmplsInSegmentLabel,
                  ibmplsOutSegmentIndex,
                  ibmplsXCAdminStatus,
                  ibmplsXCOperStatus }
   STATUS      current
   DESCRIPTION
       "This notification is generated when a
        ibmplsXCOperStatus object for one of the configured
        cross-connect entries is about to leave the down
        state and transition into some other state (but not
        into the notPresent state).  This other state is
        indicated by the included value of
        ibmplsXCOperStatus."
   ::= { ibmplsLsrNotifyPrefix 1 }

ibmplsXCDown NOTIFICATION-TYPE
   OBJECTS     { ibmplsXCIndex,
                 ibmplsInSegmentIfIndex,
                 ibmplsInSegmentLabel,
                 ibmplsOutSegmentIndex,
                 ibmplsXCAdminStatus,
                 ibmplsXCOperStatus }
   STATUS      current
   DESCRIPTION
       "This notification is generated when a
        ibmplsXCOperStatus object for one of the configured
        cross-connect entries is about to enter the down
        state from some other state (but not from the
        notPresent state).  This other state is indicated by
        the included value of ibmplsXCOperStatus."
   ::= { ibmplsLsrNotifyPrefix 2 }

-- End of notifications.


-- Module compliance.

ibmplsLsrGroups
   OBJECT IDENTIFIER ::= { ibmplsLsrConformance 1 }

ibmplsLsrCompliances
   OBJECT IDENTIFIER ::= { ibmplsLsrConformance 2 }

ibmplsLsrModuleCompliance MODULE-COMPLIANCE
   STATUS current
   DESCRIPTION
       "Compliance statement for agents that support the
        MPLS LSR MIB."
   MODULE -- this module

      -- The mandatory groups have to be implemented
      -- by all LSRs.  However, they may all be supported
      -- as read-only objects in the case where manual
      -- configuration is unsupported.

      MANDATORY-GROUPS    { ibmplsInSegmentGroup,
                            ibmplsOutSegmentGroup,
                            ibmplsXCGroup,
                            ibmplsInterfaceGroup,
                            ibmplsPerfGroup,
                            ibmplsSegmentDiscontinuityGroup }

      GROUP ibmplsHCInSegmentPerfGroup
      DESCRIPTION
          "This group is mandatory for those in-segment
           entries for which the object
           ibmplsInSegmentOutOctets wraps around too
           quickly."

      GROUP ibmplsHCOutSegmentPerfGroup
      DESCRIPTION
          "This group is mandatory for those out-segment
           entries for which the object
           ibmplsOutSegmentOctets wraps around too quickly."
          
      GROUP ibmplsTrafficParamGroup
      DESCRIPTION
          "This group is mandatory for those LSRs that
           support QoS resource reservation."

      -- Depending on whether the device implements
      -- persistent cross-connects or not one of the
      -- following two groups is mandatory.

      GROUP ibmplsXCIsPersistentGroup
      DESCRIPTION
          "This group is mandatory for devices which
           support persistent cross-connects.  The
           following constraints apply: ibmplsXCIsPersistent
           must at least be read-only returning true(2)."

      GROUP ibmplsXCIsNotPersistentGroup
      DESCRIPTION
          "This group is mandatory for devices which
           support non-persistent cross-connects.  The
           following constraints apply: ibmplsXCIsPersistent
           must at least be read-only returning false(1)."

      -- ibmplsInterfaceConfTable

      OBJECT      ibmplsInterfaceConfStorageType
      SYNTAX      INTEGER { other(1) }
      MIN-ACCESS  read-only
      DESCRIPTION
          "Only other(1) needs to be supported."
      
      -- ibmplsInSegmentTable
          
      OBJECT     ibmplsInSegmentXCIndex
      DESCRIPTION
          "Write access is not required."

      OBJECT      ibmplsInSegmentNPop
      MIN-ACCESS  read-only
      DESCRIPTION
          "Write access if not required.  This object
           should be set to 1 if it is read-only."

      OBJECT      ibmplsInSegmentAddrFamily
      DESCRIPTION
          "Write access is not required.  A <value of
           other(0) should be supported because there may
           be cases where the agent may not know about or
           support any address types."

      OBJECT      ibmplsInSegmentStorageType
      SYNTAX      INTEGER { other(1) }
      MIN-ACCESS  read-only

      DESCRIPTION
          "Only other(1) needs to be supported."

      -- ibmplsOutSegmentTable

      OBJECT      ibmplsOutSegmentIfIndex
      MIN-ACCESS  read-only
      DESCRIPTION
          "Write access is not required."
      
      OBJECT      ibmplsOutSegmentPushTopLabel
      MIN-ACCESS  read-only
      DESCRIPTION
          "Write access is not required."

      OBJECT      ibmplsOutSegmentTopLabel
      MIN-ACCESS  read-only
      DESCRIPTION
          "Write access is not required."

      OBJECT      ibmplsOutSegmentNextHopIpAddrType
      MIN-ACCESS  read-only
      DESCRIPTION
          "ipV6(3) need not be supported."

      OBJECT      ibmplsOutSegmentNextHopIpv4Addr
      MIN-ACCESS  read-only
      DESCRIPTION
          "Write access is not required."

      OBJECT      ibmplsOutSegmentNextHopIpv6Addr
      MIN-ACCESS  read-only
      DESCRIPTION
          "Write access is not required."

      OBJECT      ibmplsOutSegmentRowStatus
      SYNTAX      INTEGER { active(1), notInService(2),
                            createAndGo(4), destroy(6) }
      MIN-ACCESS  read-only
      DESCRIPTION
          "The notReady(3) and createAndWait(5) states need
           not be supported."
      OBJECT      ibmplsOutSegmentStorageType
      SYNTAX      INTEGER { other(1) }
      MIN-ACCESS  read-only
      DESCRIPTION
          "Only other(1) needs to be supported."

      -- ibmplsXCTable

      OBJECT      ibmplsXCLabelStackIndex
      MIN-ACCESS  read-only
      DESCRIPTION
          "Write access is not required."

      OBJECT      ibmplsXCIsPersistent
      MIN-ACCESS  read-only
      DESCRIPTION
          "Write access is not required."

      OBJECT      ibmplsXCAdminStatus
      SYNTAX      INTEGER { up(1), down(2) }
      MIN-ACCESS  read-only
      DESCRIPTION
          "A value of testing(3) need not be supported."

      OBJECT      ibmplsXCOperStatus
      SYNTAX      INTEGER { up(1), down(2) }
      DESCRIPTION
          "Only up(1) and down(2) need to be supported."
      
      OBJECT      ibmplsXCRowStatus
      SYNTAX      INTEGER { active(1),
                             notInService(2),
                             createAndGo(4),
                             destroy(6) }
      MIN-ACCESS  read-only
      DESCRIPTION
          "The notReady(3) and createAndWait(5) states need
           not be supported."
      
      OBJECT      ibmplsXCStorageType
      SYNTAX      INTEGER { other(1) }
      MIN-ACCESS  read-only
      DESCRIPTION
          "Only other(1) needs to be supported."

   ::= { ibmplsLsrCompliances 1 }

-- Units of conformance.

ibmplsInterfaceGroup OBJECT-GROUP
   OBJECTS { ibmplsInterfaceLabelMinIn,
             ibmplsInterfaceLabelMaxIn,
             ibmplsInterfaceLabelMinOut,
             ibmplsInterfaceLabelMaxOut,
             ibmplsInterfaceTotalBandwidth,
             ibmplsInterfaceAvailableBandwidth,
             ibmplsInterfaceLabelParticipationType,
             ibmplsInterfaceConfStorageType
          }
             
   STATUS  current
   DESCRIPTION
          "Collection of objects needed for MPLS interface
           configuration and performance information."
   ::= { ibmplsLsrGroups 1 }

ibmplsInSegmentGroup  OBJECT-GROUP
             OBJECTS { ibmplsInSegmentNPop,
             ibmplsInSegmentAddrFamily,
             ibmplsInSegmentXCIndex,
             ibmplsInSegmentOctets,
             ibmplsInSegmentDiscards,
             ibmplsInSegmentOwner,
             ibmplsInSegmentRowStatus,
             ibmplsInSegmentStorageType,
             ibmplsInSegmentTrafficParamPtr
          }
   STATUS  current
   DESCRIPTION
          "Collection of objects needed to implement an in-
           segment."
   ::= { ibmplsLsrGroups 2 }

ibmplsOutSegmentGroup  OBJECT-GROUP
   OBJECTS { ibmplsOutSegmentIndexNext,
             ibmplsOutSegmentIfIndex,
             ibmplsOutSegmentPushTopLabel,
             ibmplsOutSegmentTopLabel,
             ibmplsOutSegmentNextHopIpAddrType,
             ibmplsOutSegmentNextHopIpv4Addr,
             ibmplsOutSegmentNextHopIpv6Addr,
             ibmplsOutSegmentXCIndex,
             ibmplsOutSegmentOwner,
             ibmplsOutSegmentOctets,
             ibmplsOutSegmentDiscards,
             ibmplsOutSegmentErrors,
             ibmplsOutSegmentRowStatus,
             ibmplsOutSegmentStorageType,
             ibmplsOutSegmentTrafficParamPtr
          }
   STATUS  current
   DESCRIPTION
          "Collection of objects needed to implement an out-
           segment."
   ::= { ibmplsLsrGroups 3 }

ibmplsXCGroup  OBJECT-GROUP
   OBJECTS { ibmplsXCIndexNext,
             ibmplsXCLabelStackIndex,
             ibmplsXCOwner,
             ibmplsXCAdminStatus,
             ibmplsXCOperStatus,
             ibmplsXCRowStatus,
             ibmplsXCTrapEnable,
             ibmplsXCStorageType
          }
   STATUS  current
   DESCRIPTION
          "Collection of objects needed to implement a
           cross-connect entry."
   ::= { ibmplsLsrGroups 4 }

ibmplsXCOptionalGroup  OBJECT-GROUP
   OBJECTS { ibmplsXCLspId }
   STATUS  current
   DESCRIPTION
          "Collection of optional objects for implementing 
           a cross-connect entry."
   ::= { ibmplsLsrGroups 5 }

ibmplsPerfGroup OBJECT-GROUP
   OBJECTS { ibmplsInSegmentOctets,
             ibmplsInSegmentPackets,
             ibmplsInSegmentErrors,
             ibmplsInSegmentDiscards,
             ibmplsOutSegmentOctets,
             ibmplsOutSegmentPackets,
             ibmplsOutSegmentDiscards,
             ibmplsInterfaceInLabelsUsed,
             ibmplsInterfaceFailedLabelLookup,
             ibmplsInterfaceOutFragments,
             ibmplsInterfaceOutLabelsUsed
          }
   
   STATUS  current
   DESCRIPTION
          "Collection of objects providing performance
           information
        about an LSR."
   ::= { ibmplsLsrGroups 6 }

ibmplsHCInSegmentPerfGroup OBJECT-GROUP
   OBJECTS { ibmplsInSegmentHCOctets }
   STATUS  current
   DESCRIPTION
          "Object(s) providing performance information
           specific to out-segments for which the object
           ibmplsInterfaceInOctets wraps around too quickly."
   ::= { ibmplsLsrGroups 7 }

ibmplsHCOutSegmentPerfGroup OBJECT-GROUP
   OBJECTS { ibmplsOutSegmentHCOctets }
   STATUS  current
   DESCRIPTION
          "Object(s) providing performance information
           specific to out-segments for which the object
           ibmplsInterfaceOutOctets wraps around too
           quickly."
   ::= { ibmplsLsrGroups 8 }
   
ibmplsTrafficParamGroup OBJECT-GROUP
   OBJECTS { ibmplsTrafficParamIndexNext,
             ibmplsTrafficParamMaxRate,
             ibmplsTrafficParamMeanRate,
             ibmplsTrafficParamMaxBurstSize,
             ibmplsTrafficParamRowStatus,
             ibmplsTrafficParamStorageType
          }
   STATUS  current
   DESCRIPTION
          "Object(s) required for supporting QoS resource
           reservation."
   ::= { ibmplsLsrGroups 9 }

ibmplsXCIsPersistentGroup OBJECT-GROUP
   OBJECTS { ibmplsXCIsPersistent }
   STATUS  current
   DESCRIPTION
          "Objects needed to support persistent cross-
           connects."
   ::= { ibmplsLsrGroups 10 }

ibmplsXCIsNotPersistentGroup OBJECT-GROUP
   OBJECTS { ibmplsXCIsPersistent }
   STATUS  current
   DESCRIPTION
          "Objects needed to support non-persistent cross-
           connects."
   ::= { ibmplsLsrGroups 11 }
   
ibmplsLabelStackGroup OBJECT-GROUP
   OBJECTS { ibmplsLabelStackLabel,
             ibmplsLabelStackRowStatus,
             ibmplsLabelStackStorageType,
             ibmplsMaxLabelStackDepth,
             ibmplsLabelStackIndexNext }
   STATUS current
   DESCRIPTION
          "Objects needed to support label stacking."
      ::= { ibmplsLsrGroups 12 }
      
ibmplsSegmentDiscontinuityGroup OBJECT-GROUP
   OBJECTS { ibmplsInSegmentPerfDiscontinuityTime,
             ibmplsOutSegmentPerfDiscontinuityTime
          }
   
   STATUS  current
   DESCRIPTION
       " A collection of objects providing information
        specific to segment discontinuities.."
   ::= { ibmplsLsrGroups 13 }
      

ibmplsLsrNotificationGroup NOTIFICATION-GROUP
   NOTIFICATIONS { ibmplsXCUp,
                   ibmplsXCDown }
   STATUS  current
   DESCRIPTION
          "Set of notifications implemented in this module.
           None is mandatory."
   ::= { ibmplsLsrGroups 14 }

-- End of MPLS-LSR-MIB
END
