-- ==================================================================
-- Copyright (C) 2023 Intelbras S.A. All rights reserved.
--
-- Description: Igmp snooping MIB
-- Reference:
-- Version: V1.4
-- History:
--(1) Created by Zhangshilin, 2001.06.29
--(2) Revised by Qi Zhenglin, 2002.1.8
-- V1.1 2004-10-12 updated by gaolong
--        Import TEXTUAL-CONVENTION.
--        Relocate ibLswIgmpsnoopingMib MODULE-IDENTITY clause.
-- V1.2 Revised by yaochunyan, 2004.11.28
--        V1.2 Add ibIgmpSnoopingGroupLimitTable,
--        ibIgmpSnoopingFastLeaveTable and
--        ibIgmpSnoopingGroupPolicyTable.
--      Adjust format of the whole file by gaolong.
-- V1.3 2005-3-9 updated by fuzhenyu
--       Add object ibIgmpSnoopingNonFloodingStatus.
--       Change the descriptions of ibIgmpSnoopingGroupIfIndex,
--       ibIgmpSnoopingFastLeaveIfIndex, ibIgmpSnoopingGroupPolicyIfIndex
-- V1.4 2005-3-22 updated by wangxiaodong
--      Add ibIgmpSnoopingVlanStatusTable
--      Add ibRecvIGMPGQueryNum, ibRecvIGMPSQueryNum,
--          ibRecvIGMPV1ReportNum, ibRecvIGMPV2ReportNum,
--          ibRecvIGMPLeaveNum, ibRecvErrorIGMPPacketNum,
--          ibSentIGMPSQueryNum, ibIgmpSnoopingClearStats
--      Adjust file format
-- ==================================================================
--
-- ==================================================================
--
-- Varibles and types be imported
--
-- ==================================================================
IB-LswIGSP-MIB DEFINITIONS ::= BEGIN
IMPORTS

    Integer32,MODULE-IDENTITY,OBJECT-TYPE,Unsigned32,Counter32
        FROM SNMPv2-SMI

    TEXTUAL-CONVENTION,RowStatus
        FROM SNMPv2-TC

    iblswCommon
        FROM IB-OID-MIB

    InterfaceIndex
        FROM IF-MIB;

    ibLswIgmpsnoopingMib MODULE-IDENTITY
        LAST-UPDATED "200106290000Z"
        ORGANIZATION
            "Intelbras S.A. Industria de Telecomunicacao Eletronica Brasileria."
        CONTACT-INFO
            ""
        DESCRIPTION
            ""
        REVISION "200106290000Z"
        DESCRIPTION
            ""
        ::= { iblswCommon  7 }

    EnabledStatus ::= TEXTUAL-CONVENTION
        STATUS      current
        DESCRIPTION
            "A simple status value for the object."
        SYNTAX      INTEGER { enabled(1), disabled(2) }


-- ==================================================================
--
-- ======================= definition begin =========================
--
-- ==================================================================

    ibLswIgmpsnoopingMibObject OBJECT IDENTIFIER ::= {   ibLswIgmpsnoopingMib 1  }

    ibIgmpSnoopingStatus    OBJECT-TYPE
        SYNTAX  EnabledStatus
        MAX-ACCESS read-write
        STATUS current
        DESCRIPTION "Configure to enable IGMP Snooping."
        ::= { ibLswIgmpsnoopingMibObject  1 }

    ibIgmpSnoopingRouterPortAge  OBJECT-TYPE
        SYNTAX  INTEGER (1..1000)
        MAX-ACCESS read-write
        STATUS current
        DESCRIPTION "Configure the aging time of the router port."
        DEFVAL  {105}
        ::= { ibLswIgmpsnoopingMibObject  2 }

    ibIgmpSnoopingResponseTime  OBJECT-TYPE
        SYNTAX  INTEGER   (1..25)
        MAX-ACCESS read-write
        STATUS current
        DESCRIPTION "Configure the maximum query response time."
        DEFVAL  {10}
        ::= { ibLswIgmpsnoopingMibObject  3 }

    ibIgmpSnoopingHostTime   OBJECT-TYPE
        SYNTAX  INTEGER  (200..1000)
        MAX-ACCESS read-write
        STATUS current
        DESCRIPTION "Configure the aging time of the multicast group port."
        DEFVAL  {260}
        ::= { ibLswIgmpsnoopingMibObject  4 }

    ibIgmpSnoopingGroupLimitTable OBJECT-TYPE
        SYNTAX  SEQUENCE OF IbIgmpSnoopingGroupLimitEntry
        MAX-ACCESS not-accessible
        STATUS current
        DESCRIPTION
            "The table lists the maximum group number that one
             interface could do IGMP Snooping."
        ::= { ibLswIgmpsnoopingMibObject  5 }

    ibIgmpSnoopingGroupLimitEntry OBJECT-TYPE
        SYNTAX  IbIgmpSnoopingGroupLimitEntry
        MAX-ACCESS not-accessible
        STATUS current
        DESCRIPTION
            "An entry (conceptual row) representing  the maximum
             group number on an interface which IGMP Snooping operation
             is enabled."
        INDEX  { ibIgmpSnoopingGroupIfIndex }
        ::= { ibIgmpSnoopingGroupLimitTable 1 }

    IbIgmpSnoopingGroupLimitEntry ::= SEQUENCE {
        ibIgmpSnoopingGroupIfIndex    InterfaceIndex,
        ibIgmpSnoopingGroupLimitNumber  Unsigned32
        }

    ibIgmpSnoopingGroupIfIndex OBJECT-TYPE
        SYNTAX  InterfaceIndex
        MAX-ACCESS not-accessible
        STATUS current
        DESCRIPTION
            "The ifIndex value of the port on which IGMP
             snooping is enabled."
        ::= { ibIgmpSnoopingGroupLimitEntry 1 }

    ibIgmpSnoopingGroupLimitNumber OBJECT-TYPE
        SYNTAX  Unsigned32
        MAX-ACCESS read-write
        STATUS current
        DESCRIPTION
            "The maxmum group number of IGMP Snooping on a port."
        DEFVAL  { 4294967295 }
        ::= { ibIgmpSnoopingGroupLimitEntry 2 }

    ibIgmpSnoopingFastLeaveTable OBJECT-TYPE
        SYNTAX  SEQUENCE OF IbIgmpSnoopingFastLeaveEntry
        MAX-ACCESS not-accessible
        STATUS current
        DESCRIPTION
            "The table specifies the fast leave status
             on those ports that do IGMP Snooping."
        ::= { ibLswIgmpsnoopingMibObject  6 }

    ibIgmpSnoopingFastLeaveEntry OBJECT-TYPE
        SYNTAX  IbIgmpSnoopingFastLeaveEntry
        MAX-ACCESS not-accessible
        STATUS current
        DESCRIPTION
            "An entry specifies the fast leave status
             on those ports that do IGMP Snooping."
        INDEX  { ibIgmpSnoopingFastLeaveIfIndex }
        ::= { ibIgmpSnoopingFastLeaveTable 1 }

    IbIgmpSnoopingFastLeaveEntry ::= SEQUENCE {
        ibIgmpSnoopingFastLeaveIfIndex  InterfaceIndex,
        ibIgmpSnoopingFastLeaveStatus  EnabledStatus
        }

    ibIgmpSnoopingFastLeaveIfIndex OBJECT-TYPE
        SYNTAX  InterfaceIndex
        MAX-ACCESS not-accessible
        STATUS current
        DESCRIPTION
            "The ifIndex value of the port on which IGMP
             snooping is enabled."
        ::= { ibIgmpSnoopingFastLeaveEntry 1 }

    ibIgmpSnoopingFastLeaveStatus OBJECT-TYPE
        SYNTAX  EnabledStatus
        MAX-ACCESS read-write
        STATUS current
        DESCRIPTION
            "The fast leave status of the port on which IGMP
             Snooping is enabled."
        DEFVAL  { 2 }
        ::= { ibIgmpSnoopingFastLeaveEntry 2 }

    ibIgmpSnoopingGroupPolicyTable OBJECT-TYPE
        SYNTAX  SEQUENCE OF IbIgmpSnoopingGroupPolicyEntry
        MAX-ACCESS not-accessible
        STATUS current
        DESCRIPTION
            "This is a table specifies the group policy parameter and
             Vlan ID of the IGMP Snooping port."
        ::= { ibLswIgmpsnoopingMibObject  7 }

    ibIgmpSnoopingGroupPolicyEntry OBJECT-TYPE
        SYNTAX  IbIgmpSnoopingGroupPolicyEntry
        MAX-ACCESS not-accessible
        STATUS current
        DESCRIPTION
            "An entry representing the group policy parameter and Vlan ID
             of a port on which IGMP Snooping operation is enabled."
        INDEX  { ibIgmpSnoopingGroupPolicyIfIndex,
            ibIgmpSnoopingGroupPolicyVlanID }
        ::= { ibIgmpSnoopingGroupPolicyTable 1 }

    IbIgmpSnoopingGroupPolicyEntry ::= SEQUENCE {
        ibIgmpSnoopingGroupPolicyIfIndex  InterfaceIndex,
        ibIgmpSnoopingGroupPolicyVlanID  Integer32,
        ibIgmpSnoopingGroupPolicyParameter  Integer32,
        ibIgmpSnoopingGroupPolicyStatus  RowStatus
        }

    ibIgmpSnoopingGroupPolicyIfIndex OBJECT-TYPE
        SYNTAX  InterfaceIndex
        MAX-ACCESS not-accessible
        STATUS current
        DESCRIPTION
            "The ifIndex value of the port on which
             IGMP Snooping is enabled."
        ::= { ibIgmpSnoopingGroupPolicyEntry 1 }

    ibIgmpSnoopingGroupPolicyVlanID OBJECT-TYPE
        SYNTAX  Integer32(1..4094)
        MAX-ACCESS not-accessible
        STATUS current
        DESCRIPTION
            "The Vlan ID which the IGMP Snooping port
             is attached to."
        ::= { ibIgmpSnoopingGroupPolicyEntry 2 }

    ibIgmpSnoopingGroupPolicyParameter OBJECT-TYPE
        SYNTAX  Integer32(2000..2999)
        MAX-ACCESS read-create
        STATUS current
        DESCRIPTION
            "The ACL Number which is used as the group policy parameter
             of the IGMP Snooping port."
        ::= { ibIgmpSnoopingGroupPolicyEntry 3 }

    ibIgmpSnoopingGroupPolicyStatus OBJECT-TYPE
        SYNTAX  RowStatus
        MAX-ACCESS read-create
        STATUS current
        DESCRIPTION
            "This object is used to create or delete a row
             and represent the current status of this row.
             Now support three state:CreateAndGo,Active,Destroy."
        ::= { ibIgmpSnoopingGroupPolicyEntry 4 }

    ibIgmpSnoopingNonFloodingStatus OBJECT-TYPE
        SYNTAX EnabledStatus
        MAX-ACCESS read-write
        STATUS current
        DESCRIPTION
            "Configure to disable multicast flooding when no member exists
             in the destinated group. To use this function,IGMP snooping
             must be enabled."
        ::= { ibLswIgmpsnoopingMibObject 8 }

    ibIgmpSnoopingVlanStatusTable OBJECT-TYPE
        SYNTAX     SEQUENCE OF IbIgmpSnoopingVlanStatusEntry
        MAX-ACCESS not-accessible
        STATUS     current
        DESCRIPTION
            "The table used to enable or disable IGMP snooping 
             on the specified VLAN."
        ::= { ibLswIgmpsnoopingMibObject 9 }

    ibIgmpSnoopingVlanStatusEntry OBJECT-TYPE
        SYNTAX     IbIgmpSnoopingVlanStatusEntry
        MAX-ACCESS not-accessible
        STATUS     current
        DESCRIPTION
            "An entry representing the IGMP snooping status on 
             the specified VLAN."
        INDEX      {  ibIgmpSnoopingVlanID }
        ::= { ibIgmpSnoopingVlanStatusTable 1 }

    IbIgmpSnoopingVlanStatusEntry ::= SEQUENCE {
        ibIgmpSnoopingVlanID            Integer32,
        ibIgmpSnoopingVlanEnabled       EnabledStatus
        }
        
    ibIgmpSnoopingVlanID OBJECT-TYPE
        SYNTAX     Integer32(1..4094)
        MAX-ACCESS not-accessible
        STATUS     current
        DESCRIPTION
            "An index uniquely identifies on which VLAN IGMP 
             snooping is enabled or disabled. "
        ::= { ibIgmpSnoopingVlanStatusEntry 1 }

    ibIgmpSnoopingVlanEnabled OBJECT-TYPE
        SYNTAX     EnabledStatus
        MAX-ACCESS read-write
        STATUS     current
        DESCRIPTION
            "Indicating whether IGMP snooping is enabled on this VLAN."
        DEFVAL     { disabled }
        ::= { ibIgmpSnoopingVlanStatusEntry 2 }

    ibIgmpSnoopingStatsObjects OBJECT IDENTIFIER ::= { ibLswIgmpsnoopingMibObject 10 }

    ibRecvIGMPGQueryNum OBJECT-TYPE
        SYNTAX     Counter32
        MAX-ACCESS read-only
        STATUS     current
        DESCRIPTION
            "The statistics of IGMP general query packets received on
             the device."
        ::= { ibIgmpSnoopingStatsObjects 1 }

    ibRecvIGMPSQueryNum OBJECT-TYPE
        SYNTAX     Counter32
        MAX-ACCESS read-only
        STATUS     current
        DESCRIPTION
            "The statistics of IGMP specific query packets received on
             the device."
        ::= { ibIgmpSnoopingStatsObjects 2 }

    ibRecvIGMPV1ReportNum OBJECT-TYPE
        SYNTAX     Counter32
        MAX-ACCESS read-only
        STATUS     current
        DESCRIPTION
            "The statistics of IGMP V1 report packets received on
             the device."
        ::= { ibIgmpSnoopingStatsObjects 3 }

    ibRecvIGMPV2ReportNum OBJECT-TYPE
        SYNTAX     Counter32
        MAX-ACCESS read-only
        STATUS     current
        DESCRIPTION
            "The statistics of IGMP V2 report packets received on
             the device."
        ::= { ibIgmpSnoopingStatsObjects 4 }

    ibRecvIGMPLeaveNum OBJECT-TYPE
        SYNTAX     Counter32
        MAX-ACCESS read-only
        STATUS     current
        DESCRIPTION
            "The statistics of IGMP leave packets received on
             the device."
        ::= { ibIgmpSnoopingStatsObjects 5 }

    ibRecvErrorIGMPPacketNum OBJECT-TYPE
        SYNTAX     Counter32
        MAX-ACCESS read-only
        STATUS     current
        DESCRIPTION
            "The statistics of error IGMP packets received on
             the device."
        ::= { ibIgmpSnoopingStatsObjects 6 }

    ibSentIGMPSQueryNum OBJECT-TYPE
        SYNTAX     Counter32
        MAX-ACCESS read-only
        STATUS     current
        DESCRIPTION
            "The statistics of IGMP specific query packets sent from
             the device."
        ::= { ibIgmpSnoopingStatsObjects 7 }

    ibIgmpSnoopingClearStats  OBJECT-TYPE
        SYNTAX     INTEGER { clear(1),
                             counting(2)
                           }
        MAX-ACCESS read-write
        STATUS     current
        DESCRIPTION
            "The configuration to clear the statistics of IGMP packets."
        DEFVAL  { counting }
        ::= { ibIgmpSnoopingStatsObjects 8 }

        
END
