-- =========================================================================
-- Copyright (C) 2023 Intelbras S.A. All rights reserved.
--
-- Description: Secure Shell(SSH) MIB
-- Reference: draft-ylonen-ssh-protocol-00.txt
-- Version: V1.7
-- History:
--  V1.0 2007-11-19 created by ZhangJun 03132
--       Initial version.
--  V1.1 2013-12-21 Added enum value scp(5) to ibSSHUserServiceType by DaiRuiqiang 04358.
--  V1.2 2014-01-17 Added enum value scp(4) to ibSSHSessionServiceType by DaiRuiqiang 04358.
--       2014-02-20 Added ibSCPServerEnable and ibSTelnetServerEnable by DaiRuiqiang 04358.
--  V1.3 2014-10-25 Added enum value netconf(6) to ibSSHUserServiceType,
--                  added enum value netconf(5) to ibSSHSessionServiceType by DaiRuiqiang 04358.
--  V1.4 2016-04-26 Added ibSSHUserPublicKeyName2 to IbSSHUserConfigEntry,
--                  added ibSSHUserPublicKeyName3 to IbSSHUserConfigEntry,
--                  added ibSSHUserPublicKeyName4 to IbSSHUserConfigEntry,
--                  added ibSSHUserPublicKeyName5 to IbSSHUserConfigEntry,
--                  added ibSSHUserPublicKeyName6 to IbSSHUserConfigEntry by DaiRuiqiang 04358.
--                  Added enum values aes128CTR(5), aes192CTR(6), aes256CTR(7), aes128GCM(8),
--                  aes256GCM(9), and aes256CBC(10) to ibSSHSessionEncry by DaiRuiqiang 04358.
--       2018-02-06 Added enum value keyboard-interactive(6) in ibSSHUserAuthType by DaiRuiqiang 04358
--  V1.5 2018-06-28 Added enum value other(11) to ibSSHSessionEncry by DaiRuiqiang 04358.
--  V1.6 2021-09-15 Added ibSSHUserAuthFailureTime to ibSSHUserAuthFailure by yinwenyao kf8812
--                  Added ibSSHSessionLoginTime to ibSSHUserLogin by yinwenyao kf8812
--                  Added ibSSHSessionUserRoleName to ibSSHUserLogin by yinwenyao kf8812
--                  Added ibSSHSessionLogoffTime to ibSSHUserLogoff by yinwenyao kf8812
--                  Added ibSSHSessionUserRoleName to ibSSHUserLogoff by yinwenyao kf8812
--  V1.7 2022-05-31 Added ibSSHLoginFailedTimes to ibSSHServerObjForTrap by zhangfeng kf9168.
--                  Added ibSSHStatisticPeriod to ibSSHServerObjForTrap by zhangfeng kf9168.
--                  Added ibSSHLoginFailed to ibSSHServerNotificationsPrefix by zhangfeng kf9168.
--                  Added ibSSHLoginFailedClear to ibSSHServerNotificationsPrefix by zhangfeng kf9168.
-- =========================================================================
IB-SSH-MIB DEFINITIONS ::= BEGIN

IMPORTS
        ibCommon
    FROM IB-OID-MIB
        Integer32, OBJECT-TYPE, MODULE-IDENTITY, NOTIFICATION-TYPE, Unsigned32
    FROM SNMPv2-SMI
        InetAddressType, InetAddress
    FROM INET-ADDRESS-MIB
        DisplayString, RowStatus, DateAndTime
    FROM SNMPv2-TC;

ibSSH MODULE-IDENTITY
    LAST-UPDATED "202205310000Z"
    ORGANIZATION
        "Intelbras S.A. Industria de Telecomunicacao Eletronica Brasileria."
    CONTACT-INFO
        ""
    DESCRIPTION
        "This MIB is used to configure SSH server."
    REVISION "202205310000Z"
    DESCRIPTION
        "Added ibSSHLoginFailedTimes to ibSSHServerObjForTrap.
         Added ibSSHStatisticPeriod to ibSSHServerObjForTrap.
         Added ibSSHLoginFailed to ibSSHServerNotificationsPrefix.
         Added ibSSHLoginFailedClear to ibSSHServerNotificationsPrefix."
    REVISION "202109150000Z"
    DESCRIPTION
        "Added ibSSHUserAuthFailureTime to ibSSHUserAuthFailure.
         Added ibSSHSessionLoginTime and ibSSHSessionUserRoleName to ibSSHUserLogin.
         Added ibSSHSessionLogoffTime and ibSSHSessionUserRoleName to ibSSHUserLogoff."
    REVISION "201806280000Z"
    DESCRIPTION
        "Added enum value other(11) to ibSSHSessionEncry."
    REVISION "201802060000Z"
    DESCRIPTION
        "Added enum value keyboardInteractive(6) to ibSSHUserAuthType."
    REVISION "201604260000Z"
    DESCRIPTION
        "Added enum values aes128CTR(5), aes192CTR(6), aes256CTR(7), aes128GCM(8),
         aes256GCM(9), and aes256CBC(10) to ibSSHSessionEncry.
         Added ibSSHUserPublicKeyName2, and ibSSHUserPublicKeyName3, ibSSHUserPublicKeyName4,
         ibSSHUserPublicKeyName5, and ibSSHUserPublicKeyName6 to IbSSHUserConfigEntry."
    REVISION "201410250000Z"
    DESCRIPTION
        "Added enum value netconf(6) to ibSSHUserServiceType, add enum value netconf(5) to ibSSHSessionServiceType."
    REVISION "201402200000Z"
    DESCRIPTION
        "Added ibSCPServerEnable and ibSTelnetServerEnable."
    REVISION "201401170000Z"
    DESCRIPTION
        "Added enum value scp(4) to ibSSHSessionServiceType."
    REVISION "201312210000Z"
    DESCRIPTION
        "Added enum value scp(5) to ibSSHUserServiceType."
    REVISION "200711190000Z"
    DESCRIPTION
        "The initial version."
    ::= { ibCommon 22 }

--
-- Node definitions
--
-- Scalar MIB objects are defined in this section.
ibSSHServerMIB OBJECT IDENTIFIER ::= { ibSSH 1 }

ibSSHServerMIBObjects OBJECT IDENTIFIER ::= { ibSSHServerMIB 1 }

-- Scalar MIB objects, which are considered as global variables
-- to SSH server, are defined in this section.
ibSSHServerGlobalConfig OBJECT IDENTIFIER ::= { ibSSHServerMIBObjects 1 }

ibSSHServerVersion OBJECT-TYPE
    SYNTAX      DisplayString
    MAX-ACCESS  read-only
    STATUS      current
    DESCRIPTION
        "The protocol version of the SSH server."
    ::= { ibSSHServerGlobalConfig 1 }

ibSSHServerCompatibleSSH1x OBJECT-TYPE
    SYNTAX      INTEGER
        {
            enableCompatibleSSH1x(1),
            disableCompatibleSSH1x(2)
        }
    MAX-ACCESS  read-write
    STATUS      current
    DESCRIPTION
        "Supporting compatibility with SSH versions 1.x.  It is
        known that there are still devices using the previous
        versions.  During the transition period, it is important to
        be able to work in a way that is compatible with the
        installed SSH clients and servers that use the older version
        of the protocol."
    ::= { ibSSHServerGlobalConfig 2 }

ibSSHServerRekeyInterval OBJECT-TYPE
    SYNTAX      Integer32
    MAX-ACCESS  read-write
    STATUS      current
    DESCRIPTION
        "The time interval of regenerating SSH server key.  The unit
        is hour."
    ::= { ibSSHServerGlobalConfig 3 }

ibSSHServerAuthRetries OBJECT-TYPE
    SYNTAX      Integer32
    MAX-ACCESS  read-write
    STATUS      current
    DESCRIPTION
        "The limit times of a specified user can retry."
    ::= { ibSSHServerGlobalConfig 4 }

ibSSHServerAuthTimeout OBJECT-TYPE
    SYNTAX      Integer32
    MAX-ACCESS  read-write
    STATUS      current
    DESCRIPTION
        "The SSH server has a timeout for authentication and
        disconnect if the authentication has not been accepted
        within the timeout period.  The unit is second."
    ::= { ibSSHServerGlobalConfig 5 }

ibSFTPServerIdleTimeout OBJECT-TYPE
    SYNTAX      Integer32
    MAX-ACCESS  read-write
    STATUS      current
    DESCRIPTION
        "The SFTP server has a timeout for idle connection if a user
        has no activities within the timeout period.  The unit is
        minute."
    ::= { ibSSHServerGlobalConfig 6 }

ibSSHServerEnable OBJECT-TYPE
    SYNTAX      INTEGER
        {
            enableSSHServer(1),
            disableSSHServer(2)
        }
    MAX-ACCESS  read-write
    STATUS      current
    DESCRIPTION
        "Enable SSH server function."
    ::= { ibSSHServerGlobalConfig 7 }

ibSFTPServerEnable OBJECT-TYPE
    SYNTAX      INTEGER
        {
            enableSFTPService(1),
            disableSFTPService(2)
        }
    MAX-ACCESS  read-write
    STATUS      current
    DESCRIPTION
        "Enable SFTP server function."
    ::= { ibSSHServerGlobalConfig 8 }

ibSTelnetServerEnable OBJECT-TYPE
    SYNTAX      INTEGER
        {
            enableSTelnetServer(1),
            disableSTelnetServer(2)
        }
    MAX-ACCESS  read-write
    STATUS      current
    DESCRIPTION
        "Enable STelnet server function."
    ::= { ibSSHServerGlobalConfig 9 }

ibSCPServerEnable OBJECT-TYPE
    SYNTAX      INTEGER
        {
            enableSCPService(1),
            disableSCPService(2)
        }
    MAX-ACCESS  read-write
    STATUS      current
    DESCRIPTION
        "Enable SCP server function."
    ::= { ibSSHServerGlobalConfig 10 }

-- SSH users are defined in this section.
ibSSHUserConfig OBJECT IDENTIFIER ::= { ibSSHServerMIBObjects 2 }

-- Define a group which consists of all objects used for users.
ibSSHUserConfigTable OBJECT-TYPE
    SYNTAX      SEQUENCE OF IbSSHUserConfigEntry
    MAX-ACCESS  not-accessible
    STATUS      current
    DESCRIPTION
        "A table for managing SSH users."
    ::= { ibSSHUserConfig 1 }

ibSSHUserConfigEntry OBJECT-TYPE
    SYNTAX      IbSSHUserConfigEntry
    MAX-ACCESS  not-accessible
    STATUS      current
    DESCRIPTION
        "SSH users configuration entry."
    INDEX
        {
            ibSSHUserName
        }
    ::= { ibSSHUserConfigTable 1 }

IbSSHUserConfigEntry ::= SEQUENCE
    {
        ibSSHUserName             DisplayString,
        ibSSHUserServiceType      INTEGER,
        ibSSHUserAuthType         INTEGER,
        ibSSHUserPublicKeyName    DisplayString,
        ibSSHUserWorkDirectory    DisplayString,
        ibSSHUserRowStatus        RowStatus,
        ibSSHUserPublicKeyName2    DisplayString,
        ibSSHUserPublicKeyName3    DisplayString,
        ibSSHUserPublicKeyName4    DisplayString,
        ibSSHUserPublicKeyName5    DisplayString,
        ibSSHUserPublicKeyName6    DisplayString
    }

ibSSHUserName OBJECT-TYPE
    SYNTAX      DisplayString
    MAX-ACCESS  not-accessible
    STATUS      current
    DESCRIPTION
        "The name of SSH user."
    ::= { ibSSHUserConfigEntry 1 }

ibSSHUserServiceType OBJECT-TYPE
    SYNTAX      INTEGER
        {
            invalid(1),
            all(2),
            stelnet(3),
            sftp(4),
            scp(5),
            netconf(6)
        }
    MAX-ACCESS  read-create
    STATUS      current
    DESCRIPTION
        "The service type of SSH user uses."
    DEFVAL      { invalid }
    ::= { ibSSHUserConfigEntry 2 }

ibSSHUserAuthType OBJECT-TYPE
    SYNTAX      INTEGER
        {
            invalid(1),
            password(2),
            publicKey(3),
            any(4),
            publicKeyPassword(5),
            keyboardInteractive(6)
        }
    MAX-ACCESS  read-create
    STATUS      current
    DESCRIPTION
        "The authentication type of SSH user chooses."
    DEFVAL      { invalid }
    ::= { ibSSHUserConfigEntry 3 }

ibSSHUserPublicKeyName OBJECT-TYPE
    SYNTAX      DisplayString
    MAX-ACCESS  read-create
    STATUS      current
    DESCRIPTION
        "The public key which is used for authentication.
        A maximum of 6 public keys can be assigned to one user.
        If multiple public keys are assigned, the user
        can log in to the SSH server from different devices at the
        same time by using different public keys."
    DEFVAL      { "" }
    ::= { ibSSHUserConfigEntry 4 }

ibSSHUserWorkDirectory OBJECT-TYPE
    SYNTAX      DisplayString
    MAX-ACCESS  read-create
    STATUS      current
    DESCRIPTION
        "The SFTP user's work directory associates with an existing user."
    DEFVAL      { "" }
    ::= { ibSSHUserConfigEntry 5 }

ibSSHUserRowStatus OBJECT-TYPE
    SYNTAX      RowStatus
    MAX-ACCESS  read-create
    STATUS      current
    DESCRIPTION
        "The row status variable, used in accordance to installation
        and removal conventions for conceptual rows.

        When the `ibSSHUserRowStatus' is set to active(1), no objects
        in this table can be modified.

        When 'ibSSHUserRowStatus' is set to notInService(2), every object
        except the 'ibSSHUserName' object in this table can be modified.

        To create a row in this table, a manager must set this object
        to createAndGo(4).  Until instances of all corresponding columns
        are appropriately configured, the value of the corresponding
        instance of the ibSSHUserRowStatus column is 'notReady'."
    ::= { ibSSHUserConfigEntry 6 }

ibSSHUserPublicKeyName2 OBJECT-TYPE
    SYNTAX      DisplayString
    MAX-ACCESS  read-create
    STATUS      current
    DESCRIPTION
        "The public key which is used for authentication.
        A maximum of 6 public keys can be assigned to one user.
        If multiple public keys are assigned, the user
        can log in to the SSH server from different devices at the
        same time by using different public keys."
    DEFVAL      { "" }
    ::= { ibSSHUserConfigEntry 7 }

ibSSHUserPublicKeyName3 OBJECT-TYPE
    SYNTAX      DisplayString
    MAX-ACCESS  read-create
    STATUS      current
    DESCRIPTION
        "The public key which is used for authentication.
        A maximum of 6 public keys can be assigned to one user.
        If multiple public keys are assigned, the user
        can log in to the SSH server from different devices at the
        same time by using different public keys."
    DEFVAL      { "" }
    ::= { ibSSHUserConfigEntry 8 }

ibSSHUserPublicKeyName4 OBJECT-TYPE
    SYNTAX      DisplayString
    MAX-ACCESS  read-create
    STATUS      current
    DESCRIPTION
        "The public key which is used for authentication.
        A maximum of 6 public keys can be assigned to one user.
        If multiple public keys are assigned, the user
        can log in to the SSH server from different devices at the
        same time by using different public keys."
    DEFVAL      { "" }
    ::= { ibSSHUserConfigEntry 9 }

ibSSHUserPublicKeyName5 OBJECT-TYPE
    SYNTAX      DisplayString
    MAX-ACCESS  read-create
    STATUS      current
    DESCRIPTION
        "The public key which is used for authentication.
        A maximum of 6 public keys can be assigned to one user.
        If multiple public keys are assigned, the user
        can log in to the SSH server from different devices at the
        same time by using different public keys."
    DEFVAL      { "" }
    ::= { ibSSHUserConfigEntry 10 }

ibSSHUserPublicKeyName6 OBJECT-TYPE
    SYNTAX      DisplayString
    MAX-ACCESS  read-create
    STATUS      current
    DESCRIPTION
        "The public key which is used for authentication.
        A maximum of 6 public keys can be assigned to one user.
        If multiple public keys are assigned, the user
        can log in to the SSH server from different devices at the
        same time by using different public keys."
    DEFVAL      { "" }
    ::= { ibSSHUserConfigEntry 11 }

-- Define a group which consists of all objects used for sessions.
ibSSHSessionInfoTable OBJECT-TYPE
    SYNTAX      SEQUENCE OF IbSSHSessionInfoEntry
    MAX-ACCESS  not-accessible
    STATUS      current
    DESCRIPTION
        "A table for SSH sessions."
    ::= { ibSSHServerMIBObjects 3 }

ibSSHSessionInfoEntry OBJECT-TYPE
    SYNTAX      IbSSHSessionInfoEntry
    MAX-ACCESS  not-accessible
    STATUS      current
    DESCRIPTION
        "The SSH session information entry."
    INDEX
        {
            ibSSHSessionID
        }
    ::= { ibSSHSessionInfoTable 1 }

IbSSHSessionInfoEntry ::= SEQUENCE
    {
        ibSSHSessionID               Integer32,
        ibSSHSessionUserName         DisplayString,
        ibSSHSessionUserIpAddrType   InetAddressType,
        ibSSHSessionUserIpAddr       InetAddress,
        ibSSHSessionClientVersion    DisplayString,
        ibSSHSessionServiceType      INTEGER,
        ibSSHSessionEncry            INTEGER,
        ibSSHSessionState            INTEGER
    }

ibSSHSessionID OBJECT-TYPE
    SYNTAX      Integer32
    MAX-ACCESS  not-accessible
    STATUS      current
    DESCRIPTION
        "The identifier of SSH session."
    ::= { ibSSHSessionInfoEntry 1 }

ibSSHSessionUserName OBJECT-TYPE
    SYNTAX      DisplayString
    MAX-ACCESS  read-only
    STATUS      current
    DESCRIPTION
        "The user name of SSH session."
    ::= { ibSSHSessionInfoEntry 2 }

ibSSHSessionUserIpAddrType OBJECT-TYPE
    SYNTAX      InetAddressType
    MAX-ACCESS  read-only
    STATUS      current
    DESCRIPTION
        "The user IP address type of SSH session."
    ::= { ibSSHSessionInfoEntry 3 }

ibSSHSessionUserIpAddr OBJECT-TYPE
    SYNTAX      InetAddress
    MAX-ACCESS  read-only
    STATUS      current
    DESCRIPTION
        "The user IP address of SSH session."
    ::= { ibSSHSessionInfoEntry 4 }

ibSSHSessionClientVersion OBJECT-TYPE
    SYNTAX      DisplayString
    MAX-ACCESS  read-only
    STATUS      current
    DESCRIPTION
        "The client version of SSH session.  It is known that there are still
        devices using the previous versions."
    ::= { ibSSHSessionInfoEntry 5 }

ibSSHSessionServiceType OBJECT-TYPE
    SYNTAX      INTEGER
        {
            invalid(1),
            stelnet(2),
            sftp(3),
            scp(4),
            netconf(5)
        }
    MAX-ACCESS  read-only
    STATUS      current
    DESCRIPTION
        "The service type of SSH session."
    ::= { ibSSHSessionInfoEntry 6 }

ibSSHSessionEncry OBJECT-TYPE
    SYNTAX      INTEGER
        {
            invalid(1),
            aes128CBC(2),
            desCBC(3),
            des3CBC(4),
            aes128CTR(5),
            aes192CTR(6),
            aes256CTR(7),
            aes128GCM(8),
            aes256GCM(9),
            aes256CBC(10),
            other(11)
        }
    MAX-ACCESS  read-only
    STATUS      current
    DESCRIPTION
        "The encryption algorithm of SSH session.  There are several encryption
        algorithms used in SSH protocol, please refer to RFC4253 Section 6.3."
    ::= { ibSSHSessionInfoEntry 7 }

ibSSHSessionState OBJECT-TYPE
    SYNTAX      INTEGER
        {
            init(1),
            verExchange(2),
            keysExchange(3),
            authRequest(4),
            serviceRequest(5),
            established(6),
            disconnect(7)
        }
    MAX-ACCESS  read-only
    STATUS      current
    DESCRIPTION
        "The status of SSH session.
        init           : This session is in initial status.
        verExchange    : This session is in version exchanging.
        keysExchange   : This session is in keys exchanging.
        authRequest    : This session is in authentication requesting.
        serviceRequest : This session is in service requesting.
        established    : This session has been established.
        disconnected   : This session has been disconnected."
    ::= { ibSSHSessionInfoEntry 8 }


-- Define a group which consists of all objects used for trap.
ibSSHServerObjForTrap OBJECT IDENTIFIER ::= { ibSSHServerMIB 2 }

ibSSHAttemptUserName OBJECT-TYPE
    SYNTAX      DisplayString
    MAX-ACCESS  accessible-for-notify
    STATUS      current
    DESCRIPTION
        "The user name of the attacker who attempted to log in."
    ::= { ibSSHServerObjForTrap 1 }

ibSSHAttemptIpAddrType OBJECT-TYPE
    SYNTAX      InetAddressType
    MAX-ACCESS  accessible-for-notify
    STATUS      current
    DESCRIPTION
        "The IP address type of the attacker who attempted to log in."
    ::= { ibSSHServerObjForTrap 2 }

ibSSHAttemptIpAddr OBJECT-TYPE
    SYNTAX      InetAddress
    MAX-ACCESS  accessible-for-notify
    STATUS      current
    DESCRIPTION
        "The IP address of the attacker who attempted to log in."
    ::= { ibSSHServerObjForTrap 3 }

ibSSHUserAuthFailureReason OBJECT-TYPE
    SYNTAX      INTEGER
        {
            exceedRetries(1),
            authTimeout(2),
            otherReason(3)
        }
    MAX-ACCESS  accessible-for-notify
    STATUS      current
    DESCRIPTION
        "The reason for that a user failed to log in."
    ::= { ibSSHServerObjForTrap 4 }
ibSSHUserAuthFailureTime OBJECT-TYPE
    SYNTAX      DateAndTime
    MAX-ACCESS  accessible-for-notify
    STATUS      current
    DESCRIPTION
        "The time when authentication failed to log in.
         For example: 2021-09-14,13:30:16.
        "
    ::= { ibSSHServerObjForTrap 5 }
ibSSHSessionLoginTime OBJECT-TYPE
    SYNTAX      DateAndTime
    MAX-ACCESS  accessible-for-notify
    STATUS      current
    DESCRIPTION
        "The Login time of SSH session.
         For example: 2021-09-14,13:30:16.
        "
    ::= { ibSSHServerObjForTrap 6 }
ibSSHSessionLogoffTime OBJECT-TYPE
    SYNTAX      DateAndTime
    MAX-ACCESS  accessible-for-notify
    STATUS      current
    DESCRIPTION
        "The Logoff time of SSH session.
         For example: 2021-09-14,13:30:16.
        "
    ::= { ibSSHServerObjForTrap 7 }
ibSSHSessionUserRoleName OBJECT-TYPE
    SYNTAX      DisplayString (SIZE(1..63))
    MAX-ACCESS  accessible-for-notify
    STATUS      current
    DESCRIPTION
        "The user role of SSH session.
         such as network-admin network-operation etc.
        "
    ::= { ibSSHServerObjForTrap 8 }
ibSSHLoginFailedTimes OBJECT-TYPE
    SYNTAX      Unsigned32
    MAX-ACCESS  accessible-for-notify
    STATUS      current
    DESCRIPTION
        "The number of user login failures."
    ::= { ibSSHServerObjForTrap 9 }
ibSSHStatisticPeriod OBJECT-TYPE
    SYNTAX      Unsigned32
    UNITS       "minutes"
    MAX-ACCESS  accessible-for-notify
    STATUS      current
    DESCRIPTION
        "User login failure statistics period."
    ::= { ibSSHServerObjForTrap 10 }
--
-- Notification definitions
--
-- =================================================================
-- Traps are defined below.
ibSSHServerNotifications OBJECT IDENTIFIER ::= { ibSSHServerMIB 3 }

-- All trap definitions should be placed under this object.
ibSSHServerNotificationsPrefix OBJECT IDENTIFIER ::= { ibSSHServerNotifications 0 }

-- All objects used for TRAP only are defined here.
ibSSHUserAuthFailure NOTIFICATION-TYPE
    OBJECTS
        {
            ibSSHAttemptUserName,
            ibSSHAttemptIpAddrType,
            ibSSHAttemptIpAddr,
            ibSSHUserAuthFailureReason,
            ibSSHUserAuthFailureTime
        }
    STATUS      current
    DESCRIPTION
        "The trap is generated when a user fails to authentication."
    ::= { ibSSHServerNotificationsPrefix 1 }

ibSSHVersionNegotiationFailure NOTIFICATION-TYPE
    OBJECTS
        {
            ibSSHAttemptIpAddrType,
            ibSSHAttemptIpAddr
        }
    STATUS      current
    DESCRIPTION
        "The trap is generated when a user fails to negotiate SSH
        protocol version."
    ::= { ibSSHServerNotificationsPrefix 2 }

ibSSHUserLogin NOTIFICATION-TYPE
    OBJECTS
        {
            ibSSHSessionUserName,
            ibSSHSessionUserIpAddrType,
            ibSSHSessionUserIpAddr,
            ibSSHSessionLoginTime,
            ibSSHSessionUserRoleName
        }
    STATUS      current
    DESCRIPTION
        "The trap is generated when a user logs in successfully."
    ::= { ibSSHServerNotificationsPrefix 3 }

ibSSHUserLogoff NOTIFICATION-TYPE
    OBJECTS
        {
            ibSSHSessionUserName,
            ibSSHSessionUserIpAddrType,
            ibSSHSessionUserIpAddr,
            ibSSHSessionLogoffTime,
            ibSSHSessionUserRoleName
        }
    STATUS      current
    DESCRIPTION
        "The trap is generated when a user logs off."
    ::= { ibSSHServerNotificationsPrefix 4 }

ibSSHLoginFailed NOTIFICATION-TYPE
    OBJECTS
        {
            ibSSHLoginFailedTimes,
            ibSSHStatisticPeriod
        }
    STATUS      current
    DESCRIPTION
        "Users failed to login ssh server too frequently."
    ::= { ibSSHServerNotificationsPrefix 5 }

ibSSHLoginFailedClear NOTIFICATION-TYPE
    STATUS      current
    DESCRIPTION
        "The ssh user login-failed alarm was cleared."
    ::= { ibSSHServerNotificationsPrefix 6 }

END
