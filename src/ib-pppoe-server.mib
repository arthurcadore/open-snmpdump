-- =================================================================
-- Copyright (C) 2023 Intelbras S.A. All rights reserved.
--
-- Description: PPPoE server MIB
-- Reference:
-- Version:     V1.1
-- History:
-- V1.0 Initial version by y04444
-- V1.1 2009-09-07 Modify by yuhaibo
--      Add PPPoE server trap
-- =================================================================
IB-PPPOE-SERVER-MIB DEFINITIONS ::= BEGIN
IMPORTS
    ibCommon
        FROM IB-OID-MIB
    OBJECT-TYPE, MODULE-IDENTITY, Integer32, Counter32, NOTIFICATION-TYPE
        FROM SNMPv2-SMI;

ibPPPoEServer MODULE-IDENTITY
    LAST-UPDATED "200905060000Z"            -- May 06th, 2009 at 00:00 GMT
    ORGANIZATION
        "Intelbras S.A. Industria de Telecomunicacao Eletronica Brasileria."
    CONTACT-INFO
        ""
    DESCRIPTION
        "The MIB module is used for PPPoE server."
    REVISION    "200905060000Z"
    DESCRIPTION
        "Initial version"
    ::= { ibCommon 102 }

ibPPPoEServerObject OBJECT IDENTIFIER ::= { ibPPPoEServer 1 }

--
-- PPPOE SERVER MAXIMUM SESSIONS SUPPORT
--

ibPPPoEServerMaxSessions OBJECT-TYPE
    SYNTAX      Integer32
    MAX-ACCESS  read-only
    STATUS      current
    DESCRIPTION
        "The maximum sessions supported by PPPoE server."
    ::= { ibPPPoEServerObject 1 }

--
-- PPPOE SERVER CURRENT SESSION NUMBERS
--

ibPPPoEServerCurrSessions OBJECT-TYPE
    SYNTAX      Integer32
    MAX-ACCESS  read-only
    STATUS      current
    DESCRIPTION
        "The number of current sessions on the PPPoE server."
    ::= { ibPPPoEServerObject 2 }

--
-- PPPOE SERVER AUTHENTICATION REQUEST NUMBERS
--

ibPPPoEServerAuthRequests OBJECT-TYPE
    SYNTAX      Counter32
    MAX-ACCESS  read-only
    STATUS      current
    DESCRIPTION
        "The number of authentication requests."
    ::= { ibPPPoEServerObject 3 }

--
-- PPPOE SERVER AUTHENTICATION SUCCESS NUMBERS
--

ibPPPoEServerAuthSuccesses OBJECT-TYPE
    SYNTAX      Counter32
    MAX-ACCESS  read-only
    STATUS      current
    DESCRIPTION
        "The number of authentication succeses."
    ::= { ibPPPoEServerObject 4 }

--
-- PPPOE SERVER AUTHENTICATION FAIL NUMBERS
--

ibPPPoEServerAuthFailures OBJECT-TYPE
    SYNTAX      Counter32
    MAX-ACCESS  read-only
    STATUS      current
    DESCRIPTION
        "The number of authentication failure."
    ::= { ibPPPoEServerObject 5 }

--
-- PPPOE SERVER ABNORMAL OFFLINE COUNT THRESHOLD
--

ibPPPoESAbnormOffsThreshold OBJECT-TYPE
    SYNTAX      Integer32 (0..65535)
    MAX-ACCESS  read-write
    STATUS      current
    DESCRIPTION
        "The threshold of abnormal offline count."
    ::= { ibPPPoEServerObject 6 }

--
-- PPPOE SERVER ABNORMAL OFFLINE PERCENT THRESHOLD
--

ibPPPoESAbnormOffPerThreshold OBJECT-TYPE
    SYNTAX      Integer32 (0..100)
    MAX-ACCESS  read-write
    STATUS      current
    DESCRIPTION
        "The threshold of abnormal offline percent."
    ::= { ibPPPoEServerObject 7 }

--
-- PPPOE SERVER NORMAL OFFLINE PERCENT THRESHOLD
--

ibPPPoESNormOffPerThreshold OBJECT-TYPE
    SYNTAX      Integer32 (0..100)
    MAX-ACCESS  read-write
    STATUS      current
    DESCRIPTION
        "The threshold of normal offline percent."
    ::= { ibPPPoEServerObject 8 }

--
-- Define the PPPoE Server Traps.
--
    ibPPPoEServerTraps OBJECT IDENTIFIER ::= { ibPPPoEServer 2 }

    ibPPPoeServerTrapPrefix OBJECT IDENTIFIER ::= { ibPPPoEServerTraps 0 }

    ibPPPoESAbnormOffsAlarm NOTIFICATION-TYPE
        STATUS      current
        DESCRIPTION
            "This trap is generated when the PPPoE server abnormal
            offline counts over threshold in five minutes."
        ::= { ibPPPoeServerTrapPrefix 1 }

    ibPPPoESAbnormOffPerAlarm NOTIFICATION-TYPE
        STATUS      current
        DESCRIPTION
            "This trap is generated when the PPPoE server abnormal
            offline percent over threshold in five minutes."
        ::= { ibPPPoeServerTrapPrefix 2 }

    ibPPPoESNormOffPerAlarm NOTIFICATION-TYPE
        STATUS      current
        DESCRIPTION
            "This trap is generated when the PPPoE server normal
            offline percent under threshold in five minutes."
        ::= { ibPPPoeServerTrapPrefix 3 }

END
