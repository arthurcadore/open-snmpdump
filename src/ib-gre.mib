-- =================================================================
-- Copyright (C) 2023 Intelbras S.A. All rights reserved.
--
-- Description: Generic Routing Encapsulation configuration MIB
-- Reference: IF-MIB
-- Version: V1.0
-- History:
-- V1.0 created by Sun Ludong
--   2005-06-04 Initial version
-- =================================================================
IB-GRE-MIB DEFINITIONS ::= BEGIN

IMPORTS
    ibCommon
        FROM IB-OID-MIB
    Unsigned32, OBJECT-TYPE, MODULE-IDENTITY
        FROM SNMPv2-SMI
    ifIndex
        FROM IF-MIB; 

ibGre MODULE-IDENTITY
    LAST-UPDATED
        "200506040000Z"                        -- June 4, 2005 at 00:00 GMT
    ORGANIZATION
        "Intelbras S.A. Industria de Telecomunicacao Eletronica Brasileria."
    CONTACT-INFO
        ""
    DESCRIPTION
        "This MIB contains objects to Manage configuration and 
        Monitor running state for GRE.
        "                        
    REVISION
        "200506040000Z"                        -- June 4, 2005 at 00:00 GMT
    DESCRIPTION
        "The initial revision of this MIB module.
        "
    ::= { ibCommon 54 }

    ibGreObjects OBJECT IDENTIFIER ::= { ibGre 1 }

    ibGreTable  OBJECT-TYPE
    SYNTAX SEQUENCE OF IbGreEntry
    MAX-ACCESS not-accessible
    STATUS current
    DESCRIPTION
        "A table of Generic Routing Encapsulation(GRE) configuration. 
        It contains configuration of GRE Key, and enable flags of Key
        and Checksum. The detail of Key and Checksum is described in
        RFC2784 and RFC2890.
        "
    ::= { ibGreObjects 1 }
                        
    ibGreEntry OBJECT-TYPE
    SYNTAX IbGreEntry
    MAX-ACCESS not-accessible
    STATUS current
    DESCRIPTION
        "The entry of ibGreTable
        "
    INDEX { ifIndex }
    ::= { ibGreTable 1 }

    IbGreEntry ::= SEQUENCE {
        ibGreKeyValue
            Unsigned32, 
        ibGreKey
            INTEGER, 
        ibGreChecksum
            INTEGER
    }
    ibGreKeyValue OBJECT-TYPE
    SYNTAX Unsigned32
    MAX-ACCESS read-write
    STATUS current
    DESCRIPTION
        "The value of GRE key
        "
    ::= { ibGreEntry 1 }
                     
    ibGreKey OBJECT-TYPE
        SYNTAX INTEGER{
            enable(1), 
            disable(2)
        }
        MAX-ACCESS read-write
        STATUS current
        DESCRIPTION
        "The enable flag of GRE key
        "
    ::= { ibGreEntry 2 }
                        
    ibGreChecksum OBJECT-TYPE
        SYNTAX INTEGER{
            enable(1), 
            disable(2)
        }
        MAX-ACCESS read-write
        STATUS current
        DESCRIPTION
            "The enable flag of GRE Checksum
            "
        ::= { ibGreEntry 3 }

END
