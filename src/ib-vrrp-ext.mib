-- =========================================================================
-- Copyright (C) 2023 Intelbras S.A. All rights reserved.
--
-- Description: This file describes various common MIB objects implemented
-- by both Routers and Switches.
-- Reference: VRRP-MIB
-- Version: V1.3
-- History:
--      V1.0 2004-12-09
--        Initial version
--      V1.1 2021-07-19 updated by wangmeng
--        Add state change Trap
--      V1.2 2022-05-11 Add VRRPv3 error traps by zhengjun
--      V1.3 2023-02-10 Add VRRP MAC address configuration failure trap by zhengjun
-- =========================================================================
IB-VRRP-EXT-MIB DEFINITIONS ::= BEGIN

    IMPORTS
        MODULE-IDENTITY, OBJECT-TYPE,NOTIFICATION-TYPE, Integer32
            FROM SNMPv2-SMI

        DisplayString,RowStatus,MacAddress
            FROM SNMPv2-TC

        ifIndex, InterfaceIndex
            FROM IF-MIB

        vrrpOperVrId
            FROM VRRP-MIB

        ibCommon
            FROM IB-OID-MIB;


ibVrrpExt MODULE-IDENTITY
    LAST-UPDATED "202302101501Z"
    ORGANIZATION
        "Intelbras S.A. Industria de Telecomunicacao Eletronica Brasileria."
    CONTACT-INFO
        ""
    DESCRIPTION
        "This MIB describes objects used for managing Virtual Router
        Redundancy Protocol (VRRP) routers."
    REVISION
        "202302101501Z"
    DESCRIPTION
        "Add the traps for configuring virtual MAC addresses for VRRP groups."
    REVISION
        "202205111505Z"
    DESCRIPTION
        "Add VRRPv3 error traps."
    REVISION
        "202107190000Z"
    DESCRIPTION
        "Add state change Trap."
    ::= { ibCommon 24 }


-- ===================================================================
--  Start of MIB objects
-- ===================================================================

ibVrrpExtMibObject      OBJECT IDENTIFIER ::= { ibVrrpExt 1 }

-- ===================================================================
--  VRRP EXT Table
-- ===================================================================

ibVrrpExtTable OBJECT-TYPE
    SYNTAX       SEQUENCE OF IbVrrpExtEntry
    MAX-ACCESS   not-accessible
    STATUS       current
    DESCRIPTION
        "Table extends for a VRRP router which consists of a
        sequence (i.e., one or more conceptual rows) of
        ibVrrpExtEntry items."
    ::= { ibVrrpExtMibObject 1 }

ibVrrpExtEntry OBJECT-TYPE
    SYNTAX       IbVrrpExtEntry
    MAX-ACCESS   not-accessible
    STATUS       current
    DESCRIPTION
        "An entry in the ibVrrpExtTable containing the status
        values of a virtual router."
    INDEX    { ifIndex, vrrpOperVrId, ibVrrpExtTrackInterface }
    ::= { ibVrrpExtTable 1 }

IbVrrpExtEntry ::=
    SEQUENCE {
     ibVrrpExtTrackInterface
        Integer32,
     ibVrrpExtPriorityReduce
        Integer32,
     ibVrrpExtRowStatus
        RowStatus
}

ibVrrpExtTrackInterface OBJECT-TYPE
    SYNTAX Integer32 (0..2147483647)
    MAX-ACCESS not-accessible
    STATUS current
    DESCRIPTION
        "This value is the ifIndex that identifies which interface
        the virtual router tracked."
    ::= { ibVrrpExtEntry 1 }

ibVrrpExtPriorityReduce  OBJECT-TYPE
    SYNTAX       Integer32 (1..255)
    MAX-ACCESS   read-create
    STATUS       current
    DESCRIPTION
        "This value identifies how much priority of a virtual router
        will be reduced/increased when the interface tracked is down/up."
    DEFVAL { 10 }
    ::= { ibVrrpExtEntry 2 }

ibVrrpExtRowStatus OBJECT-TYPE
    SYNTAX       RowStatus
    MAX-ACCESS   read-create
    STATUS       current
    DESCRIPTION
        "The row status variable, used according to installation
        and removal conventions for conceptual rows. Setting this
        object to active(1) or createAndGo(4) results in the
        addition of the ifIndex tracked by a virtual router.
        Destroying the entry removes the tracked ifIndex from the
        virtual router. Other values is not supported now."
    ::= { ibVrrpExtEntry 3 }

-- trap --
ibVrrpExtTrap      OBJECT IDENTIFIER ::= { ibVrrpExt 2 }

ibVrrpTrapPrex OBJECT IDENTIFIER ::= { ibVrrpExtTrap 0 }

ibVrrpExtStateChange NOTIFICATION-TYPE
    OBJECTS
        {
            ibVrrpExtVrId,
            ibVrrpExtIpAddressType,
            ibVrrpExtIfIndex,
            ibVrrpExtIfDescr,
            ibVrrpExtOldState,
            ibVrrpExtNewState,
            ibVrrpExtStateChangeReason
        }
    STATUS       current
    DESCRIPTION
        "This trap indicates that the sending agent VRRP state has changed."
    ::= { ibVrrpTrapPrex 1 }

ibVrrpExtV3ProtoError NOTIFICATION-TYPE
    OBJECTS
        {
            ibVrrpExtVrId,
            ibVrrpExtIpAddressType,
            ibVrrpExtIfIndex,
            ibVrrpExtIfDescr
        }
    STATUS       current
    DESCRIPTION
        "This trap indicates that the VRRP received a protocol error packet."
    ::= { ibVrrpTrapPrex 2 }

ibVrrpExtAddVirtualMacFailed NOTIFICATION-TYPE
    OBJECTS
        {
            ibVrrpExtVrId,
            ibVrrpExtIpAddressType,
            ibVrrpExtIfIndex,
            ibVrrpExtIfDescr,
            ibVrrpExtIfLipAddr,
            ibVrrpExtVirtualMac
        }
    STATUS       current
    DESCRIPTION
        "This trap indicates failure to add a virtual MAC address for a VRRP group."
    ::= { ibVrrpTrapPrex 3 }

-- All objects used for trap only are defined here.
ibVrrpExtTrapOjbects OBJECT IDENTIFIER ::= { ibVrrpExtTrap 1 }

ibVrrpExtVrId OBJECT-TYPE
    SYNTAX Integer32 (1..255)
    MAX-ACCESS accessible-for-notify
    STATUS current
    DESCRIPTION
        "This object contains the Virtual Router Identifier (VRID)."
    ::= { ibVrrpExtTrapOjbects 1 }

ibVrrpExtIpAddressType OBJECT-TYPE
    SYNTAX       INTEGER {
        ipv4(1),
        ipv6(2)
    }
    MAX-ACCESS   accessible-for-notify
    STATUS       current
    DESCRIPTION
        "IP address type of VRRP.
         ipv4: IPv4 type.
         ipv6: IPv6 type."
    ::= { ibVrrpExtTrapOjbects 2 }

ibVrrpExtIfIndex OBJECT-TYPE
    SYNTAX InterfaceIndex
    MAX-ACCESS accessible-for-notify
    STATUS current
    DESCRIPTION
        "This value is the ifIndex that identifies the interface configured for
         the virtual router."
    ::= { ibVrrpExtTrapOjbects 3 }

ibVrrpExtIfDescr OBJECT-TYPE
    SYNTAX      DisplayString (SIZE(0..255))
    MAX-ACCESS accessible-for-notify
    STATUS current
    DESCRIPTION
        "This value is the interface decription that identifies the interface
        configured for the virtual router."
    ::= { ibVrrpExtTrapOjbects 4 }

ibVrrpExtOldState OBJECT-TYPE
    SYNTAX       INTEGER {
     initialize(1),
     backup(2),
     master(3)
    }
    MAX-ACCESS   accessible-for-notify
    STATUS       current

    DESCRIPTION
        "The current state of the virtual router. This object has
        three defined values:

        - `initialize', which indicates that the
         virtual router is waiting for a startup event.

        - `backup', which indicates the virtual router is
         monitoring the availability of the master router.

        - `master', which indicates that the virtual router
         is forwarding packets for IP addresses that are
         associated with this router."
    ::= { ibVrrpExtTrapOjbects 5 }

ibVrrpExtNewState OBJECT-TYPE
    SYNTAX       INTEGER {
         initialize(1),
         backup(2),
         master(3)
    }
    MAX-ACCESS   accessible-for-notify
    STATUS       current

    DESCRIPTION
        "The current state of the virtual router. This object has
        three defined values:

        - `initialize', which indicates that the
         virtual router is waiting for a startup event.

        - `backup', which indicates the virtual router is
         monitoring the availability of the master router.

        - `master', which indicates that the virtual router
         is forwarding packets for IP addresses that are
         associated with this router."
    ::= { ibVrrpExtTrapOjbects 6 }

ibVrrpExtStateChangeReason OBJECT-TYPE
    SYNTAX Integer32 (0..12)
    MAX-ACCESS accessible-for-notify
    STATUS current
    DESCRIPTION
        "Reason why VRRP state changed,
         0: other reason.
         1: Timer expired.
         2: Adding virtual MAC address failed.
         3: Interface event received.
         4: IP address deleted.
         5: The status of the tracked object changed.
         6: VRRP packet received.
         7: Current device has changed to IP address owner.
         8: Insufficient hardware resources.
         9: Master-down-timer expired.
         10: Zero priority packet received.
         11: Preempt.
         12: Master group drove."
    ::= { ibVrrpExtTrapOjbects 7 }

ibVrrpExtIfLipAddr OBJECT-TYPE
    SYNTAX Integer32 (0..65535)
    MAX-ACCESS accessible-for-notify
    STATUS current
    DESCRIPTION
        "This value is the interface index of the node that identifies
         the interface configured for the virtual router."
    ::= { ibVrrpExtTrapOjbects 8 }

ibVrrpExtVirtualMac OBJECT-TYPE
    SYNTAX MacAddress
    MAX-ACCESS accessible-for-notify
    STATUS current
    DESCRIPTION
        "This value is the MAC address that identifies the interface
         configured for the virtual router."
    ::= { ibVrrpExtTrapOjbects 9 }
END
