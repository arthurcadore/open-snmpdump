-- =================================================================
-- Copyright (C) 2023 Intelbras S.A. All rights reserved.
--
-- Description:
-- Reference:
-- Version: V1.7
-- History:
-- V1.0 created by liujingya.
--    Initial version of the MIB
-- V1.1 2008-1-29 Adjusted the structure of some tables by liujingya.
-- V1.2 2008-5-19 Added ibHPEOCCltAutoUpgrade, ibHPEOCCnuAnonymStatus and
--    ibHPEOCBitPerSymbolTable, modified description of ibHPEOCCnuBcastControl
--    by liujingya.
-- V1.3 2009-2-13 Added ibHPEOCOnLineCnuNumber, ibHPEOCCpuMacAddress,
--    ibHPEOCOffLineCnuNumber, ibHPEOCDownLoadCNUFWResult,
--    ibHPEOCCltAutoUpgradeType, ibHPEOCServerAddress, ibHPEOCServerUser,
--    ibHPEOCServerPassword and ibHPEOCCnuMacLimit by liujingya.
-- V1.4 2011-12-28 Added ibHPEOCCltLinkState by gaoguangping.
--      2012-03-14 Added ibHPEOCCltLoopbackDetect by gaoguangping.
-- V1.5 2013-08-20 Added ibHPEOCTemplate,ibHPEOCCnuAccess by xujun
--      2013-09-16 Added ibHPEOCTemplateEnable by xujun
-- V1.6 2015-04-30 Bug fixed by songhao
-- V1.7 2016-09-02 Bug fixed by gaoguangping
-- =================================================================
IB-HPEOC-MIB DEFINITIONS ::= BEGIN

IMPORTS
        ibCommon
    FROM IB-OID-MIB
        ifIndex
    FROM IF-MIB
        Integer32, Unsigned32, Counter64, OBJECT-TYPE, MODULE-IDENTITY,
        IpAddress
    FROM SNMPv2-SMI
        DisplayString, TruthValue, MacAddress, RowStatus
    FROM SNMPv2-TC;


ibHPEOC MODULE-IDENTITY
    LAST-UPDATED "200708281008Z"
    ORGANIZATION
        "Intelbras S.A. Industria de Telecomunicacao Eletronica Brasileria."
    CONTACT-INFO
        ""
    DESCRIPTION
        "
        The objects in this MIB module are used to manage and
        display current configuration of Ethernet Over Cable
        Network (EOC) which based on HomePlug(HP) AV Specification.
        "
    ::= { ibCommon 84 }

--
-- ibHPEOCSystem
--
ibHPEOCSystem OBJECT IDENTIFIER ::= { ibHPEOC 1 }

ibHPEOCCltVlanType OBJECT-TYPE
    SYNTAX      INTEGER
        {
            ieee8021q(1),
            portbased(2)
        }
    MAX-ACCESS  read-write
    STATUS      current
    DESCRIPTION
        "
        Control EOC CLT's VLAN type,
        ieee8021q : 802.1q VLAN mode,
        portbased : portbased VLAN mode.
        "
    ::= { ibHPEOCSystem 1 }

--
-- ibHPEOCCltVlanManTable
--
ibHPEOCCltVlanManTable OBJECT-TYPE
    SYNTAX      SEQUENCE OF IbHPEOCCltVlanManEntry
    MAX-ACCESS  not-accessible
    STATUS      current
    DESCRIPTION
        "
        This table implements the management of CLT(Coax Line Terminal)
        VLAN.
        "
    ::= { ibHPEOCSystem 2 }

ibHPEOCCltVlanManEntry OBJECT-TYPE
    SYNTAX      IbHPEOCCltVlanManEntry
    MAX-ACCESS  not-accessible
    STATUS      current
    DESCRIPTION
        "
        The entry of the table ibHPEOCCltVlanManTable.
        "
    INDEX
        {
            ifIndex
        }
    ::= { ibHPEOCCltVlanManTable 1 }

IbHPEOCCltVlanManEntry ::= SEQUENCE
    {
        ibHPEOCCltEthPortType    INTEGER
    }

ibHPEOCCltEthPortType OBJECT-TYPE
    SYNTAX      INTEGER
        {
            normal(1),
            debug(2)
        }
    MAX-ACCESS  read-write
    STATUS      current
    DESCRIPTION
        "
        Control CLT ethernet ports' type,
        normal : port which used for normal translation,
        debug : port which used for debug.
        "
    ::= { ibHPEOCCltVlanManEntry 1 }

--
-- ibHPEOCCltSysManTable
--
ibHPEOCCltSysManTable OBJECT-TYPE
    SYNTAX      SEQUENCE OF IbHPEOCCltSysManEntry
    MAX-ACCESS  not-accessible
    STATUS      current
    DESCRIPTION
        "
        This table implements the management of CLT(Coax Line Terminal).
        "
    ::= { ibHPEOCSystem 3 }

ibHPEOCCltSysManEntry OBJECT-TYPE
    SYNTAX      IbHPEOCCltSysManEntry
    MAX-ACCESS  not-accessible
    STATUS      current
    DESCRIPTION
        "
        The entry of the table ibHPEOCCltSysManTable.
        "
    INDEX
        {
            ifIndex
        }
    ::= { ibHPEOCCltSysManTable 1 }

IbHPEOCCltSysManEntry ::= SEQUENCE
    {
        ibHPEOCCltDescr        DisplayString,
        ibHPEOCCltFwVersion    DisplayString,
        ibHPEOCCltLinkState    INTEGER
    }

ibHPEOCCltDescr OBJECT-TYPE
    SYNTAX      DisplayString(SIZE(0..126))
    MAX-ACCESS  read-write
    STATUS      current
    DESCRIPTION
        "
        Set the description of CLT.
        "
    ::= { ibHPEOCCltSysManEntry 1 }

ibHPEOCCltFwVersion OBJECT-TYPE
    SYNTAX      DisplayString
    MAX-ACCESS  read-only
    STATUS      current
    DESCRIPTION
        "
        EOC firmware version.  If the object length is
        zero, it means the version is unknown.
        "
    ::= { ibHPEOCCltSysManEntry 2 }

ibHPEOCCltLinkState OBJECT-TYPE
    SYNTAX     INTEGER
        {
            physicaldown(1),
            linkdown(2),
            linkup(3),
            loopback(4)
        }
    MAX-ACCESS read-only
    STATUS     current
    DESCRIPTION
        "
        The cable port's link state.  The physicaldown(1) state indicates
        that the CLT is not powered on.  The linkdown(2) state indicates
        that the CLT is powered on, but registers fail.  The linkup(3)
        state indicates that the CLT is powered on, and registers
        successful.  The loopback(4) state indecates that the CLT is
        powered on and registers successful, but loopback has detected.
        "
    ::= { ibHPEOCCltSysManEntry 3 }

--
-- ibHPEOCCnuSysManTable
--
ibHPEOCCnuSysManTable OBJECT-TYPE
    SYNTAX      SEQUENCE OF IbHPEOCCnuSysManEntry
    MAX-ACCESS  not-accessible
    STATUS      current
    DESCRIPTION
        "
        This table implements the management of CNUs.
        "
    ::= { ibHPEOCSystem 4 }

ibHPEOCCnuSysManEntry OBJECT-TYPE
    SYNTAX      IbHPEOCCnuSysManEntry
    MAX-ACCESS  not-accessible
    STATUS      current
    DESCRIPTION
        "
        The entry of the table ibHPEOCCnuSysManTable.
        "
    INDEX
        {
            ifIndex
        }
    ::= { ibHPEOCCnuSysManTable 1 }

IbHPEOCCnuSysManEntry ::= SEQUENCE
    {
        ibHPEOCCnuBcastControl    TruthValue,
        ibHPEOCCnuAnonymStatus    TruthValue,
        ibHPEOCCnuMacLimit        Unsigned32
    }

ibHPEOCCnuBcastControl OBJECT-TYPE
    SYNTAX      TruthValue
    MAX-ACCESS  read-write
    STATUS      current
    DESCRIPTION
        "
        Broadcast storm suppression status.
        true(1)  - Broadcast storm suppression enable.
        false(2) - Broadcast storm suppression disable.
        "
    ::= { ibHPEOCCnuSysManEntry 1 }

ibHPEOCCnuAnonymStatus OBJECT-TYPE
    SYNTAX      TruthValue
    MAX-ACCESS  read-only
    STATUS      current
    DESCRIPTION
        "
        Anonymity status.
        true(1)  - the user which uses the CNU is anonymous.
        false(2) - the user which uses the CNU has an account.
        "
    ::= { ibHPEOCCnuSysManEntry 2 }

ibHPEOCCnuMacLimit OBJECT-TYPE
    SYNTAX      Unsigned32
    MAX-ACCESS  read-write
    STATUS      current
    DESCRIPTION
        "
        Configure the max number of MAC address entries which can access
        through the CNU, it ranges from 1 to 8.
        Otherwise,
        If configure 0, the CNU won't limit the MAC address entry.
        If configure 0xFF, it means no MAC address entry can access the CNU.
        "
    ::= { ibHPEOCCnuSysManEntry 3 }

ibHPEOCCltAutoUpgrade OBJECT-TYPE
    SYNTAX      TruthValue
    MAX-ACCESS  read-write
    STATUS      current
    DESCRIPTION
        "
        Auto upgrade Status.
        true(1) - The firmware of the CNU will be auto changed by CLT.
        false(2)- The firmware of the CNU will not be auto changed.
        "
    DEFVAL
        {
            false
        }
    ::= { ibHPEOCSystem 5 }

ibHPEOCOnLineCnuNumber OBJECT-TYPE
    SYNTAX      Integer32
    MAX-ACCESS  read-only
    STATUS      current
    DESCRIPTION
        "
        The total number of the online CNU(s).
        "
    ::= { ibHPEOCSystem 6 }

ibHPEOCCpuMacAddress OBJECT-TYPE
    SYNTAX      MacAddress
    MAX-ACCESS  read-only
    STATUS      current
    DESCRIPTION
        "
        EOC CPU's MAC address.
        "
    ::= { ibHPEOCSystem 7 }

ibHPEOCOffLineCnuNumber OBJECT-TYPE
    SYNTAX      Integer32
    MAX-ACCESS  read-only
    STATUS      current
    DESCRIPTION
        "
        The total number of the offline CNU(s).
        "
    ::= { ibHPEOCSystem 8 }

ibHPEOCDownLoadCNUFWResult OBJECT-TYPE
    SYNTAX      DisplayString
    MAX-ACCESS  accessible-for-notify
    STATUS      current
    DESCRIPTION
        "
        Download CNU firmware result.
        "
    ::= { ibHPEOCSystem 9 }

ibHPEOCCltAutoUpgradeType OBJECT-TYPE
    SYNTAX      INTEGER
        {
            flash(1),
            ftp(2),
            tftp(3)
        }
    MAX-ACCESS  read-write
    STATUS      current
    DESCRIPTION
        "
        Type of auto upgrade status.
        It depends on ibHPEOCCltAutoUpgrade status.
        flash - The CLT auto upgrade the firmware inside its flash
                   to the CNUs.
        ftp    - First download the firmware from FTP server to the CLT,
                   then the CLT auto upgrade the firmware to the CNUs.
        tftp   - First download the firmware from TFTP server to the CLT,
                   then the CLT auto upgrade the firmware to the CNUs.
        "
    ::= { ibHPEOCSystem 10 }

ibHPEOCAutoUpObjects OBJECT IDENTIFIER ::= { ibHPEOCSystem 11 }

ibHPEOCServerAddress OBJECT-TYPE
    SYNTAX     IpAddress
    MAX-ACCESS read-write
    STATUS     current
    DESCRIPTION
        "
        The address of remote host acting as server for operation.
        The default value is 0.0.0.0
        "
    ::= { ibHPEOCAutoUpObjects 1 }

ibHPEOCServerUser OBJECT-TYPE
    SYNTAX     DisplayString
    MAX-ACCESS read-write
    STATUS     current
    DESCRIPTION
        "
        When using ftp to transfer files, the user name must be
        specified through this node.  It contains 1 to 30 characters.
        "
    ::= { ibHPEOCAutoUpObjects 2 }

ibHPEOCServerPassword OBJECT-TYPE
    SYNTAX     DisplayString
    MAX-ACCESS read-write
    STATUS     current
    DESCRIPTION
        "
        Remote user password for copying via ftp protocol. Optionally,
        this object may be ignored for protocols other than ftp.
        It contains 1 to 31 characters.
        "
    ::= { ibHPEOCAutoUpObjects 3 }

ibHPEOCCltLoopbackDetect OBJECT-TYPE
    SYNTAX      INTEGER
        {
            false(0),
            true(1)
        }
    MAX-ACCESS  read-write
    STATUS      current
    DESCRIPTION
        "
        Loopback detect Status.
        true(1) - The loopback detect is enabled.
        false(0)- The loopback detect is disabled.
        "
    ::= { ibHPEOCSystem 12 }

ibHPEOCTemplateEnable OBJECT-TYPE
    SYNTAX      INTEGER
        {
            false(0),
            true(1)
        }
    MAX-ACCESS  read-write
    STATUS      current
    DESCRIPTION
        "
        Use template for white-list cnu.
        true(1) - Use template is enabled.
        false(0)- Use template detect is disabled.
        "
    ::= { ibHPEOCSystem 13 }

--
-- ibHPEOCCableInfo
--
ibHPEOCCableInfo OBJECT IDENTIFIER ::= { ibHPEOC 2 }


--
-- ibHPEOCCableInfoTable
--

ibHPEOCCableInfoTable OBJECT-TYPE
    SYNTAX      SEQUENCE OF IbHPEOCCableInfoEntry
    MAX-ACCESS  not-accessible
    STATUS      current
    DESCRIPTION
        "
        This table defines the primary parameters of the
        cable information.
        "
    ::= { ibHPEOCCableInfo 1 }

ibHPEOCCableInfoEntry OBJECT-TYPE
    SYNTAX      IbHPEOCCableInfoEntry
    MAX-ACCESS  not-accessible
    STATUS      current
    DESCRIPTION
        "
        The entry of the table ibHPEOCCableInfoTable.
        "
    INDEX
        {
            ifIndex
        }
    ::= { ibHPEOCCableInfoTable 1 }


IbHPEOCCableInfoEntry ::= SEQUENCE
    {
        ibHPEOCFECErrors            Counter64,
        ibHPEOCAvgBitsPerCarrier    Unsigned32,
        ibHPEOCAvgSNRPerCarrier     Integer32,
        ibHPEOCAvgInPBCRCErrors     Unsigned32,
        ibHPEOCInTotalPkts          Counter64,
        ibHPEOCAvgOutPower          Integer32,
        ibHPEOCAvgOutPBCRCErrors    Unsigned32,
        ibHPEOCOutTotalPkts         Counter64
    }

ibHPEOCFECErrors OBJECT-TYPE
    SYNTAX      Counter64
    MAX-ACCESS  read-only
    STATUS      current
    DESCRIPTION
        "
        The cable port's FEC bits errors ratio.  FEC means the
        payload Forward Error Correction.  It's a technology of
        controlling errors.  Packets in transmission is checked by
        the receiver, if error occurs, the receiver will announce
        the sender to resend.
        "
    ::= { ibHPEOCCableInfoEntry 1 }

ibHPEOCAvgBitsPerCarrier OBJECT-TYPE
    SYNTAX      Unsigned32
    MAX-ACCESS  read-only
    STATUS      current
    DESCRIPTION
        "
        The cable port's average bits per carrier.
        "
    ::= { ibHPEOCCableInfoEntry 2 }

ibHPEOCAvgSNRPerCarrier OBJECT-TYPE
    SYNTAX      Integer32
    MAX-ACCESS  read-only
    STATUS      current
    DESCRIPTION
        "
        The cable port's signal noise ratio(SNR) bits per carrier.
        "
    ::= { ibHPEOCCableInfoEntry 3 }

ibHPEOCAvgInPBCRCErrors OBJECT-TYPE
    SYNTAX      Unsigned32
    MAX-ACCESS  read-only
    STATUS      current
    DESCRIPTION
        "
        The input PB CRC errors on average.
        "
    ::= { ibHPEOCCableInfoEntry 4 }

ibHPEOCInTotalPkts OBJECT-TYPE
    SYNTAX      Counter64
    MAX-ACCESS  read-only
    STATUS      current
    DESCRIPTION
        "
        The total number of packets(including bad packets)
        received on this interface.
        "
    ::= { ibHPEOCCableInfoEntry 5 }

ibHPEOCAvgOutPower OBJECT-TYPE
    SYNTAX      Integer32
    MAX-ACCESS  read-only
    STATUS      current
    DESCRIPTION
        "
        The cable port's power sent on average, the unit is db.
        "
    ::= { ibHPEOCCableInfoEntry 6 }

ibHPEOCAvgOutPBCRCErrors OBJECT-TYPE
    SYNTAX      Unsigned32
    MAX-ACCESS  read-only
    STATUS      current
    DESCRIPTION
        "
        The cable port's physical block(PB) cyclic redundancy
        check(CRC) errors sent on average.
        "
    ::= { ibHPEOCCableInfoEntry 7 }

ibHPEOCOutTotalPkts OBJECT-TYPE
    SYNTAX      Counter64
    MAX-ACCESS  read-only
    STATUS      current
    DESCRIPTION
        "
        The total count of the packets(including bad packets)
        sent on this interface.
        "
    ::= { ibHPEOCCableInfoEntry 8 }

--
-- ibHPEOCBitPerSymbolTable
--

ibHPEOCBitPerSymbolTable OBJECT-TYPE
    SYNTAX      SEQUENCE OF IbHPEOCBitPerSymbolEntry
    MAX-ACCESS  not-accessible
    STATUS      current
    DESCRIPTION
        "
        This table defines the bits per symbol parameters of the
        cable line.
        "
    ::= { ibHPEOCCableInfo 2 }

ibHPEOCBitPerSymbolEntry OBJECT-TYPE
    SYNTAX      IbHPEOCBitPerSymbolEntry
    MAX-ACCESS  not-accessible
    STATUS      current
    DESCRIPTION
        "
        The entry of the table ibHPEOCBitPerSymbolTable.
        "
    INDEX
        {
            ifIndex,
            ibHPEOCBitPerSymbolIndex
        }
    ::= { ibHPEOCBitPerSymbolTable 1 }

IbHPEOCBitPerSymbolEntry ::= SEQUENCE
    {
        ibHPEOCBitPerSymbolIndex      Unsigned32,
        ibHPEOCBitPerSymbol           OCTET STRING
    }

ibHPEOCBitPerSymbolIndex OBJECT-TYPE
    SYNTAX     Unsigned32
    MAX-ACCESS not-accessible
    STATUS     current
    DESCRIPTION
        "
        The index of the ibHPEOCBitPerSymbolTable.
        "
    ::= { ibHPEOCBitPerSymbolEntry 1 }

ibHPEOCBitPerSymbol OBJECT-TYPE
    SYNTAX      OCTET STRING
    MAX-ACCESS  read-only
    STATUS      current
    DESCRIPTION
        "
        ibHPEOCBitPerSymbol returns all the bits per symbol on the fixed
        frequency.  Each 4 bits stand for one value, all the values
        picking-up will make up a cable bit map.
        "
    ::= { ibHPEOCBitPerSymbolEntry 2 }

--
-- ibHPEOCTemplate
--

ibHPEOCTemplate OBJECT IDENTIFIER ::= { ibHPEOC 3 }

--
-- ibHPEOCTemplateGlobalTable
--

ibHPEOCTemplateGlobalTable OBJECT-TYPE
    SYNTAX      SEQUENCE OF IbHPEOCTemplateGlobalEntry
    MAX-ACCESS  not-accessible
    STATUS      current
    DESCRIPTION
        "
        This table defines the global parameters of the
        Template information.
        "
    ::= { ibHPEOCTemplate 1 }

ibHPEOCTemplateGlobalEntry OBJECT-TYPE
    SYNTAX      IbHPEOCTemplateGlobalEntry
    MAX-ACCESS  not-accessible
    STATUS      current
    DESCRIPTION
        "
        The entry of the table ibHPEOCTemplateGlobalTable.
        "
    INDEX
        {
            ibHPEOCTemplateIndex
        }
    ::= { ibHPEOCTemplateGlobalTable 1 }

IbHPEOCTemplateGlobalEntry ::= SEQUENCE
    {
        ibHPEOCTemplateIndex            Integer32,
        ibHPEOCTemplateType             Integer32,
        ibHPEOCTemplateName             DisplayString,
        ibHPEOCTemplateDescr            DisplayString,
        ibHPEOCTemplateCnuMaxDownBW     Integer32,
        ibHPEOCTemplateCnuMaxUpBW       Integer32,
        ibHPEOCTemplateCnuBcastControl  TruthValue,
        ibHPEOCTemplateCnuMacLimit      Unsigned32,
        ibHPEOCTemplateCb201VlanEn      TruthValue,
        ibHPEOCTemplateRowStatus        RowStatus
    }

ibHPEOCTemplateIndex OBJECT-TYPE
    SYNTAX      Integer32
    MAX-ACCESS  read-create
    STATUS      current
    DESCRIPTION
        "
        The index of cable Template.
        "
    ::= { ibHPEOCTemplateGlobalEntry 1 }

ibHPEOCTemplateType OBJECT-TYPE
    SYNTAX      INTEGER
        {
            switch(1),
            gateway(2)
        }
    MAX-ACCESS  read-create
    STATUS      current
    DESCRIPTION
        "
        The cable Template's type, can not change after create it.
        "
    ::= { ibHPEOCTemplateGlobalEntry 2 }

ibHPEOCTemplateName OBJECT-TYPE
    SYNTAX      DisplayString
    MAX-ACCESS  read-write
    STATUS      current
    DESCRIPTION
        "
        The cable Template's name, it's recommended to set it
        uniquely and understandably. Length: 1 to 15 characters.
        "
    ::= { ibHPEOCTemplateGlobalEntry 3 }

ibHPEOCTemplateDescr OBJECT-TYPE
    SYNTAX     DisplayString
    MAX-ACCESS read-write
    STATUS     current
    DESCRIPTION
        "
        The cable Template's description. Length: 0 to 63 characters.
        "
    ::= { ibHPEOCTemplateGlobalEntry 4 }

ibHPEOCTemplateCnuMaxDownBW OBJECT-TYPE
    SYNTAX     Integer32
    MAX-ACCESS read-write
    STATUS     current
    DESCRIPTION
        "
        Maximum downstream bandwidth allowed for the CNU,
        measured in Kbit/s, ranges from 0 to 16384, and must be multiples of 64.
        "
    ::= { ibHPEOCTemplateGlobalEntry 5 }

ibHPEOCTemplateCnuMaxUpBW OBJECT-TYPE
    SYNTAX     Integer32
    MAX-ACCESS read-write
    STATUS     current
    DESCRIPTION
        "
        Maximum upstream bandwidth allowed for the CNU,
        measured in Kbit/s, ranges from 0 to 16384, and must be multiples of 64.
        "
    ::= { ibHPEOCTemplateGlobalEntry 6 }

ibHPEOCTemplateCnuBcastControl OBJECT-TYPE
    SYNTAX      TruthValue
    MAX-ACCESS  read-write
    STATUS      current
    DESCRIPTION
        "
        Broadcast storm suppression status.
        true(1)  - Broadcast storm suppression enable.
        false(2) - Broadcast storm suppression disable.
        "
    ::= { ibHPEOCTemplateGlobalEntry 7 }

ibHPEOCTemplateCnuMacLimit OBJECT-TYPE
    SYNTAX      Unsigned32
    MAX-ACCESS  read-write
    STATUS      current
    DESCRIPTION
        "
        Configure the max number of MAC address entries which can access
        through the CNU, it ranges from 1 to 8.
        Otherwise,
        If configure 0, the CNU won't limit the MAC address entry.
        If configure 0xFF, it means no MAC address entry can access the CNU.
        "
    ::= { ibHPEOCTemplateGlobalEntry 8 }

ibHPEOCTemplateCb201VlanEn OBJECT-TYPE
    SYNTAX      TruthValue
    MAX-ACCESS  read-write
    STATUS      current
    DESCRIPTION
        "
        Use for Cb201 cnu only.
        true(1)  - Enable vlan insert function.
        false(2) - Disable vlan insert function.
        "
    ::= { ibHPEOCTemplateGlobalEntry 9 }

ibHPEOCTemplateRowStatus OBJECT-TYPE
    SYNTAX     RowStatus
    MAX-ACCESS read-create
    STATUS     current
    DESCRIPTION
        "
        Operation status.
        "
    ::= { ibHPEOCTemplateGlobalEntry 10 }

--
-- ibHPEOCTemplateSwitchTable
--

ibHPEOCTemplateSwitchTable OBJECT-TYPE
    SYNTAX      SEQUENCE OF IbHPEOCTemplateSwitchEntry
    MAX-ACCESS  not-accessible
    STATUS      current
    DESCRIPTION
        "
        This table defines the port parameters of the
        switch type cnu. it's not affect on the type of gateway Template.
        "
    ::= { ibHPEOCTemplate 2 }

ibHPEOCTemplateSwitchEntry OBJECT-TYPE
    SYNTAX      IbHPEOCTemplateSwitchEntry
    MAX-ACCESS  not-accessible
    STATUS      current
    DESCRIPTION
        "
        The entry of the table ibHPEOCTemplateSwitchTable.
        "
    INDEX
        {
            ibHPEOCTemplateIndex,
            ibHPEOCTemplateUniIndex
        }
    ::= { ibHPEOCTemplateSwitchTable 1 }

IbHPEOCTemplateSwitchEntry ::= SEQUENCE
    {
        ibHPEOCTemplateUniIndex            Integer32,
        ibHPEOCTemplateUniSpeed            INTEGER,
        ibHPEOCTemplateUniDuplex           INTEGER,
        ibHPEOCTemplateUniPriority         Integer32,
        ibHPEOCTemplateUniFlowControl      TruthValue,
        ibHPEOCTemplateUniUpLineRate       Unsigned32,
        ibHPEOCTemplateUniDownLineRate     Unsigned32,
        ibHPEOCTemplateUniAdminStatus      INTEGER,
        ibHPEOCTemplateUniVLANType         INTEGER,
        ibHPEOCTemplateUniPvid             Integer32,
        ibHPEOCTemplateUniVlanTag          INTEGER
    }

ibHPEOCTemplateUniIndex OBJECT-TYPE
    SYNTAX     Integer32
    MAX-ACCESS not-accessible
    STATUS     current
    DESCRIPTION
        "
        The index value which uniquely identifies the FE
        interface of the CNU.
        "
    ::= { ibHPEOCTemplateSwitchEntry 1 }

ibHPEOCTemplateUniSpeed OBJECT-TYPE
    SYNTAX     INTEGER
        {
            auto(1),
            s10M(10),
            s100M(100)
        }
    MAX-ACCESS read-write
    STATUS     current
    DESCRIPTION
        "
        User network interface speed.
        "
    ::= { ibHPEOCTemplateSwitchEntry 2 }

ibHPEOCTemplateUniDuplex OBJECT-TYPE
    SYNTAX     INTEGER
        {
            full(1),
            half(2),
            auto(3)
        }
    MAX-ACCESS read-write
    STATUS     current
    DESCRIPTION
        "
        User network interface mode.
        "
    ::= { ibHPEOCTemplateSwitchEntry 3 }

ibHPEOCTemplateUniPriority OBJECT-TYPE
    SYNTAX     Integer32 (0..7)
    MAX-ACCESS read-write
    STATUS     current
    DESCRIPTION
        "
        The default ingress User Priority for this port.  This
        only has effect on media, such as Ethernet, that do not
        support native User Priority.
        "
    ::= { ibHPEOCTemplateSwitchEntry 4 }

ibHPEOCTemplateUniFlowControl OBJECT-TYPE
    SYNTAX      TruthValue
    MAX-ACCESS  read-write
    STATUS      current
    DESCRIPTION
        "Flow control status.
        true(1)  - Flow control status enable.
        false(2) - Flow control status disable."
    DEFVAL
        {
            false
        }
    ::= { ibHPEOCTemplateSwitchEntry 5 }

ibHPEOCTemplateUniUpLineRate OBJECT-TYPE
    SYNTAX     Unsigned32
    MAX-ACCESS read-write
    STATUS     current
    DESCRIPTION
        "
        The max speed upload in units of 1,024 bits per second
        on this interface.  The value should between 0 and 8Mbps.
        If the value is 0, it means that the upload speed is only
        restricted by the physical line.
        "
    ::= { ibHPEOCTemplateSwitchEntry 6 }

ibHPEOCTemplateUniDownLineRate OBJECT-TYPE
    SYNTAX     Unsigned32
    MAX-ACCESS read-write
    STATUS     current
    DESCRIPTION
        "
        The max speed download in units of 1,024 bits per second
        on this interface.  The value should between 0 and 8Mbps.
        If the value is 0, it means that the download speed is only
        restricted by the physical line.
        "
    ::= { ibHPEOCTemplateSwitchEntry 7 }

ibHPEOCTemplateUniAdminStatus OBJECT-TYPE
    SYNTAX      INTEGER
        {
            up(1),
            down(2)
        }
    MAX-ACCESS  read-write
    STATUS      current
    DESCRIPTION
        "
        Control if open or close the UNI.  If choose up(1), means the UNI is
        opened and packets can pass it.  If choose down(2), means the UNI is
        closed and all packets will be discard.
        "
    ::= { ibHPEOCTemplateSwitchEntry 8 }

ibHPEOCTemplateUniVLANType OBJECT-TYPE
    SYNTAX     INTEGER
        {
            access(1),
            trunk(2),
            hybrid(3)
        }
    MAX-ACCESS read-write
    STATUS     current
    DESCRIPTION
        "port vlan types.
        hybrid (3) port can carry multiple VLANs.
        "
    ::= { ibHPEOCTemplateSwitchEntry 9 }

ibHPEOCTemplateUniPvid OBJECT-TYPE
    SYNTAX     Integer32 (1..4094)
    MAX-ACCESS read-write
    STATUS     current
    DESCRIPTION
        "
        The PVID, the VLAN ID assigned to untagged frames or
        Priority-Tagged frames received on this port.
        "
    REFERENCE
        "
        IEEE 802.1Q/D11 Section 12.10.1.1
        "
    DEFVAL
        {
            1
        }
    ::= { ibHPEOCTemplateSwitchEntry 10 }

ibHPEOCTemplateUniVlanTag OBJECT-TYPE
    SYNTAX     INTEGER
        {
            tagged(1),
            untagged(2)
        }
    MAX-ACCESS read-write
    STATUS     current
    DESCRIPTION
        "
        VLAN is set tagged or untagged.
        "
    ::= { ibHPEOCTemplateSwitchEntry 11 }

--
-- ibHPEOCCnuAccess
--
ibHPEOCCnuAccess OBJECT IDENTIFIER ::= { ibHPEOC 4 }

--
-- ibHPEOCCnuAccessTable
--

ibHPEOCCnuAccessTable OBJECT-TYPE
    SYNTAX      SEQUENCE OF IbHPEOCCnuAccessEntry
    MAX-ACCESS  not-accessible
    STATUS      current
    DESCRIPTION
        "
        This table defines the global parameters of the
        cnu type permitting to access.
        "
    ::= { ibHPEOCCnuAccess 1 }

ibHPEOCCnuAccessEntry OBJECT-TYPE
    SYNTAX      IbHPEOCCnuAccessEntry
    MAX-ACCESS  not-accessible
    STATUS      current
    DESCRIPTION
        "
        The entry of the table ibHPEOCCnuAccessTable.
        "
    INDEX
        {
            ibHPEOCCnuAccessIndex
        }
    ::= { ibHPEOCCnuAccessTable 1 }


IbHPEOCCnuAccessEntry ::= SEQUENCE
    {
        ibHPEOCCnuAccessIndex        Integer32,
        ibHPEOCCnuHFID               DisplayString,
        ibHPEOCManuInfo              DisplayString,
        ibHPEOCCnuType               Integer32,
        ibHPEOCCnuSwitchType         Integer32,
        ibHPEOCCnuUniNum             Integer32,
        ibHPEOCCnuPhy2Uni            OCTET STRING,
        ibHPEOCCnuAccessRowStatus    RowStatus
    }

ibHPEOCCnuAccessIndex OBJECT-TYPE
    SYNTAX     Integer32
    MAX-ACCESS read-create
    STATUS     current
    DESCRIPTION
        "
        The index value which uniquely identifies the
        manuinfo of the CNU.
        "
    ::= { ibHPEOCCnuAccessEntry 1 }

ibHPEOCCnuHFID OBJECT-TYPE
    SYNTAX     DisplayString
    MAX-ACCESS read-write
    STATUS     current
    DESCRIPTION
        "
        The Cnu's HFID. Every type Cnu has it's unique HFID.
        Length: 1 to 64 characters.
        "
    ::= { ibHPEOCCnuAccessEntry 2 }

ibHPEOCManuInfo OBJECT-TYPE
    SYNTAX     DisplayString
    MAX-ACCESS read-write
    STATUS     current
    DESCRIPTION
        "
        The Cnu's manufactory infofamiont.
        Length: 0 to 63 characters.
        "
    ::= { ibHPEOCCnuAccessEntry 3 }

ibHPEOCCnuType OBJECT-TYPE
    SYNTAX      INTEGER
        {
            switch(1),
            gateway(2)
        }
    MAX-ACCESS  read-write
    STATUS      current
    DESCRIPTION
        "
        The Cnu's function type.
        "
    ::= { ibHPEOCCnuAccessEntry 4 }

ibHPEOCCnuSwitchType OBJECT-TYPE
    SYNTAX      INTEGER
        {
            rtl8306e(1),
            ar8236(2),
            mv6061(3),
            mv6031(4)
        }
    MAX-ACCESS  read-write
    STATUS      current
    DESCRIPTION
        "
        The Cnu's switch chip type. It's useless for gataway type cnu.
        "
    ::= { ibHPEOCCnuAccessEntry 5 }

ibHPEOCCnuUniNum OBJECT-TYPE
    SYNTAX      Integer32
    MAX-ACCESS  read-write
    STATUS      current
    DESCRIPTION
        "
        Uni number of the Cnu. It's useless for gataway type cnu.
        "
    ::= { ibHPEOCCnuAccessEntry 6 }

ibHPEOCCnuPhy2Uni OBJECT-TYPE
    SYNTAX      OCTET STRING
    MAX-ACCESS  read-write
    STATUS      current
    DESCRIPTION
        "
        Reflection from phy port to uni port of the cnu.
        It's useless for gataway type cnu.
        For example, phy port 0,1,2,3 is reflect to uni port
        1,2,3,4, then the value of this mib is {0,1,2,3}
        "
    ::= { ibHPEOCCnuAccessEntry 7 }

ibHPEOCCnuAccessRowStatus OBJECT-TYPE
    SYNTAX     RowStatus
    MAX-ACCESS read-create
    STATUS     current
    DESCRIPTION
        "
        Operation status.
        "
    ::= { ibHPEOCCnuAccessEntry 8 }

END
