-- =============================================================
-- Copyright (C) 2023 Intelbras S.A. All rights reserved.
--
-- Description:
-- Reference:  extension of RFC 1213 and RFC 2233
-- Version: V1.2
-- History:
--   V1.0 2004-12-01
--        Initial Version  by lizhiyong and fangmin
--   V1.1 2009-06-08 modified by TONGWEI
--        Added ibt1Table and ibt1InterfaceTable
--   V1.2 2012-07-16 modified SYNTAX of ibt1Clock by shuaixiaojuan.
-- =============================================================
IB-T1-MIB DEFINITIONS ::= BEGIN

IMPORTS
        MODULE-IDENTITY,
        OBJECT-TYPE,
        Integer32,
        Counter32
                FROM SNMPv2-SMI
        TEXTUAL-CONVENTION
                FROM SNMPv2-TC
        MODULE-COMPLIANCE,
        OBJECT-GROUP
                FROM SNMPv2-CONF
        ifIndex
                FROM RFC1213-MIB
        ibCommon
                FROM IB-OID-MIB;



-- =============================================================
-- T1 Module
-- =============================================================
ibT1    MODULE-IDENTITY
        LAST-UPDATED "201207161741Z"
        ORGANIZATION
            "Intelbras S.A. Industria de Telecomunicacao Eletronica Brasileria."
        CONTACT-INFO
            ""
        DESCRIPTION
             "This MIB provides T1 interface information that are
             excluded by RFC 1213 and RFC 2233"
        REVISION        "201207161741Z"
        DESCRIPTION
                "To fix bugs in the MIB file."
        REVISION        "200906081741Z"
        DESCRIPTION
                "To fix bugs in the MIB file."
        REVISION        "200412011436Z"
        DESCRIPTION
                "Initial version of this MIB module."
        ::= { ibCommon 29 }


ibt1InterfaceStatusTable OBJECT-TYPE
        SYNTAX      SEQUENCE OF IbT1InterfaceStatusEntry
        MAX-ACCESS   not-accessible
        STATUS       current
        DESCRIPTION
         "This table contains interface packet statistics  "
        ::= { ibT1 1 }

ibt1InterfaceStatusEntry OBJECT-TYPE
        SYNTAX         IbT1InterfaceStatusEntry
        MAX-ACCESS     not-accessible
        STATUS         current
        DESCRIPTION
         "This  entry contains interface packet statistics.
         The index of this Entry is ifIndex defined in ifTable
         of RFC1213-MIB"
        INDEX { ifIndex }
        ::= { ibt1InterfaceStatusTable 1 }

IbT1InterfaceStatusEntry ::= SEQUENCE  {
        ibt1InterfaceInErrs            Counter32,
        ibt1InterfaceInRuntsErrs       Counter32,
        ibt1InterfaceInGiantsErrs      Counter32,
        ibt1InterfaceInCrcErrs         Counter32,
        ibt1InterfaceInAlignErrs       Counter32,
        ibt1InterfaceInOverRunsErrs    Counter32,
        ibt1InterfaceInDribblesErrs    Counter32,
        ibt1InterfaceInAbortedSeqErrs  Counter32,
        ibt1InterfaceInNoBufferErrs    Counter32,
        ibt1InterfaceInFramingErrs     Counter32,
        ibt1InterfaceOutputErrs        Counter32,
        ibt1InterfaceOutUnderRunErrs   Counter32,
        ibt1InterfaceOutCollisonsErrs  Counter32,
        ibt1InterfaceOutDeferedErrs    Counter32
        }

ibt1InterfaceInErrs        OBJECT-TYPE
        SYNTAX          Counter32
        MAX-ACCESS      read-only
        STATUS          current
        DESCRIPTION
         "The total number of error received on this interface"
        ::= { ibt1InterfaceStatusEntry 1 }

ibt1InterfaceInRuntsErrs   OBJECT-TYPE
        SYNTAX          Counter32
        MAX-ACCESS      read-only
        STATUS          current
        DESCRIPTION
         "The number of Runts Error(too short packet) received on this interface"
        ::= { ibt1InterfaceStatusEntry 2 }

ibt1InterfaceInGiantsErrs OBJECT-TYPE
        SYNTAX          Counter32
        MAX-ACCESS      read-only
        STATUS          current
        DESCRIPTION
         "The number of Giants Error(too long packet) received on this interface"
        ::= { ibt1InterfaceStatusEntry 3 }

ibt1InterfaceInCrcErrs     OBJECT-TYPE
        SYNTAX          Counter32
        MAX-ACCESS      read-only
        STATUS          current
        DESCRIPTION
         "The number of CRC Error received on this interface"
        ::= { ibt1InterfaceStatusEntry 4 }

ibt1InterfaceInAlignErrs   OBJECT-TYPE
        SYNTAX          Counter32
        MAX-ACCESS      read-only
        STATUS          current
        DESCRIPTION
         "The number of Align Error received on this interface"
        ::= { ibt1InterfaceStatusEntry 5 }

ibt1InterfaceInOverRunsErrs OBJECT-TYPE
        SYNTAX           Counter32
        MAX-ACCESS       read-only
        STATUS          current
        DESCRIPTION
         "The number of Over Runs Error received on this interface"
        ::= { ibt1InterfaceStatusEntry 6 }

ibt1InterfaceInDribblesErrs  OBJECT-TYPE
        SYNTAX            Counter32
        MAX-ACCESS        read-only
        STATUS            current
        DESCRIPTION
         "The number of dribble packets received"
        ::= { ibt1InterfaceStatusEntry 7 }

ibt1InterfaceInAbortedSeqErrs    OBJECT-TYPE
        SYNTAX                Counter32
        MAX-ACCESS            read-only
        STATUS                current
        DESCRIPTION
         "The number of AbortedSeq Error received on this interface"
        ::= { ibt1InterfaceStatusEntry 8 }

ibt1InterfaceInNoBufferErrs      OBJECT-TYPE
        SYNTAX                Counter32
        MAX-ACCESS            read-only
        STATUS                current
        DESCRIPTION
         "The number of Error (no buffer available)"
        ::= { ibt1InterfaceStatusEntry 9 }

ibt1InterfaceInFramingErrs       OBJECT-TYPE
        SYNTAX                Counter32
        MAX-ACCESS            read-only
        STATUS                current
        DESCRIPTION
         "The number of framing Errors"
        ::= { ibt1InterfaceStatusEntry 10 }

ibt1InterfaceOutputErrs          OBJECT-TYPE
        SYNTAX                Counter32
        MAX-ACCESS            read-only
        STATUS                current
        DESCRIPTION
         "The number of total Error transmited on this interface"
        ::= { ibt1InterfaceStatusEntry 11 }

ibt1InterfaceOutUnderRunErrs     OBJECT-TYPE
        SYNTAX                Counter32
        MAX-ACCESS            read-only
        STATUS                current
        DESCRIPTION
         "The number of UnderRun Error transmited on this interface"
        ::= { ibt1InterfaceStatusEntry 12 }

ibt1InterfaceOutCollisonsErrs    OBJECT-TYPE
        SYNTAX                Counter32
        MAX-ACCESS            read-only
        STATUS                current
        DESCRIPTION
         "The number of Collisions Error transmited on this interface"
        ::= { ibt1InterfaceStatusEntry 13 }

ibt1InterfaceOutDeferedErrs      OBJECT-TYPE
        SYNTAX                Counter32
        MAX-ACCESS            read-only
        STATUS                current
        DESCRIPTION
         "The number of Deferred Error transmited on this interface"
        ::= { ibt1InterfaceStatusEntry 14 }

ibt1Table OBJECT-TYPE
        SYNTAX      SEQUENCE OF IbT1Entry
        MAX-ACCESS   not-accessible
        STATUS       current
        DESCRIPTION
         "A list of T1 interface entries."
        ::= { ibT1 2 }

ibt1Entry OBJECT-TYPE
        SYNTAX         IbT1Entry
        MAX-ACCESS     not-accessible
        STATUS         current
        DESCRIPTION
         "This entry contains T1 interface management information."
        INDEX { ifIndex }
        ::= { ibt1Table 1 }

IbT1TimeSlot ::= TEXTUAL-CONVENTION
        STATUS      current
        DESCRIPTION
            "Each octet within this value specifies a set of time
            slots, with the first octet specifying time slot 1 through
            8, the second octet specifying time slots 9 through 16, etc.
            Within each octet, the most significant bit represents
            the highest numbered time slot, and the least significant bit
            represents the lowest numbered time slot.  Thus, each time slot
            of the T1 is represented by a single bit within the
            value of this object.  If that bit has a value of '1'
            then that time slot is included in the set of time slots;
            the time slot is not included if its bit has a value of '0'."
        SYNTAX      OCTET STRING(SIZE (3))

IbT1Entry ::= SEQUENCE  {
        ibt1Type              BITS,
        ibt1Clock             INTEGER,
        ibt1FrameFormat       INTEGER,
        ibt1LineCode          INTEGER,
        ibt1PriSetTimeSlot    IbT1TimeSlot,
        ibt1DChannelIndex     Integer32,
        ibt1SubScribLineChannelIndex Integer32
        }

ibt1Type              OBJECT-TYPE
        SYNTAX  BITS {
                    voice(0)
                }
        MAX-ACCESS      read-only
        STATUS          current
        DESCRIPTION
         "Specifies the type of the T1 interface."
        ::= { ibt1Entry 1 }

ibt1Clock             OBJECT-TYPE
        SYNTAX  INTEGER {
                    slave(1),
                    master(2),
                    internal(3),
                    line(4),
                    linePri(5)
                }
        MAX-ACCESS      read-write
        STATUS          current
        DESCRIPTION
         "Specifies the clock type used on the T1 interface."
        ::= { ibt1Entry 2 }

ibt1FrameFormat       OBJECT-TYPE
        SYNTAX   INTEGER {
                    sf(1),
                    esf(2)
                }
        MAX-ACCESS      read-write
        STATUS          current
        DESCRIPTION
         "Specifies the frame format used on the T1 interface."
        DEFVAL { esf }
        ::= { ibt1Entry 3 }

ibt1LineCode          OBJECT-TYPE
        SYNTAX  INTEGER {
                    ami(1),
                    b8zs(2)
                }
        MAX-ACCESS      read-write
        STATUS          current
        DESCRIPTION
         "Specifies the line code type used on the T1 interface."
        DEFVAL { b8zs }
        ::= { ibt1Entry 4 }

ibt1PriSetTimeSlot    OBJECT-TYPE
        SYNTAX          IbT1TimeSlot
        MAX-ACCESS      read-write
        STATUS          current
        DESCRIPTION
         "This is a bit-map of PRI time slots used on the T1 interface.
         It needs to administratively shut down the D channel of
         the T1 interface before cancelling PRI time slots."
        ::= { ibt1Entry 5 }

ibt1DChannelIndex      OBJECT-TYPE
        SYNTAX                Integer32
        MAX-ACCESS            read-only
        STATUS                current
        DESCRIPTION
         "This is the ifIndex of the D channel of the T1 interface."
        ::= { ibt1Entry 6 }

ibt1SubScribLineChannelIndex      OBJECT-TYPE
        SYNTAX                Integer32
        MAX-ACCESS            read-only
        STATUS                current
        DESCRIPTION
         "This is the ifIndex of the subscriber-line channel of the T1 interface."
        ::= { ibt1Entry 7 }

ibt1InterfaceTable OBJECT-TYPE
        SYNTAX      SEQUENCE OF IbT1InterfaceEntry
        MAX-ACCESS   not-accessible
        STATUS       current
        DESCRIPTION
         "A list of channels of T1 interface entries.
         Including D channels and subscriber-line channels."
        ::= { ibT1 3 }

ibt1InterfaceEntry OBJECT-TYPE
        SYNTAX         IbT1InterfaceEntry
        MAX-ACCESS     not-accessible
        STATUS         current
        DESCRIPTION
         "This entry contains channels of T1 interface management information.
         Including D channels and subscriber-line channels."
        INDEX { ifIndex }
        ::= { ibt1InterfaceTable 1 }

IbT1InterfaceEntry ::= SEQUENCE  {
        ibt1ControllerIndex        Integer32
        }

ibt1ControllerIndex      OBJECT-TYPE
        SYNTAX                Integer32
        MAX-ACCESS            read-only
        STATUS                current
        DESCRIPTION
         "Which T1 interface is this channel belonged to."
        ::= { ibt1InterfaceEntry 1 }

END
