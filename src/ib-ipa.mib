-- ============================================================================
-- Copyright (C) 2023 Intelbras S.A. All rights reserved.
--
-- Description: This MIB is designed for IP Accounting Software
-- Reference:
-- Version: V1.0
-- History:
-- V1.0 created by kongfanhua.
-- ============================================================================
IB-IPA-MIB DEFINITIONS ::= BEGIN

IMPORTS
    MODULE-IDENTITY, OBJECT-TYPE, Counter32, Counter64,
    Integer32, IpAddress
        FROM SNMPv2-SMI
    RowStatus, TEXTUAL-CONVENTION
        FROM SNMPv2-TC
    ibCommon
        FROM IB-OID-MIB;


ibIpa MODULE-IDENTITY
       LAST-UPDATED "200411010000Z"
       ORGANIZATION
           "Intelbras S.A. Industria de Telecomunicacao Eletronica Brasileria."
       CONTACT-INFO
           ""
       DESCRIPTION
            "
            This MIB is used to acquire ip accounting information.

            The ibIpaAccountListTable is set by user to define the group of ip address
            which they want to account.
            This module can be enabled in each port,
            which was defined in the ibIpaIfConfigTable.

            If this module has been enabled, the packets will be accounted
            when crossing the router from the ports having been enabled by user,
            according to whether the source/destination ip address is in ibIpaAccountListTable
            and what kinds of function(in/out/both/fw) are enabled
            and also whether it is denied by the firewall.
            If it is denied by the firewall, it will be accounted in ibIpaFWListTable
            If it is accepted by the firewall, and ip source or ip destination is in ibIpaAccountListTable,
            it will be accounted in ibIpaIntListTable, otherwise it will be accounted
            in ibIpaExtListTable.

            And IP Accounting function also differentiates the packets by direction.
            If the packet is inbound, the accounting information can be seen as
              ibIpaIntListInPackets/ibIpaIntListInBytes in ibIpaIntListTable,
              ibIpaExtListInPackets/ibIpaExtListInBytes in ibIpaExtListTable,
              ibIpaFWListInPackets/ibIpaFWListInBytes in ibIpaFWListTable.

            or else the accounting information can be seen as
              ibIpaIntListOutPackets/ibIpaIntListOutBytes in ibIpaIntListTable,
              ibIpaExtListOutPackets/ibIpaExtListOutBytes in ibIpaExtListTable,
              ibIpaFWListOutPackets/ibIpaFWListOutBytes in ibIpaFWListTable.
            "
        ::= { ibCommon 25 }

   InterfaceIndex ::= TEXTUAL-CONVENTION
       DISPLAY-HINT "d"
       STATUS       current
       DESCRIPTION
               "A unique value, greater than zero, for each interface
               or interface sub-layer in the managed system.  It is
               recommended that values are assigned contiguously
               starting from 1.  The value for each interface sub-
               layer must remain constant at least from one re-
               initialization of the entity's network management
               system to the next re-initialization."
       SYNTAX       Integer32 (1..2147483647)


-- =============================================================================
   -- ibIpaGlobalConfigTable
   --  The Global Data Set By User of IPA

    ibIpaGlobalStats OBJECT IDENTIFIER ::= { ibIpa 1 }

    ibIpaGlobalEnable OBJECT-TYPE
        SYNTAX      INTEGER {
                        disabled(1),  -- the IPA function is disabled
                        enabled(2)    -- the IPA function is enabled
                       }
           MAX-ACCESS  read-write
        STATUS      current
        DESCRIPTION
               "
               The indication of whether Ip Accounting function is enabled.
               If it is disabled, ip packets will not be accounted.
               "
        DEFVAL        { disabled }
        ::= { ibIpaGlobalStats 1 }

    ibIpaTimeOutSeconds OBJECT-TYPE
        SYNTAX      Integer32
        MAX-ACCESS  read-write
        STATUS      current
        DESCRIPTION
               "
               The value of List aging timeout.
               The unit is second.
               If exceeding the interval, the item in ibIpaIntListTable, ibIpaExtListTable
               and ibIpaFWListTable will be removed automaticlly.
               The range is (3600..604800).
               "
        DEFVAL        { 43200 }
        ::= { ibIpaGlobalStats 2 }

    ibIpaIntListMaxItemNum OBJECT-TYPE
        SYNTAX      Integer32
        MAX-ACCESS  read-write
        STATUS      current
        DESCRIPTION
               "
               The max number of items in ibIpaIntListTable.
               The range is (0..16384).
               "
        DEFVAL        { 512 }
        ::= { ibIpaGlobalStats 3 }

    ibIpaExtListMaxItemNum OBJECT-TYPE
        SYNTAX      Integer32
        MAX-ACCESS  read-write
        STATUS      current
        DESCRIPTION
               "
               The max number of items in ibIpaExtListTable.
               The range is (0..8192).
               "
        DEFVAL        { 0 }
        ::= { ibIpaGlobalStats 4 }

    ibIpaFWListMaxItemNum OBJECT-TYPE
        SYNTAX      Integer32
        MAX-ACCESS  read-only
        STATUS      current
        DESCRIPTION
               "
               The max number of items in ibIpaFWListTable.
               "
        ::= { ibIpaGlobalStats 5 }

     ibIpaAccountListMaxItemNum OBJECT-TYPE
        SYNTAX      Integer32
        MAX-ACCESS  read-only
        STATUS      current
        DESCRIPTION
               "
               The max number of items in ibIpaAccountListTable.
               "
        ::= { ibIpaGlobalStats 6 }

     ibIpaAccountListNextIndex OBJECT-TYPE
        SYNTAX      Integer32
        MAX-ACCESS  read-only
        STATUS      current
        DESCRIPTION
               "
               The next available index for creating rows of ibIpaAccountListTable.
               If the value is zero, it means the table is full and no available index
               can be used.
               "
        ::= { ibIpaGlobalStats 7 }

    ibIpaListCleaningFlag OBJECT-TYPE
        SYNTAX      INTEGER {
                        idle(1),             -- idling
                        cleaningAll(2),      -- clearing all of the tables below.
                        cleaningIntList(3),  -- clearing ibIpaIntListTable
                        cleaningExtList(4),  -- clearing ibIpaExtListTable
                        cleaningFWList(5)    -- clearing ibIpaFWListTable
                    }
          MAX-ACCESS  read-write
        STATUS      current
        DESCRIPTION
               "
               Cleaning List in this module.
               The default value is idle. If user wants to clean some lists, he
               can set the value to 2, 3, 4 and 5 to clean the corresponding list.
               After the operation, the value will return to idle.
               "
        DEFVAL        { idle }
        ::= { ibIpaGlobalStats 8 }


-- =============================================================================
   -- ibIpaIfConfigTable
   --  enable or disable and show ip accounting function under interface

     ibIpaIfConfigTable OBJECT-TYPE
         SYNTAX   SEQUENCE OF IbIpaIfConfigEntry
         MAX-ACCESS   not-accessible
         STATUS   current
         DESCRIPTION
            "
            Enable or disable the ip accounting inbound/outbound
            function under a particular interface.
            "
         ::= { ibIpa 2 }

    ibIpaIfConfigEntry OBJECT-TYPE
         SYNTAX   IbIpaIfConfigEntry
         MAX-ACCESS   not-accessible
         STATUS   current
         DESCRIPTION
            "
            Entry of the table.
            "
         INDEX { ibIpaIfConfigIfIndex }
         ::= { ibIpaIfConfigTable 1 }

    IbIpaIfConfigEntry ::=
        SEQUENCE {
            ibIpaIfConfigIfIndex
                InterfaceIndex,
            ibIpaIfConfigInEnable
                INTEGER,
            ibIpaIfConfigOutEnable
                INTEGER,
            ibIpaIfConfigFWEnable
                INTEGER
        }

    ibIpaIfConfigIfIndex OBJECT-TYPE
        SYNTAX   InterfaceIndex
        MAX-ACCESS   not-accessible
        STATUS   current
        DESCRIPTION
            "It equals to ifIndex"
        ::= { ibIpaIfConfigEntry 1 }

    ibIpaIfConfigInEnable OBJECT-TYPE
        SYNTAX      INTEGER {
            disabled(1),  -- inbound packets are not accounted in this interface
            enabled(2)    -- inbound packets are accounted in this interface
        }
        MAX-ACCESS  read-write
        STATUS      current

        DESCRIPTION
            "
            This object is applicable to ibIpaIntListTable and ibIpaExtListTable.
            If the value is disabled, inbound ip packets are not accounted.
            "
        DEFVAL        { disabled }
        ::= { ibIpaIfConfigEntry 2 }

    ibIpaIfConfigOutEnable OBJECT-TYPE
        SYNTAX      INTEGER {
            disabled(1),  -- outbound packets are not accounted in this interface
            enabled(2)    -- outbound packets are accounted in this interface
        }
        MAX-ACCESS  read-write
        STATUS      current
        DESCRIPTION
            "
            This object is applicable to ibIpaIntListTable and ibIpaExtListTable.
            If the value is disabled, outbound ip packets are not accounted.
            "
        DEFVAL        { disabled }
        ::= { ibIpaIfConfigEntry 3 }

    ibIpaIfConfigFWEnable OBJECT-TYPE
        SYNTAX      INTEGER {
            nodirection(1),
            inbound(2),
            outbound(3),
            bidirection(4)
        }
        MAX-ACCESS  read-write
        STATUS      current
        DESCRIPTION
            "
            This object is applicable to ibIpaFWListTable only.

            If the value is 'inbound', then inbound ip packets which are denied by firewall
            are accounted.
            If the value is 'outbound', then outbound ip packets which were denied by firewall
            are accounted.
            If the value is 'nodirection', neither inbound nor outbound ip packets
            which were denied by firewall are accounted.
            If the value is 'bidirection', both inbound and outbound ip packets which
            were denied by firewall are accounted.
            "
        DEFVAL        { nodirection }
        ::= { ibIpaIfConfigEntry 4 }

-- =============================================================================
     -- ibIpaAccountListTable
     -- The function of ibIpaAccountListTable is to classify the ip packets
     -- ibIpaAccountListTable is set and deleted by user

    ibIpaAccountListTable OBJECT-TYPE
        SYNTAX   SEQUENCE OF IbIpaAccountListEntry
        MAX-ACCESS   not-accessible
        STATUS   current
        DESCRIPTION
            "
            The List is used by user to sort packets into two groups
            by source or destination ip address.
            When source/destination ip address of a packet matches a item in this table,
            the packet is accounted in ibIpaIntListTable.
            When source/destination ip address of a packet does not match any item
            in this table, the packet is accounted in ibIpaExtListTable.
            "
         ::= { ibIpa 3 }

    ibIpaAccountListEntry OBJECT-TYPE
        SYNTAX   IbIpaAccountListEntry
        MAX-ACCESS   not-accessible
        STATUS   current
        DESCRIPTION
            "
            Entry of the table.
            "
        INDEX { ibIpaAccountListIndex }
        ::= { ibIpaAccountListTable 1 }

    IbIpaAccountListEntry ::=
        SEQUENCE {
            ibIpaAccountListIndex
                Integer32,
            ibIpaAccountListIpAddr
                IpAddress,
            ibIpaAccountListIpMask
                IpAddress,
            ibIpaAccountListRowStatus
                RowStatus
        }

    ibIpaAccountListIndex OBJECT-TYPE
        SYNTAX   Integer32(1..2147483647)
        MAX-ACCESS   not-accessible
        STATUS   current
        DESCRIPTION
            "
            The Index of the table.
            "
        ::= { ibIpaAccountListEntry 1 }

    ibIpaAccountListIpAddr OBJECT-TYPE
        SYNTAX      IpAddress
        MAX-ACCESS  read-create
        STATUS      current
        DESCRIPTION
            "
            The IP address to which this entry's addressing information
            pertains.
            "
        ::= { ibIpaAccountListEntry 2 }

    ibIpaAccountListIpMask OBJECT-TYPE
        SYNTAX      IpAddress
        MAX-ACCESS  read-create
        STATUS      current
        DESCRIPTION
            "
            The subnet mask associated with the IP address of this
            entry.  The value of the mask is an IP address with all the
            network bits set to 1 and all the hosts bits set to 0.
            "
        ::= { ibIpaAccountListEntry 3 }

    ibIpaAccountListRowStatus  OBJECT-TYPE
        SYNTAX RowStatus
        MAX-ACCESS read-create
        STATUS current
        DESCRIPTION
           "
           The row status of the entry,
           Supporting CreateAndGo and Destroy operation.
           "
        ::= { ibIpaAccountListEntry 4 }


-- =============================================================================
     -- ibIpaIntListTable
     -- for showing accounting information of packet not match ibIpaAccountListTable

    ibIpaIntListTable OBJECT-TYPE
        SYNTAX   SEQUENCE OF IbIpaIntListEntry
        MAX-ACCESS   not-accessible
        STATUS   current
        DESCRIPTION
            "
            If matching the ip address recorded in ibIpaAccountListTable
            and not denied by the firewall, the packets will be accounted
            in this list.
            "
        ::= { ibIpa 4 }

    ibIpaIntListEntry OBJECT-TYPE
        SYNTAX   IbIpaIntListEntry
        MAX-ACCESS   not-accessible
        STATUS   current
        DESCRIPTION
            "
            Entry of the table.
            "
        INDEX { ibIpaIntListIpSrc,
                ibIpaIntListIpDst,
                ibIpaIntListProtocol
              }
        ::= { ibIpaIntListTable 1 }

    IbIpaIntListEntry ::=
        SEQUENCE {
            ibIpaIntListIpSrc
                IpAddress,
            ibIpaIntListIpDst
                IpAddress,
            ibIpaIntListProtocol
                Integer32,
            ibIpaIntListInPackets
                Counter32,
            ibIpaIntListInBytes
                Counter64,
            ibIpaIntListOutPackets
                Counter32,
            ibIpaIntListOutBytes
                Counter64
        }

    ibIpaIntListIpSrc OBJECT-TYPE
        SYNTAX      IpAddress
        MAX-ACCESS  not-accessible
        STATUS      current
        DESCRIPTION
            "
            Source IP-address of these accounted packets.
            "
        ::= { ibIpaIntListEntry 1 }

    ibIpaIntListIpDst OBJECT-TYPE
        SYNTAX      IpAddress
        MAX-ACCESS  not-accessible
        STATUS      current
        DESCRIPTION
            "
            Destination IP-address of these accounted packets.
            "
        ::= { ibIpaIntListEntry 2 }

    ibIpaIntListProtocol OBJECT-TYPE
        SYNTAX Integer32(0..2147483647)
        MAX-ACCESS  not-accessible
        STATUS      current
        DESCRIPTION
            "
            The type of these accounted IP packets defined in RFC 1700.
            "
        ::= { ibIpaIntListEntry 3 }

    ibIpaIntListInPackets OBJECT-TYPE
        SYNTAX      Counter32
        MAX-ACCESS  read-only
        STATUS      current
        DESCRIPTION
            "
            The number of inbound packets in ibIpaIntListTable.
            "
        ::= { ibIpaIntListEntry 4 }

    ibIpaIntListInBytes OBJECT-TYPE
        SYNTAX      Counter64
        MAX-ACCESS  read-only
        STATUS      current
        DESCRIPTION
            "
            The number of inbound bytes in ibIpaIntListTable.
            "
        ::= { ibIpaIntListEntry 5 }

    ibIpaIntListOutPackets OBJECT-TYPE
        SYNTAX      Counter32
        MAX-ACCESS  read-only
        STATUS      current
        DESCRIPTION
            "
            The number of outbound Packets in ibIpaIntListTable.
            "
        ::= { ibIpaIntListEntry 6 }

    ibIpaIntListOutBytes OBJECT-TYPE
        SYNTAX      Counter64
        MAX-ACCESS  read-only
        STATUS      current
        DESCRIPTION
            "
            The number of outbound bytes in ibIpaIntListTable.
            "
        ::= { ibIpaIntListEntry 7 }

-- =============================================================================
    -- ibIpaExtListTable
    -- for showing accounting information of packet not match ibIpaAccountListTable

    ibIpaExtListTable OBJECT-TYPE
        SYNTAX   SEQUENCE OF IbIpaExtListEntry
        MAX-ACCESS   not-accessible
        STATUS   current
        DESCRIPTION
            "
            If mismatching the ip address recorded in the ibIpaAccountListTable
            and not denied by the firewall, the packets will be accounted
            in this list.
            "
        ::= { ibIpa 5 }

    ibIpaExtListEntry OBJECT-TYPE
        SYNTAX   IbIpaExtListEntry
        MAX-ACCESS   not-accessible
        STATUS   current
        DESCRIPTION
           "
           Entry of the table.
           "
        INDEX { ibIpaExtListIpSrc,
                ibIpaExtListIpDst,
                ibIpaExtListProtocol
              }
        ::= { ibIpaExtListTable 1 }

    IbIpaExtListEntry ::=
        SEQUENCE {
            ibIpaExtListIpSrc
                IpAddress,
            ibIpaExtListIpDst
                IpAddress,
            ibIpaExtListProtocol
                Integer32,
            ibIpaExtListInPackets
                Counter32,
            ibIpaExtListInBytes
                Counter64,
            ibIpaExtListOutPackets
                Counter32,
            ibIpaExtListOutBytes
                Counter64
        }

    ibIpaExtListIpSrc OBJECT-TYPE
        SYNTAX      IpAddress
        MAX-ACCESS  not-accessible
        STATUS      current
        DESCRIPTION
            "
            Source IP-address of these accounted packets.
            "
        ::= { ibIpaExtListEntry 1 }

    ibIpaExtListIpDst OBJECT-TYPE
        SYNTAX      IpAddress
        MAX-ACCESS  not-accessible
        STATUS      current
        DESCRIPTION
            "
            Destination IP-address of these accounted packets.
            "
        ::= { ibIpaExtListEntry 2 }

    ibIpaExtListProtocol OBJECT-TYPE
        SYNTAX Integer32(0..2147483647)
        MAX-ACCESS  not-accessible
        STATUS      current
        DESCRIPTION
            "
            The value indicates the value of the 'protocol' field
            which is part of ip packet header.
            "
        ::= { ibIpaExtListEntry 3 }

    ibIpaExtListInPackets OBJECT-TYPE
        SYNTAX      Counter32
        MAX-ACCESS  read-only
        STATUS      current
        DESCRIPTION
            "
            The number of inbound packets in ibIpaExtListTable.
            "
        ::= { ibIpaExtListEntry 4 }

    ibIpaExtListInBytes OBJECT-TYPE
        SYNTAX      Counter64
        MAX-ACCESS  read-only
        STATUS      current
        DESCRIPTION
            "
            The number of inbound bytes in ibIpaExtListTable.
            "
        ::= { ibIpaExtListEntry 5 }

    ibIpaExtListOutPackets OBJECT-TYPE
        SYNTAX      Counter32
        MAX-ACCESS  read-only
        STATUS      current
        DESCRIPTION
            "
            The number of outbound packets in ibIpaExtListTable.
            "
        ::= { ibIpaExtListEntry 6 }

    ibIpaExtListOutBytes OBJECT-TYPE
        SYNTAX      Counter64
        MAX-ACCESS  read-only
        STATUS      current
        DESCRIPTION
            "
            The number of outbound bytes in ibIpaExtListTable.
            "
        ::= { ibIpaExtListEntry 7 }

-- =============================================================================
    -- ibIpaFWListTable
    -- for showing accounting information of packet denied by the firewall

    ibIpaFWListTable OBJECT-TYPE
        SYNTAX   SEQUENCE OF IbIpaFWListEntry
        MAX-ACCESS   not-accessible
        STATUS   current
        DESCRIPTION
            "
            If the packet is denied by the firewall,
            it will be accounted in this list.
            "
        ::= { ibIpa 6 }

    ibIpaFWListEntry OBJECT-TYPE
        SYNTAX   IbIpaFWListEntry
        MAX-ACCESS   not-accessible
        STATUS   current
        DESCRIPTION
            "
            Entry of the table.
            "
        INDEX { ibIpaFWListIpSrc,
                ibIpaFWListIpDst
              }
        ::= { ibIpaFWListTable 1 }

    IbIpaFWListEntry ::=
        SEQUENCE {
            ibIpaFWListIpSrc
                IpAddress,
            ibIpaFWListIpDst
                IpAddress,
            ibIpaFWListInPackets
                Counter32,
            ibIpaFWListInBytes
                Counter64,
            ibIpaFWListOutPackets
                Counter32,
            ibIpaFWListOutBytes
                Counter64
        }

    ibIpaFWListIpSrc OBJECT-TYPE
        SYNTAX      IpAddress
        MAX-ACCESS  not-accessible
        STATUS      current
        DESCRIPTION
             "
             Source IP-address of these accounted packets.
             "
        ::= { ibIpaFWListEntry 1 }

    ibIpaFWListIpDst OBJECT-TYPE
        SYNTAX      IpAddress
        MAX-ACCESS  not-accessible
        STATUS      current
        DESCRIPTION
             "
             Destination IP-address of these accounted packets.
             "
        ::= { ibIpaFWListEntry 2 }

    ibIpaFWListInPackets OBJECT-TYPE
        SYNTAX      Counter32
        MAX-ACCESS  read-only
        STATUS      current
        DESCRIPTION
             "
             The number of outbound packets in ibIpaFWListTable.
             "
        ::= { ibIpaFWListEntry 3 }

    ibIpaFWListInBytes OBJECT-TYPE
        SYNTAX      Counter64
        MAX-ACCESS  read-only
        STATUS      current
        DESCRIPTION
            "
            The number of inbound bytes in ibIpaFWListTable.
            "
        ::= { ibIpaFWListEntry 4 }

    ibIpaFWListOutPackets OBJECT-TYPE
        SYNTAX      Counter32
        MAX-ACCESS  read-only
        STATUS      current
        DESCRIPTION
            "
            The number of outbound packets in ibIpaFWListTable.
            "
        ::= { ibIpaFWListEntry 5 }

   ibIpaFWListOutBytes OBJECT-TYPE
       SYNTAX      Counter64
       MAX-ACCESS  read-only
       STATUS      current
       DESCRIPTION
           "
           The number of outbound bytes in ibIpaFWListTable.
           "
       ::= { ibIpaFWListEntry 6 }

END
