-- =================================================================
-- Copyright (C) 2023 Intelbras S.A. All rights reserved.
--
-- Description: NETCONF mib
-- Reference:
-- Version: V1.2
-- History:
--  V1.0 Created by zhangfeng
--      Initial version 2021-07-07
--  V1.1 2022-06-14 Modified by yuantengfei
--      Added ibNetconfSessionLoginTime, ibNetconfSessionAccessType
--      and ibNetconfSessionUserRole to ibNetconfServerSessionStart.
--      Added ibNetconfSessionLogoutTime, ibNetconfSessionAccessType
--      and ibNetconfSessionUserRole to ibNetconfServerSessionEnd.
--      Added ibNetconfSessionLoginTime and ibNetconfSessionAccessType
--      to ibNetconfServerLoginFailure.
--      Added ibNetconfServerLoginFailure.
--  V1.2 2023-01-01 Modified by xiexiang
--      Added ibNetconfCli.
--      Added ibNetconfEditConfig.
--      Added ibNetconfEditConfigCli.
--      Added ibNetconfMsgDel.
--      Added ibNetconfThread.
--      Added ibNetconfAbnormalReason.
--      Added ibNetconfOperationResult.
-- =================================================================
IB-NETCONF-MIB DEFINITIONS ::= BEGIN

IMPORTS
    MODULE-IDENTITY, OBJECT-TYPE, NOTIFICATION-TYPE,
    Integer32
        FROM SNMPv2-SMI
    DateAndTime, DisplayString
        FROM SNMPv2-TC
    InetAddressType, InetAddress
        FROM INET-ADDRESS-MIB
    ibCommon
        FROM IB-OID-MIB;

ibNetconf MODULE-IDENTITY
    LAST-UPDATED "202301010000Z"
    ORGANIZATION
        "Intelbras S.A. Industria de Telecomunicacao Eletronica Brasileria."
    CONTACT-INFO
        ""
    DESCRIPTION
        "The MIB module is used for NETCONF connection notification."
    REVISION "202301010000Z"
    DESCRIPTION
        "Added ibNetconfCli.
         Added ibNetconfEditConfig.
         Added ibNetconfEditConfigCli.
         Added ibNetconfMsgDel.
         Added ibNetconfThread.
         Added ibNetconfAbnormalReason.
         Added ibNetconfOperationResult"
    REVISION "202206140000Z"
    DESCRIPTION
        "Added ibNetconfSessionLoginTime, ibNetconfSessionAccessType
         and ibNetconfSessionUserRole to ibNetconfServerSessionStart.
         Added ibNetconfSessionLogoutTime, ibNetconfSessionAccessType
         and ibNetconfSessionUserRole to ibNetconfServerSessionEnd.
         Added ibNetconfSessionLoginTime and ibNetconfSessionAccessType
         to ibNetconfServerLoginFailure.
         Added ibNetconfServerLoginFailure."
    REVISION    "202107070000Z"
    DESCRIPTION    "The initial version."
    ::= { ibCommon 206 }

-- ==================================================================
--
-- NETCONF trap object
--
-- ==================================================================
ibNetconfObjects OBJECT IDENTIFIER ::= { ibNetconf 1 }

ibNetconfConnObjects OBJECT IDENTIFIER ::= { ibNetconfObjects 1 }

ibNetconfSessionId OBJECT-TYPE
    SYNTAX       Integer32(1..2147483647)
    MAX-ACCESS   accessible-for-notify
    STATUS   current
    DESCRIPTION
    "ID of a NETCONF session."
    ::= { ibNetconfConnObjects 1 }

ibNetconfSessionUserName OBJECT-TYPE
    SYNTAX       DisplayString (SIZE(1..80))
    MAX-ACCESS   accessible-for-notify
    STATUS   current
    DESCRIPTION
    "Username of the NETCONF session."
    ::= { ibNetconfConnObjects 2 }

ibNetconfSessionPeerIPAddressType OBJECT-TYPE
    SYNTAX       InetAddressType
    MAX-ACCESS   accessible-for-notify
    STATUS   current
    DESCRIPTION
    "Peer IP address type of the NETCONF session."
    ::= { ibNetconfConnObjects 3 }

ibNetconfSessionPeerIPAddress OBJECT-TYPE
    SYNTAX       InetAddress
    MAX-ACCESS   accessible-for-notify
    STATUS   current
    DESCRIPTION
    "Peer IP address of the NETCONF session."
    ::= { ibNetconfConnObjects 4 }

ibNetconfSessionTerminationReason OBJECT-TYPE
    SYNTAX              INTEGER
    {
        other               (1),
        closed              (2),
        linkDown            (3),
        idleTimeout         (4)
    }
    MAX-ACCESS   accessible-for-notify
    STATUS   current
    DESCRIPTION
    "Termination reason of the NETCONF session.
       Value other(1) represents other reason.
       Value closed(2) indicates that the session was closed.
       Value linkDown(3) indicates that the session was abnormal.
       Value idleTimeout(4) indicates that the session timed out."
    ::= { ibNetconfConnObjects 5 }

ibNetconfSessionLoginTime OBJECT-TYPE
    SYNTAX       DateAndTime
    MAX-ACCESS   accessible-for-notify
    STATUS   current
    DESCRIPTION
    "Login time of the NETCONF session.
        For example: 2021-09-14,13:30:16."
    ::= { ibNetconfConnObjects 6 }

ibNetconfSessionLogoutTime OBJECT-TYPE
    SYNTAX       DateAndTime
    MAX-ACCESS   accessible-for-notify
    STATUS   current
    DESCRIPTION
    "Logout time of the NETCONF session.
        For example: 2021-09-14,13:30:16."
    ::= { ibNetconfConnObjects 7 }

ibNetconfSessionAccessType OBJECT-TYPE
    SYNTAX       INTEGER
    {
        other           (1),
        web             (2),
        soap            (3),
        terminal        (4)
    }
    MAX-ACCESS   accessible-for-notify
    STATUS   current
    DESCRIPTION
    "Login type for the NETCONF session.
        Value other(1) represents other type.
        Value web(2) represents Web login.
        Value soap(3) represents SOAP login.
        Value terminal(4) represents terminal login."
    ::= { ibNetconfConnObjects 8 }

ibNetconfSessionUserRole OBJECT-TYPE
    SYNTAX       DisplayString (SIZE(1..80))
    MAX-ACCESS   accessible-for-notify
    STATUS   current
    DESCRIPTION
    "User role of the user established the NETCONF session.
        The user role can be single or multiple, Because the
        size of the defined user role remains unchanged, when
        there are multiple user roles, the user roles may be
        truncated."
::= { ibNetconfConnObjects 9 }

ibNetconfAbnormalReason OBJECT-TYPE
    SYNTAX       DisplayString (SIZE(1..80))
    MAX-ACCESS   accessible-for-notify
    STATUS   current
    DESCRIPTION
    "The abnormal reason of NETCONF server.
        For example: Maximum number of NETCONF threads already reached."
::= { ibNetconfConnObjects 10 }

ibNetconfOperationResult OBJECT-TYPE
    SYNTAX       DisplayString (SIZE(1..80))
    MAX-ACCESS   accessible-for-notify
    STATUS   current
    DESCRIPTION
    "The operation result of NETCONF.
        For example: Succeeded."
::= { ibNetconfConnObjects 11 }


ibNetconfTrap OBJECT IDENTIFIER ::= { ibNetconf 2 }

ibNetconfConnTrapPrefix OBJECT IDENTIFIER ::= { ibNetconfTrap 0 }

ibNetconfServerSessionStart NOTIFICATION-TYPE
    OBJECTS {
            ibNetconfSessionId,
            ibNetconfSessionUserName,
            ibNetconfSessionPeerIPAddressType,
            ibNetconfSessionPeerIPAddress,
            ibNetconfSessionLoginTime,
            ibNetconfSessionAccessType,
            ibNetconfSessionUserRole
        }
    STATUS  current
    DESCRIPTION
        "The NETCONF server created a session."
::= { ibNetconfConnTrapPrefix 1 }

ibNetconfServerSessionEnd NOTIFICATION-TYPE
    OBJECTS {
            ibNetconfSessionId,
            ibNetconfSessionUserName,
            ibNetconfSessionPeerIPAddressType,
            ibNetconfSessionPeerIPAddress,
            ibNetconfSessionTerminationReason,
            ibNetconfSessionLogoutTime,
            ibNetconfSessionAccessType,
            ibNetconfSessionUserRole
        }
    STATUS  current
    DESCRIPTION
        "A session created by the NETCONF server ended."
::= { ibNetconfConnTrapPrefix 2 }

ibNetconfServerLoginFailure NOTIFICATION-TYPE
    OBJECTS {
            ibNetconfSessionUserName,
            ibNetconfSessionPeerIPAddressType,
            ibNetconfSessionPeerIPAddress,
            ibNetconfSessionLoginTime,
            ibNetconfSessionAccessType
        }
    STATUS  current
    DESCRIPTION
        "Failure in accessing the NETCONF server through a NETCONF session."
::= { ibNetconfConnTrapPrefix 3 }

ibNetconfCli NOTIFICATION-TYPE
    OBJECTS {
            ibNetconfSessionId,
            ibNetconfSessionUserName,
            ibNetconfOperationResult
        }
    STATUS  current
    DESCRIPTION
        "The NETCONF operation of cli."
::= { ibNetconfConnTrapPrefix 4 }

ibNetconfEditConfig NOTIFICATION-TYPE
    OBJECTS {
            ibNetconfSessionId,
            ibNetconfSessionUserName,
            ibNetconfOperationResult
        }
    STATUS  current
    DESCRIPTION
        "The NETCONF operation of edit config."
::= { ibNetconfConnTrapPrefix 5 }

ibNetconfEditConfigCli NOTIFICATION-TYPE
    OBJECTS {
            ibNetconfSessionId,
            ibNetconfSessionUserName,
            ibNetconfOperationResult
        }
    STATUS  current
    DESCRIPTION
        "The NETCONF operation of edit config cli."
::= { ibNetconfConnTrapPrefix 6 }

ibNetconfMsgDel NOTIFICATION-TYPE
    OBJECTS {
            ibNetconfAbnormalReason
        }
    STATUS  current
    DESCRIPTION
        "The packet size exceeded the upper limit."
::= { ibNetconfConnTrapPrefix 7 }

ibNetconfThread NOTIFICATION-TYPE
    OBJECTS {
            ibNetconfAbnormalReason
        }
    STATUS  current
    DESCRIPTION
        "Maximum number of NETCONF threads already reached."
::= { ibNetconfConnTrapPrefix 8 }
END
